-- GENERATED MIB FILE. DO NOT EDIT --
BEA-WEBLOGIC-MIB DEFINITIONS ::= BEGIN

   IMPORTS
      
      DisplayString    
      			FROM RFC1213-MIB
      
      OBJECT-TYPE, MODULE-IDENTITY, Counter32, Integer32, 
      Counter64, NOTIFICATION-TYPE    
      			
      			FROM SNMPv2-SMI;
   
   
   wls MODULE-IDENTITY
      LAST-UPDATED "070515160000Z"
      ORGANIZATION "BEA Systems Inc."
      CONTACT-INFO "www.bea.com"
      DESCRIPTION "BEA"
      ::= { bea 625  }
      
   
   bea OBJECT IDENTIFIER ::= { enterprises 140  }
   
   experimental OBJECT IDENTIFIER ::= { wls 10  }
   
   trapVars OBJECT IDENTIFIER ::= { wls 100  }
   
   alsb OBJECT IDENTIFIER ::= { bea 800  }
   
   alsbTrapVars OBJECT IDENTIFIER ::= { alsb 100  }
   
   mibObjectName OBJECT-TYPE
      SYNTAX      DisplayString (SIZE (1..512))
      MAX-ACCESS  read-write
      STATUS      current
      DESCRIPTION "Name of the Mib Object in the form <MBeanType>:<MBeanName>:<AttributeName>."
      ::= { experimental 1  }
   
   mibObjectOid OBJECT-TYPE
      SYNTAX      OBJECT IDENTIFIER
      MAX-ACCESS  read-only
      STATUS      current
      DESCRIPTION "The Oid of the Mib object name, that was specified in the MibObjectName."
      ::= { experimental 2  }
   
   trapTime OBJECT-TYPE
      SYNTAX      DisplayString (SIZE (1..32))
      MAX-ACCESS  read-only
      STATUS      current
      DESCRIPTION "A string that indicates the time"
      ::= { trapVars 5  }
   
   trapServerName OBJECT-TYPE
      SYNTAX      DisplayString (SIZE (1..64))
      MAX-ACCESS  read-only
      STATUS      current
      DESCRIPTION "A string that indicates the server which generated the trap"
      ::= { trapVars 10  }
   
   trapMachineName OBJECT-TYPE
      SYNTAX      DisplayString (SIZE (1..64))
      MAX-ACCESS  read-only
      STATUS      current
      DESCRIPTION "A string that indicates the machine where the trap is generated"
      ::= { trapVars 15  }
   
   trapLogThreadId OBJECT-TYPE
      SYNTAX      DisplayString (SIZE (1..16))
      MAX-ACCESS  read-only
      STATUS      current
      DESCRIPTION "An integer that indicates the if of the thread in which the trap is generated"
      ::= { trapVars 20  }
   
   trapLogTransactionId OBJECT-TYPE
      SYNTAX      DisplayString (SIZE (1..64))
      MAX-ACCESS  read-only
      STATUS      current
      DESCRIPTION "A string that indicates the transactions from which the trap is generated"
      ::= { trapVars 25  }
   
   trapLogUserId OBJECT-TYPE
      SYNTAX      DisplayString (SIZE (1..32))
      MAX-ACCESS  read-only
      STATUS      current
      DESCRIPTION "A string that indicates the user id from which the trap is generated"
      ::= { trapVars 30  }
   
   trapLogSubsystem OBJECT-TYPE
      SYNTAX      DisplayString (SIZE (1..32))
      MAX-ACCESS  read-only
      STATUS      current
      DESCRIPTION "A string that indicates the subsystem from which the trap is generated"
      ::= { trapVars 35  }
   
   trapLogMsgId OBJECT-TYPE
      SYNTAX      DisplayString (SIZE (1..16))
      MAX-ACCESS  read-only
      STATUS      current
      DESCRIPTION "An intefer that indicates the trap's message id"
      ::= { trapVars 40  }
   
   trapLogSeverity OBJECT-TYPE
      SYNTAX      DisplayString (SIZE (1..16))
      MAX-ACCESS  read-only
      STATUS      current
      DESCRIPTION "A string that indicates the severity of the trap's message"
      ::= { trapVars 45  }
   
   trapLogMessage OBJECT-TYPE
      SYNTAX      DisplayString (SIZE (1..1024))
      MAX-ACCESS  read-only
      STATUS      current
      DESCRIPTION "A string that includes the body of the log message"
      ::= { trapVars 50  }
   
   trapMonitorType OBJECT-TYPE
      SYNTAX      DisplayString (SIZE (1..16))
      MAX-ACCESS  read-only
      STATUS      current
      DESCRIPTION "A string that should be either CounterMonitor, or GaugeMonitor, or StringMonitor"
      ::= { trapVars 55  }
   
   trapMonitorThreshold OBJECT-TYPE
      SYNTAX      DisplayString (SIZE (1..32))
      MAX-ACCESS  read-only
      STATUS      current
      DESCRIPTION "An ASCII-string representation of the value which triggerd this monitor"
      ::= { trapVars 60  }
   
   trapMonitorValue OBJECT-TYPE
      SYNTAX      DisplayString (SIZE (1..32))
      MAX-ACCESS  read-only
      STATUS      current
      DESCRIPTION "An ASCII-string representation, which is the derived value"
      ::= { trapVars 65  }
   
   trapMBeanName OBJECT-TYPE
      SYNTAX      DisplayString (SIZE (1..256))
      MAX-ACCESS  read-only
      STATUS      current
      DESCRIPTION "The Name of the MBean"
      ::= { trapVars 70  }
   
   trapMBeanType OBJECT-TYPE
      SYNTAX      DisplayString (SIZE (1..256))
      MAX-ACCESS  read-only
      STATUS      current
      DESCRIPTION "The type of the MBean"
      ::= { trapVars 75  }
   
   trapAttributeName OBJECT-TYPE
      SYNTAX      DisplayString (SIZE (1..256))
      MAX-ACCESS  read-only
      STATUS      current
      DESCRIPTION "The name of an attribute"
      ::= { trapVars 80  }
   
   trapAttributeType OBJECT-TYPE
      SYNTAX      DisplayString (SIZE (1..32))
      MAX-ACCESS  read-only
      STATUS      current
      DESCRIPTION "The type of an attribute"
      ::= { trapVars 85  }
   
   trapAttributeChangeType OBJECT-TYPE
      SYNTAX      DisplayString (SIZE (1..32))
      MAX-ACCESS  read-only
      STATUS      current
      DESCRIPTION "The type of Change, an attribute has gone thru. It can be either ADD, or REMOVE, or UPDATE"
      ::= { trapVars 90  }
   
   trapAttributeOldVal OBJECT-TYPE
      SYNTAX      DisplayString (SIZE (1..512))
      MAX-ACCESS  read-only
      STATUS      current
      DESCRIPTION "The OLD value of an attribute"
      ::= { trapVars 95  }
   
   trapAttributeNewVal OBJECT-TYPE
      SYNTAX      DisplayString (SIZE (1..512))
      MAX-ACCESS  read-only
      STATUS      current
      DESCRIPTION "The NEW value of an attribute"
      ::= { trapVars 100  }
   
   trapWatchName OBJECT-TYPE
      SYNTAX      DisplayString (SIZE (1..512))
      MAX-ACCESS  read-only
      STATUS      current
      DESCRIPTION "The name of the watch that evaluated to true"
      ::= { trapVars 105  }
   
   trapWatchRuleType OBJECT-TYPE
      SYNTAX      DisplayString (SIZE (1..32))
      MAX-ACCESS  read-only
      STATUS      current
      DESCRIPTION "The type of watch rule"
      ::= { trapVars 110  }
   
   trapWatchRule OBJECT-TYPE
      SYNTAX      DisplayString (SIZE (1..2048))
      MAX-ACCESS  read-only
      STATUS      current
      DESCRIPTION "The watch rule expression"
      ::= { trapVars 115  }
   
   trapWatchSeverity OBJECT-TYPE
      SYNTAX      DisplayString (SIZE (1..16))
      MAX-ACCESS  read-only
      STATUS      current
      DESCRIPTION "A string that indicates the severity of the watch rule"
      ::= { trapVars 120  }
   
   trapWatchData OBJECT-TYPE
      SYNTAX      DisplayString (SIZE (1..2048))
      MAX-ACCESS  read-only
      STATUS      current
      DESCRIPTION "A string that indicates the key value data of the event that satisfied the watch rule"
      ::= { trapVars 125  }
   
   trapWatchAlarmType OBJECT-TYPE
      SYNTAX      DisplayString (SIZE (1..32))
      MAX-ACCESS  read-only
      STATUS      current
      DESCRIPTION "The type of alarm for the watch rule"
      ::= { trapVars 130  }
   
   trapWatchAlarmResetPeriod OBJECT-TYPE
      SYNTAX      DisplayString (SIZE (1..16))
      MAX-ACCESS  read-only
      STATUS      current
      DESCRIPTION "The period to elaspe before the alarm is reset applicable for AutomaticReset type watches"
      ::= { trapVars 135  }
   
   trapWatchSNMPNotificationName OBJECT-TYPE
      SYNTAX      DisplayString (SIZE (1..16))
      MAX-ACCESS  read-only
      STATUS      current
      DESCRIPTION "The name of the configured WLDFSNMPNotification that issued this trap"
      ::= { trapVars 140  }
   
   trapDomainName OBJECT-TYPE
      SYNTAX      DisplayString (SIZE (1..16))
      MAX-ACCESS  read-only
      STATUS      current
      DESCRIPTION "The name of the WebLogic domain in which this trap occurred"
      ::= { trapVars 145  }
   
   trapALSBAlertTrapType OBJECT-TYPE
      SYNTAX      DisplayString (SIZE (1..16))
      MAX-ACCESS  read-only
      STATUS      current
      DESCRIPTION "The Type of the ALSB Alert that caused this trap to occur"
      ::= { alsbTrapVars 1  }
   
   trapALSBAlertSeverity OBJECT-TYPE
      SYNTAX      DisplayString (SIZE (1..16))
      MAX-ACCESS  read-only
      STATUS      current
      DESCRIPTION "The Severity of the ALSB Alert that caused this trap to occur"
      ::= { alsbTrapVars 2  }
   
   trapALSBAlertDomainName OBJECT-TYPE
      SYNTAX      DisplayString (SIZE (1..64))
      MAX-ACCESS  read-only
      STATUS      current
      DESCRIPTION "The Domain Name for the domain in which the ALSB Alert occurred"
      ::= { alsbTrapVars 3  }
   
   trapALSBAlertServerName OBJECT-TYPE
      SYNTAX      DisplayString (SIZE (1..64))
      MAX-ACCESS  read-only
      STATUS      current
      DESCRIPTION "The Server Name for the server on which the ALSB Alert occurred"
      ::= { alsbTrapVars 4  }
   
   trapALSBAlertAlertId OBJECT-TYPE
      SYNTAX      DisplayString (SIZE (1..64))
      MAX-ACCESS  read-only
      STATUS      current
      DESCRIPTION "The Alert Id for the ALSB Alert that caused this trap to occur"
      ::= { alsbTrapVars 5  }
   
   trapALSBAlertRuleId OBJECT-TYPE
      SYNTAX      DisplayString (SIZE (1..64))
      MAX-ACCESS  read-only
      STATUS      current
      DESCRIPTION "The Rule Id for the ALSB Alert that caused this trap to occur"
      ::= { alsbTrapVars 6  }
   
   trapALSBAlertRuleName OBJECT-TYPE
      SYNTAX      DisplayString (SIZE (1..80))
      MAX-ACCESS  read-only
      STATUS      current
      DESCRIPTION "The Rule Name for the ALSB Alert that caused this trap to occur"
      ::= { alsbTrapVars 7  }
   
   trapALSBAlertRuleCondition OBJECT-TYPE
      SYNTAX      DisplayString (SIZE (1..512))
      MAX-ACCESS  read-only
      STATUS      current
      DESCRIPTION "The Rule Condition for the ALSB Alert that caused this trap to occur"
      ::= { alsbTrapVars 8  }
   
   trapALSBAlertAlertTime OBJECT-TYPE
      SYNTAX      DisplayString (SIZE (1..48))
      MAX-ACCESS  read-only
      STATUS      current
      DESCRIPTION "The Time that the ALSB Alert was raised that caused this trap to occur"
      ::= { alsbTrapVars 9  }
   
   trapALSBAlertAnnotation OBJECT-TYPE
      SYNTAX      DisplayString (SIZE (1..1024))
      MAX-ACCESS  read-only
      STATUS      current
      DESCRIPTION "The Annotation for the ALSB Alert that caused this trap to occur"
      ::= { alsbTrapVars 10  }
   
   trapALSBAlertServiceName OBJECT-TYPE
      SYNTAX      DisplayString (SIZE (1..80))
      MAX-ACCESS  read-only
      STATUS      current
      DESCRIPTION "The Service Name for the ALSB Alert that caused this trap to occur"
      ::= { alsbTrapVars 11  }
   
   trapALSBAlertServicePath OBJECT-TYPE
      SYNTAX      DisplayString (SIZE (1..256))
      MAX-ACCESS  read-only
      STATUS      current
      DESCRIPTION "The Service Path for the ALSB Alert that caused this trap to occur"
      ::= { alsbTrapVars 12  }
   
   applicationRuntimeTable OBJECT-TYPE
      SYNTAX      SEQUENCE OF ApplicationRuntimeEntry
      MAX-ACCESS  not-accessible
      STATUS      current
      DESCRIPTION "This table used for any application specific parameters"
      ::= { wls 105  }
      
   
   applicationRuntimeEntry OBJECT-TYPE
      SYNTAX      ApplicationRuntimeEntry
      MAX-ACCESS  not-accessible
      STATUS      current
      DESCRIPTION "Entry of applicationRuntimeTable"
      INDEX { applicationRuntimeIndex}
      ::= { applicationRuntimeTable 1 }
      
   ApplicationRuntimeEntry ::=
      SEQUENCE
      {
         applicationRuntimeIndex DisplayString (SIZE (1..16)),
         applicationRuntimeObjectName DisplayString (SIZE (1..256)),
         applicationRuntimeType DisplayString (SIZE (1..64)),
         applicationRuntimeName DisplayString (SIZE (1..64)),
         applicationRuntimeParent DisplayString (SIZE (1..256)),
         applicationRuntimeApplicationName DisplayString (SIZE (1..2048)),
         applicationRuntimeApplicationVersion OCTET STRING
      }
      
   
   applicationRuntimeIndex OBJECT-TYPE
      SYNTAX      DisplayString (SIZE (1..16))
      MAX-ACCESS  read-only
      STATUS      current
      DESCRIPTION "Unique value directed from ObjectName which is used as table index"
      ::= { applicationRuntimeEntry 1  }
   
   
   applicationRuntimeObjectName OBJECT-TYPE
      SYNTAX      DisplayString (SIZE (1..256))
      MAX-ACCESS  read-only
      STATUS      current
      DESCRIPTION "JMX-standard MBean name"
      ::= { applicationRuntimeEntry 5  }
   
   
   applicationRuntimeType OBJECT-TYPE
      SYNTAX      DisplayString (SIZE (1..64))
      MAX-ACCESS  read-only
      STATUS      current
      DESCRIPTION "BEA-proprietary MBean type"
      ::= { applicationRuntimeEntry 10  }
   
   
   applicationRuntimeName OBJECT-TYPE
      SYNTAX      DisplayString (SIZE (1..64))
      MAX-ACCESS  read-only
      STATUS      current
      DESCRIPTION "BEA-proprietary MBean name"
      ::= { applicationRuntimeEntry 15  }
   
   
   applicationRuntimeParent OBJECT-TYPE
      SYNTAX      DisplayString (SIZE (1..256))
      MAX-ACCESS  read-only
      STATUS      current
      DESCRIPTION "BEA-proprietary Parent object's identification, with syntax
      <type>:<name>"
      ::= { applicationRuntimeEntry 20  }
   
   
   applicationRuntimeApplicationName OBJECT-TYPE
      SYNTAX      DisplayString (SIZE (1..2048))
      MAX-ACCESS  read-only
      STATUS      current
      DESCRIPTION "The application Name."
      ::= { applicationRuntimeEntry 25  }
   
   
   applicationRuntimeApplicationVersion OBJECT-TYPE
      SYNTAX      OCTET STRING
      MAX-ACCESS  read-only
      STATUS      current
      DESCRIPTION "The Enterprise application's version identifier.  This is particularly useful, when using the side-by-side deployment feature, to differentiate between two different versions of the same application that are deployed at the same time."
      ::= { applicationRuntimeEntry 26  }
   
   
   clusterRuntimeTable OBJECT-TYPE
      SYNTAX      SEQUENCE OF ClusterRuntimeEntry
      MAX-ACCESS  not-accessible
      STATUS      current
      DESCRIPTION "This table is used for monitoring a server's view of the members
      of a WebLogic cluster within a WebLogic domain"
      ::= { wls 110  }
      
   
   clusterRuntimeEntry OBJECT-TYPE
      SYNTAX      ClusterRuntimeEntry
      MAX-ACCESS  not-accessible
      STATUS      current
      DESCRIPTION "Entry of clusterRuntimeTable"
      INDEX { clusterRuntimeIndex}
      ::= { clusterRuntimeTable 1 }
      
   ClusterRuntimeEntry ::=
      SEQUENCE
      {
         clusterRuntimeIndex  DisplayString (SIZE (1..16)),
         clusterRuntimeObjectName DisplayString (SIZE (1..256)),
         clusterRuntimeType   DisplayString (SIZE (1..64)),
         clusterRuntimeName   DisplayString (SIZE (1..64)),
         clusterRuntimeParent DisplayString (SIZE (1..256)),
         clusterRuntimeAliveServerCount INTEGER,
         clusterRuntimeResendRequestsCount Counter64,
         clusterRuntimeFragmentsSentCount Counter64,
         clusterRuntimeFragmentsReceivedCount Counter64,
         clusterRuntimeMulticastMessagesLostCount Counter64,
         clusterRuntimeServerNames DisplayString (SIZE (1..2048)),
         clusterRuntimeSecondaryDistributionNames DisplayString (SIZE (1..2048)),
         clusterRuntimePrimaryCount Counter64,
         clusterRuntimeCurrentSecondaryServer OCTET STRING,
         clusterRuntimeForeignFragmentsDroppedCount Counter64,
         clusterRuntimeCurrentAsyncSecondaryServer OCTET STRING,
         clusterRuntimeAsyncPrimaryCount Counter64
      }
      
   
   clusterRuntimeIndex OBJECT-TYPE
      SYNTAX      DisplayString (SIZE (1..16))
      MAX-ACCESS  read-only
      STATUS      current
      DESCRIPTION "Unique value directed from ObjectName which is used as table index"
      ::= { clusterRuntimeEntry 1  }
   
   
   clusterRuntimeObjectName OBJECT-TYPE
      SYNTAX      DisplayString (SIZE (1..256))
      MAX-ACCESS  read-only
      STATUS      current
      DESCRIPTION "JMX-standard MBean name"
      ::= { clusterRuntimeEntry 5  }
   
   
   clusterRuntimeType OBJECT-TYPE
      SYNTAX      DisplayString (SIZE (1..64))
      MAX-ACCESS  read-only
      STATUS      current
      DESCRIPTION "BEA-proprietary MBean type"
      ::= { clusterRuntimeEntry 10  }
   
   
   clusterRuntimeName OBJECT-TYPE
      SYNTAX      DisplayString (SIZE (1..64))
      MAX-ACCESS  read-only
      STATUS      current
      DESCRIPTION "BEA-proprietary MBean name"
      ::= { clusterRuntimeEntry 15  }
   
   
   clusterRuntimeParent OBJECT-TYPE
      SYNTAX      DisplayString (SIZE (1..256))
      MAX-ACCESS  read-only
      STATUS      current
      DESCRIPTION "BEA-proprietary Parent object's identification, with syntax
      <type>:<name>"
      ::= { clusterRuntimeEntry 20  }
   
   
   clusterRuntimeAliveServerCount OBJECT-TYPE
      SYNTAX      INTEGER
      MAX-ACCESS  read-only
      STATUS      current
      DESCRIPTION "The current total number of alive servers in this cluster."
      ::= { clusterRuntimeEntry 25  }
   
   
   clusterRuntimeResendRequestsCount OBJECT-TYPE
      SYNTAX      Counter64
      MAX-ACCESS  read-only
      STATUS      current
      DESCRIPTION "The number of state-delta messages that had to be resent 
      because a receiving server in the cluster missed a message."
      ::= { clusterRuntimeEntry 30  }
   
   
   clusterRuntimeFragmentsSentCount OBJECT-TYPE
      SYNTAX      Counter64
      MAX-ACCESS  read-only
      STATUS      current
      DESCRIPTION "The total number of multicast fragments sent
      from this server into the cluster."
      ::= { clusterRuntimeEntry 35  }
   
   
   clusterRuntimeFragmentsReceivedCount OBJECT-TYPE
      SYNTAX      Counter64
      MAX-ACCESS  read-only
      STATUS      current
      DESCRIPTION "The total number of multicast messages received
      on this server from the cluster."
      ::= { clusterRuntimeEntry 40  }
   
   
   clusterRuntimeMulticastMessagesLostCount OBJECT-TYPE
      SYNTAX      Counter64
      MAX-ACCESS  read-only
      STATUS      current
      DESCRIPTION "The total number of in-coming multicast messages that
      were lost according to this server."
      ::= { clusterRuntimeEntry 45  }
   
   
   clusterRuntimeServerNames OBJECT-TYPE
      SYNTAX      DisplayString (SIZE (1..2048))
      MAX-ACCESS  read-only
      STATUS      current
      DESCRIPTION "The names of the servers in the cluster."
      ::= { clusterRuntimeEntry 50  }
   
   
   clusterRuntimeSecondaryDistributionNames OBJECT-TYPE
      SYNTAX      DisplayString (SIZE (1..2048))
      MAX-ACCESS  read-only
      STATUS      current
      DESCRIPTION "Answer the names of the remote servers (e.g. myserver) of which the local 
      server is hosting secondary objects. The name is appended with a number
      to indicate the number of secondaries hosted on behalf of that server."
      ::= { clusterRuntimeEntry 55  }
   
   
   clusterRuntimePrimaryCount OBJECT-TYPE
      SYNTAX      Counter64
      MAX-ACCESS  read-only
      STATUS      current
      DESCRIPTION "Answer the number of object that the local server hosts as primaries."
      ::= { clusterRuntimeEntry 60  }
   
   
   clusterRuntimeCurrentSecondaryServer OBJECT-TYPE
      SYNTAX      OCTET STRING
      MAX-ACCESS  read-only
      STATUS      current
      DESCRIPTION ""
      ::= { clusterRuntimeEntry 61  }
   
   
   clusterRuntimeForeignFragmentsDroppedCount OBJECT-TYPE
      SYNTAX      Counter64
      MAX-ACCESS  read-only
      STATUS      current
      DESCRIPTION "Provides the number of fragments that originated in foreign domains or clusters which use the same multicast address.  Answer the number of fragments that originated in foreign domains/cluster that use the same multicast address."
      ::= { clusterRuntimeEntry 62  }
   
   
   clusterRuntimeCurrentAsyncSecondaryServer OBJECT-TYPE
      SYNTAX      OCTET STRING
      MAX-ACCESS  read-only
      STATUS      current
      DESCRIPTION " "
      ::= { clusterRuntimeEntry 63  }
   
   
   clusterRuntimeAsyncPrimaryCount OBJECT-TYPE
      SYNTAX      Counter64
      MAX-ACCESS  read-only
      STATUS      current
      DESCRIPTION " Provides the number of objects hosted by Aysnc Replication Manager on local server as primaries. "
      ::= { clusterRuntimeEntry 64  }
   
   
   wanreplicationRuntimeTable OBJECT-TYPE
      SYNTAX      SEQUENCE OF WanreplicationRuntimeEntry
      MAX-ACCESS  not-accessible
      STATUS      current
      DESCRIPTION "This table is used for monitoring a WANreplication within a WebLogic domain"
      ::= { wls 111  }
      
   
   wanreplicationRuntimeEntry OBJECT-TYPE
      SYNTAX      WanreplicationRuntimeEntry
      MAX-ACCESS  not-accessible
      STATUS      current
      DESCRIPTION "Entry of wanreplicationRuntimeTable"
      INDEX { wanreplicationRuntimeIndex}
      ::= { wanreplicationRuntimeTable 1 }
      
   WanreplicationRuntimeEntry ::=
      SEQUENCE
      {
         wanreplicationRuntimeIndex DisplayString (SIZE (1..16)),
         wanreplicationRuntimeObjectName DisplayString (SIZE (1..256)),
         wanreplicationRuntimeType DisplayString (SIZE (1..64)),
         wanreplicationRuntimeName DisplayString (SIZE (1..64)),
         wanreplicationRuntimeParent DisplayString (SIZE (1..256)),
         wanreplicationRuntimeNumberOfSessionsFlushedToTheDatabase Counter64,
         wanreplicationRuntimeNumberOfSessionsRetrievedFromTheDatabase Counter64,
         wanreplicationRuntimeSecondaryServerName DisplayString (SIZE (1..128)),
         wanreplicationRuntimePrimaryCount Counter64,
         wanreplicationRuntimeSecondaryCount Counter64,
         wanreplicationRuntimeRemoteClusterReachable INTEGER
      }
      
   
   wanreplicationRuntimeIndex OBJECT-TYPE
      SYNTAX      DisplayString (SIZE (1..16))
      MAX-ACCESS  read-only
      STATUS      current
      DESCRIPTION "Unique value directed from ObjectName which is used as table index"
      ::= { wanreplicationRuntimeEntry 1  }
   
   
   wanreplicationRuntimeObjectName OBJECT-TYPE
      SYNTAX      DisplayString (SIZE (1..256))
      MAX-ACCESS  read-only
      STATUS      current
      DESCRIPTION "JMX-standard MBean name"
      ::= { wanreplicationRuntimeEntry 5  }
   
   
   wanreplicationRuntimeType OBJECT-TYPE
      SYNTAX      DisplayString (SIZE (1..64))
      MAX-ACCESS  read-only
      STATUS      current
      DESCRIPTION "BEA-proprietary MBean type"
      ::= { wanreplicationRuntimeEntry 10  }
   
   
   wanreplicationRuntimeName OBJECT-TYPE
      SYNTAX      DisplayString (SIZE (1..64))
      MAX-ACCESS  read-only
      STATUS      current
      DESCRIPTION "BEA-proprietary MBean name"
      ::= { wanreplicationRuntimeEntry 15  }
   
   
   wanreplicationRuntimeParent OBJECT-TYPE
      SYNTAX      DisplayString (SIZE (1..256))
      MAX-ACCESS  read-only
      STATUS      current
      DESCRIPTION "BEA-proprietary Parent object's identification, with syntax <type>:<name>"
      ::= { wanreplicationRuntimeEntry 20  }
   
   
   wanreplicationRuntimeNumberOfSessionsFlushedToTheDatabase OBJECT-TYPE
      SYNTAX      Counter64
      MAX-ACCESS  read-only
      STATUS      current
      DESCRIPTION "Returns the count of the number of sessions that have been flushed to the database."
      ::= { wanreplicationRuntimeEntry 25  }
   
   
   wanreplicationRuntimeNumberOfSessionsRetrievedFromTheDatabase OBJECT-TYPE
      SYNTAX      Counter64
      MAX-ACCESS  read-only
      STATUS      current
      DESCRIPTION "Returns the count of the number of sessions that have been retrieved from the database."
      ::= { wanreplicationRuntimeEntry 30  }
   
   
   wanreplicationRuntimeSecondaryServerName OBJECT-TYPE
      SYNTAX      DisplayString (SIZE (1..128))
      MAX-ACCESS  read-only
      STATUS      current
      DESCRIPTION "Returns the name of the current secondary server."
      ::= { wanreplicationRuntimeEntry 35  }
   
   
   wanreplicationRuntimePrimaryCount OBJECT-TYPE
      SYNTAX      Counter64
      MAX-ACCESS  read-only
      STATUS      current
      DESCRIPTION "Returns the number of object that the local server hosts as primaries."
      ::= { wanreplicationRuntimeEntry 40  }
   
   
   wanreplicationRuntimeSecondaryCount OBJECT-TYPE
      SYNTAX      Counter64
      MAX-ACCESS  read-only
      STATUS      current
      DESCRIPTION "Returns the number of object that the local server hosts as secondaries."
      ::= { wanreplicationRuntimeEntry 45  }
   
   
   wanreplicationRuntimeRemoteClusterReachable OBJECT-TYPE
      SYNTAX      INTEGER
      MAX-ACCESS  read-only
      STATUS      current
      DESCRIPTION "Returns true if the remote cluster is reachable."
      ::= { wanreplicationRuntimeEntry 50  }
   
   
   deploymentTaskRuntimeTable OBJECT-TYPE
      SYNTAX      SEQUENCE OF DeploymentTaskRuntimeEntry
      MAX-ACCESS  not-accessible
      STATUS      current
      DESCRIPTION "This table is used for monitoring a WebLogic deploymentTask."
      ::= { wls 121  }
      
   
   deploymentTaskRuntimeEntry OBJECT-TYPE
      SYNTAX      DeploymentTaskRuntimeEntry
      MAX-ACCESS  not-accessible
      STATUS      current
      DESCRIPTION "Entry of deploymentTaskRuntimeTable"
      INDEX { deploymentTaskRuntimeIndex}
      ::= { deploymentTaskRuntimeTable 1 }
      
   DeploymentTaskRuntimeEntry ::=
      SEQUENCE
      {
         deploymentTaskRuntimeIndex DisplayString (SIZE (1..16)),
         deploymentTaskRuntimeObjectName DisplayString (SIZE (1..256)),
         deploymentTaskRuntimeType DisplayString (SIZE (1..64)),
         deploymentTaskRuntimeName DisplayString (SIZE (1..64)),
         deploymentTaskRuntimeParent DisplayString (SIZE (1..256)),
         deploymentTaskRuntimeApplicationName DisplayString (SIZE (1..256)),
         deploymentTaskRuntimeId DisplayString (SIZE (1..256)),
         deploymentTaskRuntimeSource DisplayString (SIZE (1..16)),
         deploymentTaskRuntimeState DisplayString (SIZE (1..32)),
         deploymentTaskRuntimeInUse INTEGER,
         deploymentTaskRuntimeNewSource DisplayString (SIZE (1..256))
      }
      
   
   deploymentTaskRuntimeIndex OBJECT-TYPE
      SYNTAX      DisplayString (SIZE (1..16))
      MAX-ACCESS  read-only
      STATUS      current
      DESCRIPTION "Unique value directed from ObjectName which is used as table index"
      ::= { deploymentTaskRuntimeEntry 1  }
   
   
   deploymentTaskRuntimeObjectName OBJECT-TYPE
      SYNTAX      DisplayString (SIZE (1..256))
      MAX-ACCESS  read-only
      STATUS      current
      DESCRIPTION "JMX-standard MBean name"
      ::= { deploymentTaskRuntimeEntry 5  }
   
   
   deploymentTaskRuntimeType OBJECT-TYPE
      SYNTAX      DisplayString (SIZE (1..64))
      MAX-ACCESS  read-only
      STATUS      current
      DESCRIPTION "BEA-proprietary MBean type"
      ::= { deploymentTaskRuntimeEntry 10  }
   
   
   deploymentTaskRuntimeName OBJECT-TYPE
      SYNTAX      DisplayString (SIZE (1..64))
      MAX-ACCESS  read-only
      STATUS      current
      DESCRIPTION "BEA-proprietary MBean name"
      ::= { deploymentTaskRuntimeEntry 15  }
   
   
   deploymentTaskRuntimeParent OBJECT-TYPE
      SYNTAX      DisplayString (SIZE (1..256))
      MAX-ACCESS  read-only
      STATUS      current
      DESCRIPTION "BEA-proprietary Parent object's identification, with syntax
      <type>:<name>"
      ::= { deploymentTaskRuntimeEntry 20  }
   
   
   deploymentTaskRuntimeApplicationName OBJECT-TYPE
      SYNTAX      DisplayString (SIZE (1..256))
      MAX-ACCESS  read-only
      STATUS      current
      DESCRIPTION "The value of the name for the application that was specified to DeployerRuntime.activate"
      ::= { deploymentTaskRuntimeEntry 25  }
   
   
   deploymentTaskRuntimeId OBJECT-TYPE
      SYNTAX      DisplayString (SIZE (1..256))
      MAX-ACCESS  read-only
      STATUS      current
      DESCRIPTION "A task can be referenced by the id assigned to it, or one the user assigns to it."
      ::= { deploymentTaskRuntimeEntry 30  }
   
   
   deploymentTaskRuntimeSource OBJECT-TYPE
      SYNTAX      DisplayString (SIZE (1..16))
      MAX-ACCESS  read-only
      STATUS      current
      DESCRIPTION "The value of the source file that was specified to DeployerRuntime.activate."
      ::= { deploymentTaskRuntimeEntry 35  }
   
   
   deploymentTaskRuntimeState OBJECT-TYPE
      SYNTAX      DisplayString (SIZE (1..32))
      MAX-ACCESS  read-only
      STATUS      current
      DESCRIPTION "Overall state of this task"
      ::= { deploymentTaskRuntimeEntry 40  }
   
   
   deploymentTaskRuntimeInUse OBJECT-TYPE
      SYNTAX      INTEGER
      MAX-ACCESS  read-only
      STATUS      current
      DESCRIPTION "This indicates if the MBean is free for deletion or timeout."
      ::= { deploymentTaskRuntimeEntry 45  }
   
   
   deploymentTaskRuntimeNewSource OBJECT-TYPE
      SYNTAX      DisplayString (SIZE (1..256))
      MAX-ACCESS  read-only
      STATUS      current
      DESCRIPTION "Indicates whether a new source for the application was specified in an activate request."
      ::= { deploymentTaskRuntimeEntry 46  }
   
   
   domainRuntimeTable OBJECT-TYPE
      SYNTAX      SEQUENCE OF DomainRuntimeEntry
      MAX-ACCESS  not-accessible
      STATUS      current
      DESCRIPTION "This table is used for monitoring a WebLogic deployment."
      ::= { wls 130  }
      
   
   domainRuntimeEntry OBJECT-TYPE
      SYNTAX      DomainRuntimeEntry
      MAX-ACCESS  not-accessible
      STATUS      current
      DESCRIPTION "Entry of domainRuntimeTable"
      INDEX { domainRuntimeIndex}
      ::= { domainRuntimeTable 1 }
      
   DomainRuntimeEntry ::=
      SEQUENCE
      {
         domainRuntimeIndex   DisplayString (SIZE (1..16)),
         domainRuntimeObjectName DisplayString (SIZE (1..256)),
         domainRuntimeType    DisplayString (SIZE (1..64)),
         domainRuntimeName    DisplayString (SIZE (1..64)),
         domainRuntimeParent  DisplayString (SIZE (1..256)),
         domainRuntimeActivationTime DisplayString (SIZE (1..32))
      }
      
   
   domainRuntimeIndex OBJECT-TYPE
      SYNTAX      DisplayString (SIZE (1..16))
      MAX-ACCESS  read-only
      STATUS      current
      DESCRIPTION "Unique value directed from ObjectName which is used as table index"
      ::= { domainRuntimeEntry 1  }
   
   
   domainRuntimeObjectName OBJECT-TYPE
      SYNTAX      DisplayString (SIZE (1..256))
      MAX-ACCESS  read-only
      STATUS      current
      DESCRIPTION "JMX-standard MBean name"
      ::= { domainRuntimeEntry 5  }
   
   
   domainRuntimeType OBJECT-TYPE
      SYNTAX      DisplayString (SIZE (1..64))
      MAX-ACCESS  read-only
      STATUS      current
      DESCRIPTION "BEA-proprietary MBean type"
      ::= { domainRuntimeEntry 10  }
   
   
   domainRuntimeName OBJECT-TYPE
      SYNTAX      DisplayString (SIZE (1..64))
      MAX-ACCESS  read-only
      STATUS      current
      DESCRIPTION "BEA-proprietary MBean name"
      ::= { domainRuntimeEntry 15  }
   
   
   domainRuntimeParent OBJECT-TYPE
      SYNTAX      DisplayString (SIZE (1..256))
      MAX-ACCESS  read-only
      STATUS      current
      DESCRIPTION "BEA-proprietary Parent object's identification, with syntax
      <type>:<name>"
      ::= { domainRuntimeEntry 20  }
   
   
   domainRuntimeActivationTime OBJECT-TYPE
      SYNTAX      DisplayString (SIZE (1..32))
      MAX-ACCESS  read-only
      STATUS      current
      DESCRIPTION "The time when the domain became active."
      ::= { domainRuntimeEntry 25  }
   
   
   queryCacheRuntimeTable OBJECT-TYPE
      SYNTAX      SEQUENCE OF QueryCacheRuntimeEntry
      MAX-ACCESS  not-accessible
      STATUS      current
      DESCRIPTION "This table represents a QueryCacheRuntime for all query cache runtime information collected for an EJB."
      ::= { wls 135  }
      
   
   queryCacheRuntimeEntry OBJECT-TYPE
      SYNTAX      QueryCacheRuntimeEntry
      MAX-ACCESS  not-accessible
      STATUS      current
      DESCRIPTION "Entry of queryCacheRuntimeTable"
      INDEX { queryCacheRuntimeIndex}
      ::= { queryCacheRuntimeTable 1 }
      
   QueryCacheRuntimeEntry ::=
      SEQUENCE
      {
         queryCacheRuntimeIndex DisplayString (SIZE (1..16)),
         queryCacheRuntimeObjectName DisplayString (SIZE (1..256)),
         queryCacheRuntimeType DisplayString (SIZE (1..64)),
         queryCacheRuntimeName DisplayString (SIZE (1..64)),
         queryCacheRuntimeParent DisplayString (SIZE (1..256)),
         queryCacheRuntimeTotalCachedQueriesCount INTEGER,
         queryCacheRuntimeCacheAccessCount Counter64,
         queryCacheRuntimeCacheHitCount Counter64,
         queryCacheRuntimeTotalCacheMissCount Counter64,
         queryCacheRuntimeCacheMissByTimeoutCount Counter64,
         queryCacheRuntimeCacheMissByBeanEvictionCount Counter64,
         queryCacheRuntimeCacheMissByRelatedQueryMissCount Counter64,
         queryCacheRuntimeCacheMissByDependentQueryMissCount Counter64
      }
      
   
   queryCacheRuntimeIndex OBJECT-TYPE
      SYNTAX      DisplayString (SIZE (1..16))
      MAX-ACCESS  read-only
      STATUS      current
      DESCRIPTION "Unique value directed from ObjectName which is used as table index"
      ::= { queryCacheRuntimeEntry 1  }
   
   
   queryCacheRuntimeObjectName OBJECT-TYPE
      SYNTAX      DisplayString (SIZE (1..256))
      MAX-ACCESS  read-only
      STATUS      current
      DESCRIPTION "JMX-standard MBean name"
      ::= { queryCacheRuntimeEntry 5  }
   
   
   queryCacheRuntimeType OBJECT-TYPE
      SYNTAX      DisplayString (SIZE (1..64))
      MAX-ACCESS  read-only
      STATUS      current
      DESCRIPTION "BEA-proprietary MBean type"
      ::= { queryCacheRuntimeEntry 10  }
   
   
   queryCacheRuntimeName OBJECT-TYPE
      SYNTAX      DisplayString (SIZE (1..64))
      MAX-ACCESS  read-only
      STATUS      current
      DESCRIPTION "BEA-proprietary MBean name"
      ::= { queryCacheRuntimeEntry 15  }
   
   
   queryCacheRuntimeParent OBJECT-TYPE
      SYNTAX      DisplayString (SIZE (1..256))
      MAX-ACCESS  read-only
      STATUS      current
      DESCRIPTION "BEA-proprietary Parent object's identification, with syntax
      <type>:<name>"
      ::= { queryCacheRuntimeEntry 20  }
   
   
   queryCacheRuntimeTotalCachedQueriesCount OBJECT-TYPE
      SYNTAX      INTEGER
      MAX-ACCESS  read-only
      STATUS      current
      DESCRIPTION "Returns the count of the total number of query results for this EJB currently in the query cache."
      ::= { queryCacheRuntimeEntry 25  }
   
   
   queryCacheRuntimeCacheAccessCount OBJECT-TYPE
      SYNTAX      Counter64
      MAX-ACCESS  read-only
      STATUS      current
      DESCRIPTION "Returns the count of the number of accesses of the query cache for this EJB."
      ::= { queryCacheRuntimeEntry 30  }
   
   
   queryCacheRuntimeCacheHitCount OBJECT-TYPE
      SYNTAX      Counter64
      MAX-ACCESS  read-only
      STATUS      current
      DESCRIPTION "Returns the count of the number of cache hits of the query cache for this EJB."
      ::= { queryCacheRuntimeEntry 35  }
   
   
   queryCacheRuntimeTotalCacheMissCount OBJECT-TYPE
      SYNTAX      Counter64
      MAX-ACCESS  read-only
      STATUS      current
      DESCRIPTION "Returns the count of the total number of cache misses of the query cache for this EJB."
      ::= { queryCacheRuntimeEntry 40  }
   
   
   queryCacheRuntimeCacheMissByTimeoutCount OBJECT-TYPE
      SYNTAX      Counter64
      MAX-ACCESS  read-only
      STATUS      current
      DESCRIPTION "Returns the count of the number of cache misses of the query cache for this EJB due to query results timing out."
      ::= { queryCacheRuntimeEntry 45  }
   
   
   queryCacheRuntimeCacheMissByBeanEvictionCount OBJECT-TYPE
      SYNTAX      Counter64
      MAX-ACCESS  read-only
      STATUS      current
      DESCRIPTION "Returns the count of the number of cache misses of the query cache for this EJB because corresponding beans were
      not found in the entity cache."
      ::= { queryCacheRuntimeEntry 50  }
   
   
   queryCacheRuntimeCacheMissByRelatedQueryMissCount OBJECT-TYPE
      SYNTAX      Counter64
      MAX-ACCESS  read-only
      STATUS      current
      DESCRIPTION "Returns the count of the number of cache misses of the query cache for this EJB because a related query was not
      found in another EJB query cache."
      ::= { queryCacheRuntimeEntry 55  }
   
   
   queryCacheRuntimeCacheMissByDependentQueryMissCount OBJECT-TYPE
      SYNTAX      Counter64
      MAX-ACCESS  read-only
      STATUS      current
      DESCRIPTION "Returns the count of the number of cache misses of the query cache for this EJB because a dependent query was not
      found in another EJB query cache."
      ::= { queryCacheRuntimeEntry 60  }
   
   
   ejbCacheRuntimeTable OBJECT-TYPE
      SYNTAX      SEQUENCE OF EjbCacheRuntimeEntry
      MAX-ACCESS  not-accessible
      STATUS      current
      DESCRIPTION "This table represents an EJBCacheRuntime."
      ::= { wls 137  }
      
   
   ejbCacheRuntimeEntry OBJECT-TYPE
      SYNTAX      EjbCacheRuntimeEntry
      MAX-ACCESS  not-accessible
      STATUS      current
      DESCRIPTION "Entry of ejbCacheRuntimeTable"
      INDEX { ejbCacheRuntimeIndex}
      ::= { ejbCacheRuntimeTable 1 }
      
   EjbCacheRuntimeEntry ::=
      SEQUENCE
      {
         ejbCacheRuntimeIndex DisplayString (SIZE (1..16)),
         ejbCacheRuntimeObjectName DisplayString (SIZE (1..256)),
         ejbCacheRuntimeType  DisplayString (SIZE (1..64)),
         ejbCacheRuntimeName  DisplayString (SIZE (1..64)),
         ejbCacheRuntimeParent DisplayString (SIZE (1..256)),
         ejbCacheRuntimeActivationCount DisplayString (SIZE (1..16)),
         ejbCacheRuntimeCacheAccessCount Counter64,
         ejbCacheRuntimeCachedBeansCurrentCount Counter64,
         ejbCacheRuntimeCacheHitCount Counter64,
         ejbCacheRuntimePassivationCount Counter64,
         ejbCacheRuntimeCacheMissCount Counter64
      }
      
   
   ejbCacheRuntimeIndex OBJECT-TYPE
      SYNTAX      DisplayString (SIZE (1..16))
      MAX-ACCESS  read-only
      STATUS      current
      DESCRIPTION "Unique value directed from ObjectName which is used as table index"
      ::= { ejbCacheRuntimeEntry 1  }
   
   
   ejbCacheRuntimeObjectName OBJECT-TYPE
      SYNTAX      DisplayString (SIZE (1..256))
      MAX-ACCESS  read-only
      STATUS      current
      DESCRIPTION "JMX-standard MBean name"
      ::= { ejbCacheRuntimeEntry 5  }
   
   
   ejbCacheRuntimeType OBJECT-TYPE
      SYNTAX      DisplayString (SIZE (1..64))
      MAX-ACCESS  read-only
      STATUS      current
      DESCRIPTION "BEA-proprietary MBean type"
      ::= { ejbCacheRuntimeEntry 10  }
   
   
   ejbCacheRuntimeName OBJECT-TYPE
      SYNTAX      DisplayString (SIZE (1..64))
      MAX-ACCESS  read-only
      STATUS      current
      DESCRIPTION "BEA-proprietary MBean name"
      ::= { ejbCacheRuntimeEntry 15  }
   
   
   ejbCacheRuntimeParent OBJECT-TYPE
      SYNTAX      DisplayString (SIZE (1..256))
      MAX-ACCESS  read-only
      STATUS      current
      DESCRIPTION "BEA-proprietary Parent object's identification, with syntax
      <type>:<name>"
      ::= { ejbCacheRuntimeEntry 20  }
   
   
   ejbCacheRuntimeActivationCount OBJECT-TYPE
      SYNTAX      DisplayString (SIZE (1..16))
      MAX-ACCESS  read-only
      STATUS      current
      DESCRIPTION "Returns the number of entity beans activated"
      ::= { ejbCacheRuntimeEntry 25  }
   
   
   ejbCacheRuntimeCacheAccessCount OBJECT-TYPE
      SYNTAX      Counter64
      MAX-ACCESS  read-only
      STATUS      current
      DESCRIPTION "Returns the cache access count"
      ::= { ejbCacheRuntimeEntry 30  }
   
   
   ejbCacheRuntimeCachedBeansCurrentCount OBJECT-TYPE
      SYNTAX      Counter64
      MAX-ACCESS  read-only
      STATUS      current
      DESCRIPTION "Returns the cached beans current count"
      ::= { ejbCacheRuntimeEntry 35  }
   
   
   ejbCacheRuntimeCacheHitCount OBJECT-TYPE
      SYNTAX      Counter64
      MAX-ACCESS  read-only
      STATUS      current
      DESCRIPTION "Returns the cached hit count"
      ::= { ejbCacheRuntimeEntry 40  }
   
   
   ejbCacheRuntimePassivationCount OBJECT-TYPE
      SYNTAX      Counter64
      MAX-ACCESS  read-only
      STATUS      current
      DESCRIPTION "Returns the number of entity beans passivated"
      ::= { ejbCacheRuntimeEntry 45  }
   
   
   ejbCacheRuntimeCacheMissCount OBJECT-TYPE
      SYNTAX      Counter64
      MAX-ACCESS  read-only
      STATUS      current
      DESCRIPTION "Returns the total number of times an attempt to access a bean from the cache failed."
      ::= { ejbCacheRuntimeEntry 46  }
   
   
   ejbRuntimeTable OBJECT-TYPE
      SYNTAX      SEQUENCE OF EjbRuntimeEntry
      MAX-ACCESS  not-accessible
      STATUS      current
      DESCRIPTION "This interface contains accessor methods for all common runtime information collected for all EJB types."
      ::= { wls 138  }
      
   
   ejbRuntimeEntry OBJECT-TYPE
      SYNTAX      EjbRuntimeEntry
      MAX-ACCESS  not-accessible
      STATUS      current
      DESCRIPTION "Entry of ejbRuntimeTable"
      INDEX { ejbRuntimeIndex}
      ::= { ejbRuntimeTable 1 }
      
   EjbRuntimeEntry ::=
      SEQUENCE
      {
         ejbRuntimeIndex      DisplayString (SIZE (1..16)),
         ejbRuntimeObjectName DisplayString (SIZE (1..256)),
         ejbRuntimeType       DisplayString (SIZE (1..64)),
         ejbRuntimeName       DisplayString (SIZE (1..64)),
         ejbRuntimeParent     DisplayString (SIZE (1..256)),
         ejbRuntimeEJBName    DisplayString (SIZE (1..16))
      }
      
   
   ejbRuntimeIndex OBJECT-TYPE
      SYNTAX      DisplayString (SIZE (1..16))
      MAX-ACCESS  read-only
      STATUS      current
      DESCRIPTION "Unique value directed from ObjectName which is used as table index"
      ::= { ejbRuntimeEntry 1  }
   
   
   ejbRuntimeObjectName OBJECT-TYPE
      SYNTAX      DisplayString (SIZE (1..256))
      MAX-ACCESS  read-only
      STATUS      current
      DESCRIPTION "JMX-standard MBean name"
      ::= { ejbRuntimeEntry 5  }
   
   
   ejbRuntimeType OBJECT-TYPE
      SYNTAX      DisplayString (SIZE (1..64))
      MAX-ACCESS  read-only
      STATUS      current
      DESCRIPTION "BEA-proprietary MBean type"
      ::= { ejbRuntimeEntry 10  }
   
   
   ejbRuntimeName OBJECT-TYPE
      SYNTAX      DisplayString (SIZE (1..64))
      MAX-ACCESS  read-only
      STATUS      current
      DESCRIPTION "BEA-proprietary MBean name"
      ::= { ejbRuntimeEntry 15  }
   
   
   ejbRuntimeParent OBJECT-TYPE
      SYNTAX      DisplayString (SIZE (1..256))
      MAX-ACCESS  read-only
      STATUS      current
      DESCRIPTION "BEA-proprietary Parent object's identification, with syntax
      <type>:<name>"
      ::= { ejbRuntimeEntry 20  }
   
   
   ejbRuntimeEJBName OBJECT-TYPE
      SYNTAX      DisplayString (SIZE (1..16))
      MAX-ACCESS  read-only
      STATUS      current
      DESCRIPTION "The EJBName value"
      ::= { ejbRuntimeEntry 25  }
   
   
   ejbComponentRuntimeTable OBJECT-TYPE
      SYNTAX      SEQUENCE OF EjbComponentRuntimeEntry
      MAX-ACCESS  not-accessible
      STATUS      current
      DESCRIPTION "This table represents an EJBDeployment."
      ::= { wls 140  }
      
   
   ejbComponentRuntimeEntry OBJECT-TYPE
      SYNTAX      EjbComponentRuntimeEntry
      MAX-ACCESS  not-accessible
      STATUS      current
      DESCRIPTION "Entry of ejbComponentRuntimeTable"
      INDEX { ejbComponentRuntimeIndex}
      ::= { ejbComponentRuntimeTable 1 }
      
   EjbComponentRuntimeEntry ::=
      SEQUENCE
      {
         ejbComponentRuntimeIndex DisplayString (SIZE (1..16)),
         ejbComponentRuntimeObjectName DisplayString (SIZE (1..256)),
         ejbComponentRuntimeType DisplayString (SIZE (1..64)),
         ejbComponentRuntimeName DisplayString (SIZE (1..64)),
         ejbComponentRuntimeParent DisplayString (SIZE (1..256)),
         ejbComponentRuntimeModuleId OCTET STRING,
         ejbComponentRuntimeDeploymentState INTEGER
      }
      
   
   ejbComponentRuntimeIndex OBJECT-TYPE
      SYNTAX      DisplayString (SIZE (1..16))
      MAX-ACCESS  read-only
      STATUS      current
      DESCRIPTION "Unique value directed from ObjectName which is used as table index"
      ::= { ejbComponentRuntimeEntry 1  }
   
   
   ejbComponentRuntimeObjectName OBJECT-TYPE
      SYNTAX      DisplayString (SIZE (1..256))
      MAX-ACCESS  read-only
      STATUS      current
      DESCRIPTION "JMX-standard MBean name"
      ::= { ejbComponentRuntimeEntry 5  }
   
   
   ejbComponentRuntimeType OBJECT-TYPE
      SYNTAX      DisplayString (SIZE (1..64))
      MAX-ACCESS  read-only
      STATUS      current
      DESCRIPTION "BEA-proprietary MBean type"
      ::= { ejbComponentRuntimeEntry 10  }
   
   
   ejbComponentRuntimeName OBJECT-TYPE
      SYNTAX      DisplayString (SIZE (1..64))
      MAX-ACCESS  read-only
      STATUS      current
      DESCRIPTION "BEA-proprietary MBean name"
      ::= { ejbComponentRuntimeEntry 15  }
   
   
   ejbComponentRuntimeParent OBJECT-TYPE
      SYNTAX      DisplayString (SIZE (1..256))
      MAX-ACCESS  read-only
      STATUS      current
      DESCRIPTION "BEA-proprietary Parent object's identification, with syntax
      <type>:<name>"
      ::= { ejbComponentRuntimeEntry 20  }
   
   
   ejbComponentRuntimeModuleId OBJECT-TYPE
      SYNTAX      OCTET STRING
      MAX-ACCESS  read-only
      STATUS      current
      DESCRIPTION "Returns the identifier for this Component.  The identifier is unique within the application.  Typical modules will use the URI for their id.  Web Modules will return their context-root since the web-uri may not be unique within an EAR."
      ::= { ejbComponentRuntimeEntry 21  }
   
   
   ejbComponentRuntimeDeploymentState OBJECT-TYPE
      SYNTAX      INTEGER
      MAX-ACCESS  read-only
      STATUS      current
      DESCRIPTION "The current deployment state of the module."
      ::= { ejbComponentRuntimeEntry 22  }
   
   
   ejbLockingRuntimeTable OBJECT-TYPE
      SYNTAX      SEQUENCE OF EjbLockingRuntimeEntry
      MAX-ACCESS  not-accessible
      STATUS      current
      DESCRIPTION "This table represents an ejbTimerRuntime."
      ::= { wls 151  }
      
   
   ejbLockingRuntimeEntry OBJECT-TYPE
      SYNTAX      EjbLockingRuntimeEntry
      MAX-ACCESS  not-accessible
      STATUS      current
      DESCRIPTION "Entry of ejbTimerRuntimeTable"
      INDEX { ejbLockingRuntimeIndex}
      ::= { ejbLockingRuntimeTable 1 }
      
   EjbLockingRuntimeEntry ::=
      SEQUENCE
      {
         ejbLockingRuntimeIndex DisplayString (SIZE (1..16)),
         ejbLockingRuntimeObjectName DisplayString (SIZE (1..256)),
         ejbLockingRuntimeType DisplayString (SIZE (1..64)),
         ejbLockingRuntimeName DisplayString (SIZE (1..64)),
         ejbLockingRuntimeParent DisplayString (SIZE (1..256)),
         ejbLockingRuntimeLockEntriesCurrentCount DisplayString (SIZE (1..16)),
         ejbLockingRuntimeLockManagerAccessCount Counter64,
         ejbLockingRuntimeWaiterTotalCount Counter64,
         ejbLockingRuntimeWaiterCurrentCount INTEGER,
         ejbLockingRuntimeTimeoutTotalCount Counter64
      }
      
   
   ejbLockingRuntimeIndex OBJECT-TYPE
      SYNTAX      DisplayString (SIZE (1..16))
      MAX-ACCESS  read-only
      STATUS      current
      DESCRIPTION "Unique value directed from ObjectName which is used as table index"
      ::= { ejbLockingRuntimeEntry 1  }
   
   
   ejbLockingRuntimeObjectName OBJECT-TYPE
      SYNTAX      DisplayString (SIZE (1..256))
      MAX-ACCESS  read-only
      STATUS      current
      DESCRIPTION "JMX-standard MBean name"
      ::= { ejbLockingRuntimeEntry 5  }
   
   
   ejbLockingRuntimeType OBJECT-TYPE
      SYNTAX      DisplayString (SIZE (1..64))
      MAX-ACCESS  read-only
      STATUS      current
      DESCRIPTION "BEA-proprietary MBean type"
      ::= { ejbLockingRuntimeEntry 10  }
   
   
   ejbLockingRuntimeName OBJECT-TYPE
      SYNTAX      DisplayString (SIZE (1..64))
      MAX-ACCESS  read-only
      STATUS      current
      DESCRIPTION "BEA-proprietary MBean name"
      ::= { ejbLockingRuntimeEntry 15  }
   
   
   ejbLockingRuntimeParent OBJECT-TYPE
      SYNTAX      DisplayString (SIZE (1..256))
      MAX-ACCESS  read-only
      STATUS      current
      DESCRIPTION "BEA-proprietary Parent object's identification, with syntax
      <type>:<name>"
      ::= { ejbLockingRuntimeEntry 20  }
   
   
   ejbLockingRuntimeLockEntriesCurrentCount OBJECT-TYPE
      SYNTAX      DisplayString (SIZE (1..16))
      MAX-ACCESS  read-only
      STATUS      current
      DESCRIPTION "Provides a count of the number of beans currently locked."
      ::= { ejbLockingRuntimeEntry 25  }
   
   
   ejbLockingRuntimeLockManagerAccessCount OBJECT-TYPE
      SYNTAX      Counter64
      MAX-ACCESS  read-only
      STATUS      current
      DESCRIPTION "Provides the total number of attempts to obtain a lock on a bean."
      ::= { ejbLockingRuntimeEntry 30  }
   
   
   ejbLockingRuntimeWaiterTotalCount OBJECT-TYPE
      SYNTAX      Counter64
      MAX-ACCESS  read-only
      STATUS      current
      DESCRIPTION "Provides the total number of Threads that have waited for a lock on a bean."
      ::= { ejbLockingRuntimeEntry 35  }
   
   
   ejbLockingRuntimeWaiterCurrentCount OBJECT-TYPE
      SYNTAX      INTEGER
      MAX-ACCESS  read-only
      STATUS      current
      DESCRIPTION "Provides the current number of Threads that have waited for a lock on a bean."
      ::= { ejbLockingRuntimeEntry 40  }
   
   
   ejbLockingRuntimeTimeoutTotalCount OBJECT-TYPE
      SYNTAX      Counter64
      MAX-ACCESS  read-only
      STATUS      current
      DESCRIPTION "Provides the current number of Threads that have timed out waiting for a lock on a bean."
      ::= { ejbLockingRuntimeEntry 45  }
   
   
   ejbPoolRuntimeTable OBJECT-TYPE
      SYNTAX      SEQUENCE OF EjbPoolRuntimeEntry
      MAX-ACCESS  not-accessible
      STATUS      current
      DESCRIPTION "Runtime representation of a EJBPool Bean."
      ::= { wls 161  }
      
   
   ejbPoolRuntimeEntry OBJECT-TYPE
      SYNTAX      EjbPoolRuntimeEntry
      MAX-ACCESS  not-accessible
      STATUS      current
      DESCRIPTION "Entry of ejbPoolRuntimeTable"
      INDEX { ejbPoolRuntimeIndex}
      ::= { ejbPoolRuntimeTable 1 }
      
   EjbPoolRuntimeEntry ::=
      SEQUENCE
      {
         ejbPoolRuntimeIndex  DisplayString (SIZE (1..16)),
         ejbPoolRuntimeObjectName DisplayString (SIZE (1..256)),
         ejbPoolRuntimeType   DisplayString (SIZE (1..64)),
         ejbPoolRuntimeName   DisplayString (SIZE (1..64)),
         ejbPoolRuntimeParent DisplayString (SIZE (1..256)),
         ejbPoolRuntimeBeansInUseCount INTEGER,
         ejbPoolRuntimeIdleBeansCount INTEGER,
         ejbPoolRuntimeTimeoutTotalCount Counter64,
         ejbPoolRuntimeWaiterTotalCount Counter64,
         ejbPoolRuntimeAccessTotalCount Counter64,
         ejbPoolRuntimeBeansInUseCurrentCount INTEGER,
         ejbPoolRuntimeDestroyedTotalCount Counter64,
         ejbPoolRuntimeMissTotalCount Counter64,
         ejbPoolRuntimeWaiterCurrentCount INTEGER,
         ejbPoolRuntimePooledBeansCurrentCount INTEGER
      }
      
   
   ejbPoolRuntimeIndex OBJECT-TYPE
      SYNTAX      DisplayString (SIZE (1..16))
      MAX-ACCESS  read-only
      STATUS      current
      DESCRIPTION "Unique value directed from ObjectName which is used as table index"
      ::= { ejbPoolRuntimeEntry 1  }
   
   
   ejbPoolRuntimeObjectName OBJECT-TYPE
      SYNTAX      DisplayString (SIZE (1..256))
      MAX-ACCESS  read-only
      STATUS      current
      DESCRIPTION "JMX-standard MBean name"
      ::= { ejbPoolRuntimeEntry 5  }
   
   
   ejbPoolRuntimeType OBJECT-TYPE
      SYNTAX      DisplayString (SIZE (1..64))
      MAX-ACCESS  read-only
      STATUS      current
      DESCRIPTION "BEA-proprietary MBean type"
      ::= { ejbPoolRuntimeEntry 10  }
   
   
   ejbPoolRuntimeName OBJECT-TYPE
      SYNTAX      DisplayString (SIZE (1..64))
      MAX-ACCESS  read-only
      STATUS      current
      DESCRIPTION "BEA-proprietary MBean name"
      ::= { ejbPoolRuntimeEntry 15  }
   
   
   ejbPoolRuntimeParent OBJECT-TYPE
      SYNTAX      DisplayString (SIZE (1..256))
      MAX-ACCESS  read-only
      STATUS      current
      DESCRIPTION "BEA-proprietary Parent object's identification, with syntax
      <type>:<name>"
      ::= { ejbPoolRuntimeEntry 20  }
   
   
   ejbPoolRuntimeBeansInUseCount OBJECT-TYPE
      SYNTAX      INTEGER
      MAX-ACCESS  read-only
      STATUS      current
      DESCRIPTION ""
      ::= { ejbPoolRuntimeEntry 25  }
   
   
   ejbPoolRuntimeIdleBeansCount OBJECT-TYPE
      SYNTAX      INTEGER
      MAX-ACCESS  read-only
      STATUS      current
      DESCRIPTION "A boolean value (true Or false)"
      ::= { ejbPoolRuntimeEntry 30  }
   
   
   ejbPoolRuntimeTimeoutTotalCount OBJECT-TYPE
      SYNTAX      Counter64
      MAX-ACCESS  read-only
      STATUS      current
      DESCRIPTION "Timeout total"
      ::= { ejbPoolRuntimeEntry 35  }
   
   
   ejbPoolRuntimeWaiterTotalCount OBJECT-TYPE
      SYNTAX      Counter64
      MAX-ACCESS  read-only
      STATUS      current
      DESCRIPTION "Waiter total count"
      ::= { ejbPoolRuntimeEntry 40  }
   
   
   ejbPoolRuntimeAccessTotalCount OBJECT-TYPE
      SYNTAX      Counter64
      MAX-ACCESS  read-only
      STATUS      current
      DESCRIPTION "Returns the total number of times an attempt was made to get an instance from the free pool."
      ::= { ejbPoolRuntimeEntry 41  }
   
   
   ejbPoolRuntimeBeansInUseCurrentCount OBJECT-TYPE
      SYNTAX      INTEGER
      MAX-ACCESS  read-only
      STATUS      current
      DESCRIPTION "Returns the number of bean instances currently being used from the free pool."
      ::= { ejbPoolRuntimeEntry 42  }
   
   
   ejbPoolRuntimeDestroyedTotalCount OBJECT-TYPE
      SYNTAX      Counter64
      MAX-ACCESS  read-only
      STATUS      current
      DESCRIPTION "Returns the total number of times a bean instance from this pool was destroyed due to a non-application Exception being thrown from it."
      ::= { ejbPoolRuntimeEntry 43  }
   
   
   ejbPoolRuntimeMissTotalCount OBJECT-TYPE
      SYNTAX      Counter64
      MAX-ACCESS  read-only
      STATUS      current
      DESCRIPTION "Returns the total number of times a failed attempt was made to get an instance from the free pool.  An Attempt to get a bean from the pool will fail if there are no available instances in the pool."
      ::= { ejbPoolRuntimeEntry 44  }
   
   
   ejbPoolRuntimeWaiterCurrentCount OBJECT-TYPE
      SYNTAX      INTEGER
      MAX-ACCESS  read-only
      STATUS      current
      DESCRIPTION "Returns the number of Threads currently waiting for an available bean instance from the free pool."
      ::= { ejbPoolRuntimeEntry 45  }
   
   
   ejbPoolRuntimePooledBeansCurrentCount OBJECT-TYPE
      SYNTAX      INTEGER
      MAX-ACCESS  read-only
      STATUS      current
      DESCRIPTION "Provides a count of the current number of available bean instances in the free pool."
      ::= { ejbPoolRuntimeEntry 46  }
   
   
   ejbTimerRuntimeTable OBJECT-TYPE
      SYNTAX      SEQUENCE OF EjbTimerRuntimeEntry
      MAX-ACCESS  not-accessible
      STATUS      current
      DESCRIPTION "Runtime representation of a EJBTimer Bean."
      ::= { wls 162  }
      
   
   ejbTimerRuntimeEntry OBJECT-TYPE
      SYNTAX      EjbTimerRuntimeEntry
      MAX-ACCESS  not-accessible
      STATUS      current
      DESCRIPTION "Entry of ejbTimerRuntimeTable"
      INDEX { ejbTimerRuntimeIndex}
      ::= { ejbTimerRuntimeTable 1 }
      
   EjbTimerRuntimeEntry ::=
      SEQUENCE
      {
         ejbTimerRuntimeIndex DisplayString (SIZE (1..16)),
         ejbTimerRuntimeObjectName DisplayString (SIZE (1..256)),
         ejbTimerRuntimeType  DisplayString (SIZE (1..64)),
         ejbTimerRuntimeName  DisplayString (SIZE (1..64)),
         ejbTimerRuntimeParent DisplayString (SIZE (1..256)),
         ejbTimerRuntimeDisabledTimerCount INTEGER,
         ejbTimerRuntimeCancelledTimerCount Counter64,
         ejbTimerRuntimeTimeoutCount Counter64,
         ejbTimerRuntimeActiveTimerCount INTEGER
      }
      
   
   ejbTimerRuntimeIndex OBJECT-TYPE
      SYNTAX      DisplayString (SIZE (1..16))
      MAX-ACCESS  read-only
      STATUS      current
      DESCRIPTION "Unique value directed from ObjectName which is used as table index"
      ::= { ejbTimerRuntimeEntry 1  }
   
   
   ejbTimerRuntimeObjectName OBJECT-TYPE
      SYNTAX      DisplayString (SIZE (1..256))
      MAX-ACCESS  read-only
      STATUS      current
      DESCRIPTION "JMX-standard MBean name"
      ::= { ejbTimerRuntimeEntry 5  }
   
   
   ejbTimerRuntimeType OBJECT-TYPE
      SYNTAX      DisplayString (SIZE (1..64))
      MAX-ACCESS  read-only
      STATUS      current
      DESCRIPTION "BEA-proprietary MBean type"
      ::= { ejbTimerRuntimeEntry 10  }
   
   
   ejbTimerRuntimeName OBJECT-TYPE
      SYNTAX      DisplayString (SIZE (1..64))
      MAX-ACCESS  read-only
      STATUS      current
      DESCRIPTION "BEA-proprietary MBean name"
      ::= { ejbTimerRuntimeEntry 15  }
   
   
   ejbTimerRuntimeParent OBJECT-TYPE
      SYNTAX      DisplayString (SIZE (1..256))
      MAX-ACCESS  read-only
      STATUS      current
      DESCRIPTION "BEA-proprietary Parent object's identification, with syntax
      <type>:<name>"
      ::= { ejbTimerRuntimeEntry 20  }
   
   
   ejbTimerRuntimeDisabledTimerCount OBJECT-TYPE
      SYNTAX      INTEGER
      MAX-ACCESS  read-only
      STATUS      current
      DESCRIPTION ""
      ::= { ejbTimerRuntimeEntry 25  }
   
   
   ejbTimerRuntimeCancelledTimerCount OBJECT-TYPE
      SYNTAX      Counter64
      MAX-ACCESS  read-only
      STATUS      current
      DESCRIPTION "A boolean value (true Or false)"
      ::= { ejbTimerRuntimeEntry 30  }
   
   
   ejbTimerRuntimeTimeoutCount OBJECT-TYPE
      SYNTAX      Counter64
      MAX-ACCESS  read-only
      STATUS      current
      DESCRIPTION "Timeout total"
      ::= { ejbTimerRuntimeEntry 35  }
   
   
   ejbTimerRuntimeActiveTimerCount OBJECT-TYPE
      SYNTAX      INTEGER
      MAX-ACCESS  read-only
      STATUS      current
      DESCRIPTION "Waiter total count"
      ::= { ejbTimerRuntimeEntry 40  }
   
   
   ejbTransactionRuntimeTable OBJECT-TYPE
      SYNTAX      SEQUENCE OF EjbTransactionRuntimeEntry
      MAX-ACCESS  not-accessible
      STATUS      current
      DESCRIPTION "This table is used to monitor ejb transaction runtime."
      ::= { wls 171  }
      
   
   ejbTransactionRuntimeEntry OBJECT-TYPE
      SYNTAX      EjbTransactionRuntimeEntry
      MAX-ACCESS  not-accessible
      STATUS      current
      DESCRIPTION "Entry of ejbTransactionRuntimeTable"
      INDEX { ejbTransactionRuntimeIndex}
      ::= { ejbTransactionRuntimeTable 1 }
      
   EjbTransactionRuntimeEntry ::=
      SEQUENCE
      {
         ejbTransactionRuntimeIndex DisplayString (SIZE (1..16)),
         ejbTransactionRuntimeObjectName DisplayString (SIZE (1..256)),
         ejbTransactionRuntimeType DisplayString (SIZE (1..64)),
         ejbTransactionRuntimeName DisplayString (SIZE (1..64)),
         ejbTransactionRuntimeParent DisplayString (SIZE (1..256)),
         ejbTransactionRuntimeTransactionsCommittedTotalCount Counter64,
         ejbTransactionRuntimeTransactionsRolledBackTotalCount Counter64,
         ejbTransactionRuntimeTransactionsTimedOutTotalCount Counter64
      }
      
   
   ejbTransactionRuntimeIndex OBJECT-TYPE
      SYNTAX      DisplayString (SIZE (1..16))
      MAX-ACCESS  read-only
      STATUS      current
      DESCRIPTION "Unique value directed from ObjectName which is used as table index"
      ::= { ejbTransactionRuntimeEntry 1  }
   
   
   ejbTransactionRuntimeObjectName OBJECT-TYPE
      SYNTAX      DisplayString (SIZE (1..256))
      MAX-ACCESS  read-only
      STATUS      current
      DESCRIPTION "JMX-standard MBean name"
      ::= { ejbTransactionRuntimeEntry 5  }
   
   
   ejbTransactionRuntimeType OBJECT-TYPE
      SYNTAX      DisplayString (SIZE (1..64))
      MAX-ACCESS  read-only
      STATUS      current
      DESCRIPTION "BEA-proprietary MBean type"
      ::= { ejbTransactionRuntimeEntry 10  }
   
   
   ejbTransactionRuntimeName OBJECT-TYPE
      SYNTAX      DisplayString (SIZE (1..64))
      MAX-ACCESS  read-only
      STATUS      current
      DESCRIPTION "BEA-proprietary MBean name"
      ::= { ejbTransactionRuntimeEntry 15  }
   
   
   ejbTransactionRuntimeParent OBJECT-TYPE
      SYNTAX      DisplayString (SIZE (1..256))
      MAX-ACCESS  read-only
      STATUS      current
      DESCRIPTION "BEA-proprietary Parent object's identification, with syntax
      <type>:<name>"
      ::= { ejbTransactionRuntimeEntry 20  }
   
   
   ejbTransactionRuntimeTransactionsCommittedTotalCount OBJECT-TYPE
      SYNTAX      Counter64
      MAX-ACCESS  read-only
      STATUS      current
      DESCRIPTION "the total number of transactions committed by beans of this Home."
      ::= { ejbTransactionRuntimeEntry 25  }
   
   
   ejbTransactionRuntimeTransactionsRolledBackTotalCount OBJECT-TYPE
      SYNTAX      Counter64
      MAX-ACCESS  read-only
      STATUS      current
      DESCRIPTION "the total number of transactions rolled back by beans of this Home."
      ::= { ejbTransactionRuntimeEntry 30  }
   
   
   ejbTransactionRuntimeTransactionsTimedOutTotalCount OBJECT-TYPE
      SYNTAX      Counter64
      MAX-ACCESS  read-only
      STATUS      current
      DESCRIPTION "the total number of transactions timed out."
      ::= { ejbTransactionRuntimeEntry 35  }
   
   
   entityCacheCumulativeRuntimeTable OBJECT-TYPE
      SYNTAX      SEQUENCE OF EntityCacheCumulativeRuntimeEntry
      MAX-ACCESS  not-accessible
      STATUS      current
      DESCRIPTION "This table is used to monitor an XML Cache."
      ::= { wls 172  }
      
   
   entityCacheCumulativeRuntimeEntry OBJECT-TYPE
      SYNTAX      EntityCacheCumulativeRuntimeEntry
      MAX-ACCESS  not-accessible
      STATUS      current
      DESCRIPTION "Entry of entityCacheCumulativeRuntimeTable"
      INDEX { entityCacheCumulativeRuntimeIndex}
      ::= { entityCacheCumulativeRuntimeTable 1 }
      
   EntityCacheCumulativeRuntimeEntry ::=
      SEQUENCE
      {
         entityCacheCumulativeRuntimeIndex DisplayString (SIZE (1..16)),
         entityCacheCumulativeRuntimeObjectName DisplayString (SIZE (1..256)),
         entityCacheCumulativeRuntimeType DisplayString (SIZE (1..64)),
         entityCacheCumulativeRuntimeName DisplayString (SIZE (1..64)),
         entityCacheCumulativeRuntimeParent DisplayString (SIZE (1..256)),
         entityCacheCumulativeRuntimeAvgEntrySizeDiskPurged INTEGER,
         entityCacheCumulativeRuntimeAvgEntrySizeMemoryPurged INTEGER,
         entityCacheCumulativeRuntimeDiskPurgesPerHour INTEGER,
         entityCacheCumulativeRuntimeMostRecentDiskPurge INTEGER,
         entityCacheCumulativeRuntimeMostRecentMemoryPurge INTEGER,
         entityCacheCumulativeRuntimePercentRejected INTEGER,
         entityCacheCumulativeRuntimeTotalItemsDiskPurged Counter64,
         entityCacheCumulativeRuntimeTotalItemsMemoryPurged Counter64,
         entityCacheCumulativeRuntimeTotalNumberDiskPurges Counter64,
         entityCacheCumulativeRuntimeTotalNumberMemoryPurges Counter64,
         entityCacheCumulativeRuntimeTotalNumberOfRejections Counter64,
         entityCacheCumulativeRuntimeTotalNumberOfRenewals Counter64,
         entityCacheCumulativeRuntimeTotalSizeOfRejections Counter64,
         entityCacheCumulativeRuntimeTotalCurrentEntries Counter64,
         entityCacheCumulativeRuntimeAvgPerEntryDiskSize OCTET STRING,
         entityCacheCumulativeRuntimeTotalPersistentCurrentEntries Counter64,
         entityCacheCumulativeRuntimeMaxEntryTimeout OCTET STRING,
         entityCacheCumulativeRuntimeMaxEntryMemorySize Counter64,
         entityCacheCumulativeRuntimeTotalTransientCurrentEntries Counter64,
         entityCacheCumulativeRuntimeAvgPerEntryMemorySize OCTET STRING,
         entityCacheCumulativeRuntimeAvgPercentPersistent OCTET STRING,
         entityCacheCumulativeRuntimeMinEntryMemorySize Counter64,
         entityCacheCumulativeRuntimeAvgTimeout OCTET STRING,
         entityCacheCumulativeRuntimeMemoryPurgesPerHour OCTET STRING,
         entityCacheCumulativeRuntimeMinEntryTimeout OCTET STRING,
         entityCacheCumulativeRuntimeAvgPercentTransient OCTET STRING
      }
      
   
   entityCacheCumulativeRuntimeIndex OBJECT-TYPE
      SYNTAX      DisplayString (SIZE (1..16))
      MAX-ACCESS  read-only
      STATUS      current
      DESCRIPTION "Unique value directed from ObjectName which is used as table index"
      ::= { entityCacheCumulativeRuntimeEntry 1  }
   
   
   entityCacheCumulativeRuntimeObjectName OBJECT-TYPE
      SYNTAX      DisplayString (SIZE (1..256))
      MAX-ACCESS  read-only
      STATUS      current
      DESCRIPTION "JMX-standard MBean name"
      ::= { entityCacheCumulativeRuntimeEntry 5  }
   
   
   entityCacheCumulativeRuntimeType OBJECT-TYPE
      SYNTAX      DisplayString (SIZE (1..64))
      MAX-ACCESS  read-only
      STATUS      current
      DESCRIPTION "BEA-proprietary MBean type"
      ::= { entityCacheCumulativeRuntimeEntry 10  }
   
   
   entityCacheCumulativeRuntimeName OBJECT-TYPE
      SYNTAX      DisplayString (SIZE (1..64))
      MAX-ACCESS  read-only
      STATUS      current
      DESCRIPTION "BEA-proprietary MBean name"
      ::= { entityCacheCumulativeRuntimeEntry 15  }
   
   
   entityCacheCumulativeRuntimeParent OBJECT-TYPE
      SYNTAX      DisplayString (SIZE (1..256))
      MAX-ACCESS  read-only
      STATUS      current
      DESCRIPTION "BEA-proprietary Parent object's identification, with syntax
      <type>:<name>"
      ::= { entityCacheCumulativeRuntimeEntry 20  }
   
   
   entityCacheCumulativeRuntimeAvgEntrySizeDiskPurged OBJECT-TYPE
      SYNTAX      INTEGER
      MAX-ACCESS  read-only
      STATUS      current
      DESCRIPTION "Disks purged"
      ::= { entityCacheCumulativeRuntimeEntry 25  }
   
   
   entityCacheCumulativeRuntimeAvgEntrySizeMemoryPurged OBJECT-TYPE
      SYNTAX      INTEGER
      MAX-ACCESS  read-only
      STATUS      current
      DESCRIPTION "the total number of transactions committed by beans of this Home."
      ::= { entityCacheCumulativeRuntimeEntry 26  }
   
   
   entityCacheCumulativeRuntimeDiskPurgesPerHour OBJECT-TYPE
      SYNTAX      INTEGER
      MAX-ACCESS  read-only
      STATUS      current
      DESCRIPTION "the total number of transactions committed by beans of this Home."
      ::= { entityCacheCumulativeRuntimeEntry 27  }
   
   
   entityCacheCumulativeRuntimeMostRecentDiskPurge OBJECT-TYPE
      SYNTAX      INTEGER
      MAX-ACCESS  read-only
      STATUS      current
      DESCRIPTION "the total number of transactions committed by beans of this Home."
      ::= { entityCacheCumulativeRuntimeEntry 28  }
   
   
   entityCacheCumulativeRuntimeMostRecentMemoryPurge OBJECT-TYPE
      SYNTAX      INTEGER
      MAX-ACCESS  read-only
      STATUS      current
      DESCRIPTION "the total number of transactions committed by beans of this Home."
      ::= { entityCacheCumulativeRuntimeEntry 29  }
   
   
   entityCacheCumulativeRuntimePercentRejected OBJECT-TYPE
      SYNTAX      INTEGER
      MAX-ACCESS  read-only
      STATUS      current
      DESCRIPTION "the total number of transactions committed by beans of this Home."
      ::= { entityCacheCumulativeRuntimeEntry 30  }
   
   
   entityCacheCumulativeRuntimeTotalItemsDiskPurged OBJECT-TYPE
      SYNTAX      Counter64
      MAX-ACCESS  read-only
      STATUS      current
      DESCRIPTION "JMX-standard MBean name"
      ::= { entityCacheCumulativeRuntimeEntry 31  }
   
   
   entityCacheCumulativeRuntimeTotalItemsMemoryPurged OBJECT-TYPE
      SYNTAX      Counter64
      MAX-ACCESS  read-only
      STATUS      current
      DESCRIPTION "JMX-standard MBean name"
      ::= { entityCacheCumulativeRuntimeEntry 32  }
   
   
   entityCacheCumulativeRuntimeTotalNumberDiskPurges OBJECT-TYPE
      SYNTAX      Counter64
      MAX-ACCESS  read-only
      STATUS      current
      DESCRIPTION "JMX-standard MBean name"
      ::= { entityCacheCumulativeRuntimeEntry 33  }
   
   
   entityCacheCumulativeRuntimeTotalNumberMemoryPurges OBJECT-TYPE
      SYNTAX      Counter64
      MAX-ACCESS  read-only
      STATUS      current
      DESCRIPTION "JMX-standard MBean name"
      ::= { entityCacheCumulativeRuntimeEntry 34  }
   
   
   entityCacheCumulativeRuntimeTotalNumberOfRejections OBJECT-TYPE
      SYNTAX      Counter64
      MAX-ACCESS  read-only
      STATUS      current
      DESCRIPTION "JMX-standard MBean name"
      ::= { entityCacheCumulativeRuntimeEntry 35  }
   
   
   entityCacheCumulativeRuntimeTotalNumberOfRenewals OBJECT-TYPE
      SYNTAX      Counter64
      MAX-ACCESS  read-only
      STATUS      current
      DESCRIPTION "JMX-standard MBean name"
      ::= { entityCacheCumulativeRuntimeEntry 36  }
   
   
   entityCacheCumulativeRuntimeTotalSizeOfRejections OBJECT-TYPE
      SYNTAX      Counter64
      MAX-ACCESS  read-only
      STATUS      current
      DESCRIPTION "JMX-standard MBean name"
      ::= { entityCacheCumulativeRuntimeEntry 37  }
   
   
   entityCacheCumulativeRuntimeTotalCurrentEntries OBJECT-TYPE
      SYNTAX      Counter64
      MAX-ACCESS  read-only
      STATUS      current
      DESCRIPTION "Provides a count of the total current number of entries in the entity cache.  Returns the total current number of entries in the entity cache."
      ::= { entityCacheCumulativeRuntimeEntry 38  }
   
   
   entityCacheCumulativeRuntimeAvgPerEntryDiskSize OBJECT-TYPE
      SYNTAX      OCTET STRING
      MAX-ACCESS  read-only
      STATUS      current
      DESCRIPTION "Provides the current average size of the entries in the entity disk cache.  Returns the current average size of the entries in the entity disk cache."
      ::= { entityCacheCumulativeRuntimeEntry 39  }
   
   
   entityCacheCumulativeRuntimeTotalPersistentCurrentEntries OBJECT-TYPE
      SYNTAX      Counter64
      MAX-ACCESS  read-only
      STATUS      current
      DESCRIPTION "Provides a count of the total current number of entries in the cache that have been persisted to disk.  Returns the total current number of entries in the cache that have been persisted to disk."
      ::= { entityCacheCumulativeRuntimeEntry 40  }
   
   
   entityCacheCumulativeRuntimeMaxEntryTimeout OBJECT-TYPE
      SYNTAX      OCTET STRING
      MAX-ACCESS  read-only
      STATUS      current
      DESCRIPTION "Provides the largest timeout value for any current entry in the entity cache.  Returns the largest timeout value for any current entry in the entity cache."
      ::= { entityCacheCumulativeRuntimeEntry 41  }
   
   
   entityCacheCumulativeRuntimeMaxEntryMemorySize OBJECT-TYPE
      SYNTAX      Counter64
      MAX-ACCESS  read-only
      STATUS      current
      DESCRIPTION "Provides the current maximum size of the entries in the entity memory cache.  Returns the current maximum size of the entries in the entity memory cache."
      ::= { entityCacheCumulativeRuntimeEntry 42  }
   
   
   entityCacheCumulativeRuntimeTotalTransientCurrentEntries OBJECT-TYPE
      SYNTAX      Counter64
      MAX-ACCESS  read-only
      STATUS      current
      DESCRIPTION "Provides a count of the total current number of transient (not yet persisted to disk) entries in the entity cache.  Returns the total current number of transient entries in the entity cache."
      ::= { entityCacheCumulativeRuntimeEntry 43  }
   
   
   entityCacheCumulativeRuntimeAvgPerEntryMemorySize OBJECT-TYPE
      SYNTAX      OCTET STRING
      MAX-ACCESS  read-only
      STATUS      current
      DESCRIPTION "Provides the current average size of the entries in the entity memory cache.  Returns the current average size of the entries in the entity memory cache."
      ::= { entityCacheCumulativeRuntimeEntry 44  }
   
   
   entityCacheCumulativeRuntimeAvgPercentPersistent OBJECT-TYPE
      SYNTAX      OCTET STRING
      MAX-ACCESS  read-only
      STATUS      current
      DESCRIPTION "Provides the current average percentage of entries in the entity cache that have been persisted to the disk cache.  Returns current average percentage of entries in the entity cache that have been persisted to the disk cache."
      ::= { entityCacheCumulativeRuntimeEntry 45  }
   
   
   entityCacheCumulativeRuntimeMinEntryMemorySize OBJECT-TYPE
      SYNTAX      Counter64
      MAX-ACCESS  read-only
      STATUS      current
      DESCRIPTION "Provides the current minimum size of the entries in the entity memory cache.  Returns the current minimum size of the entries in the entity memory cache."
      ::= { entityCacheCumulativeRuntimeEntry 46  }
   
   
   entityCacheCumulativeRuntimeAvgTimeout OBJECT-TYPE
      SYNTAX      OCTET STRING
      MAX-ACCESS  read-only
      STATUS      current
      DESCRIPTION "Provides the average amount of time that the entity cache has timed out when trying to retrieve an entity.  Returns the average amount of time that the entity cache has timed out when trying to retrieve an entity."
      ::= { entityCacheCumulativeRuntimeEntry 47  }
   
   
   entityCacheCumulativeRuntimeMemoryPurgesPerHour OBJECT-TYPE
      SYNTAX      OCTET STRING
      MAX-ACCESS  read-only
      STATUS      current
      DESCRIPTION "Provides the cumulative average number of entries that have been purged from the entity cache."
      ::= { entityCacheCumulativeRuntimeEntry 48  }
   
   
   entityCacheCumulativeRuntimeMinEntryTimeout OBJECT-TYPE
      SYNTAX      OCTET STRING
      MAX-ACCESS  read-only
      STATUS      current
      DESCRIPTION "Provides the smallest timeout value for any current entry in the entity cache.  Returns the smallest timeout value for any current entry in the entity cache."
      ::= { entityCacheCumulativeRuntimeEntry 49  }
   
   
   entityCacheCumulativeRuntimeAvgPercentTransient OBJECT-TYPE
      SYNTAX      OCTET STRING
      MAX-ACCESS  read-only
      STATUS      current
      DESCRIPTION "Provides the current average percentage of entries in the entity cache that are transient, or have not been persisted.  Returns current average percentage of entries in the entity cache that are transient, or have not been persisted."
      ::= { entityCacheCumulativeRuntimeEntry 50  }
   
   
   entityCacheCurrentStateRuntimeTable OBJECT-TYPE
      SYNTAX      SEQUENCE OF EntityCacheCurrentStateRuntimeEntry
      MAX-ACCESS  not-accessible
      STATUS      current
      DESCRIPTION "This table is used to monitor an XML Cache."
      ::= { wls 173  }
      
   
   entityCacheCurrentStateRuntimeEntry OBJECT-TYPE
      SYNTAX      EntityCacheCurrentStateRuntimeEntry
      MAX-ACCESS  not-accessible
      STATUS      current
      DESCRIPTION "Entry of entityCacheCurrentStateRuntimeTable"
      INDEX { entityCacheCurrentStateRuntimeIndex}
      ::= { entityCacheCurrentStateRuntimeTable 1 }
      
   EntityCacheCurrentStateRuntimeEntry ::=
      SEQUENCE
      {
         entityCacheCurrentStateRuntimeIndex DisplayString (SIZE (1..16)),
         entityCacheCurrentStateRuntimeObjectName DisplayString (SIZE (1..256)),
         entityCacheCurrentStateRuntimeType DisplayString (SIZE (1..64)),
         entityCacheCurrentStateRuntimeName DisplayString (SIZE (1..64)),
         entityCacheCurrentStateRuntimeParent DisplayString (SIZE (1..256)),
         entityCacheCurrentStateRuntimeDiskUsage Counter64,
         entityCacheCurrentStateRuntimeMemoryUsage Counter64,
         entityCacheCurrentStateRuntimeTotalCurrentEntries Counter64,
         entityCacheCurrentStateRuntimeMinEntryMemorySize Counter64,
         entityCacheCurrentStateRuntimeAvgPercentPersistent OCTET STRING,
         entityCacheCurrentStateRuntimeAvgTimeout OCTET STRING,
         entityCacheCurrentStateRuntimeAvgPerEntryDiskSize OCTET STRING,
         entityCacheCurrentStateRuntimeTotalPersistentCurrentEntries Counter64,
         entityCacheCurrentStateRuntimeMaxEntryTimeout OCTET STRING,
         entityCacheCurrentStateRuntimeMaxEntryMemorySize Counter64,
         entityCacheCurrentStateRuntimeTotalTransientCurrentEntries Counter64,
         entityCacheCurrentStateRuntimeAvgPerEntryMemorySize OCTET STRING,
         entityCacheCurrentStateRuntimeMinEntryTimeout OCTET STRING,
         entityCacheCurrentStateRuntimeAvgPercentTransient OCTET STRING
      }
      
   
   entityCacheCurrentStateRuntimeIndex OBJECT-TYPE
      SYNTAX      DisplayString (SIZE (1..16))
      MAX-ACCESS  read-only
      STATUS      current
      DESCRIPTION "Unique value directed from ObjectName which is used as table index"
      ::= { entityCacheCurrentStateRuntimeEntry 1  }
   
   
   entityCacheCurrentStateRuntimeObjectName OBJECT-TYPE
      SYNTAX      DisplayString (SIZE (1..256))
      MAX-ACCESS  read-only
      STATUS      current
      DESCRIPTION "JMX-standard MBean name"
      ::= { entityCacheCurrentStateRuntimeEntry 5  }
   
   
   entityCacheCurrentStateRuntimeType OBJECT-TYPE
      SYNTAX      DisplayString (SIZE (1..64))
      MAX-ACCESS  read-only
      STATUS      current
      DESCRIPTION "BEA-proprietary MBean type"
      ::= { entityCacheCurrentStateRuntimeEntry 10  }
   
   
   entityCacheCurrentStateRuntimeName OBJECT-TYPE
      SYNTAX      DisplayString (SIZE (1..64))
      MAX-ACCESS  read-only
      STATUS      current
      DESCRIPTION "BEA-proprietary MBean name"
      ::= { entityCacheCurrentStateRuntimeEntry 15  }
   
   
   entityCacheCurrentStateRuntimeParent OBJECT-TYPE
      SYNTAX      DisplayString (SIZE (1..256))
      MAX-ACCESS  read-only
      STATUS      current
      DESCRIPTION "BEA-proprietary Parent object's identification, with syntax
      <type>:<name>"
      ::= { entityCacheCurrentStateRuntimeEntry 20  }
   
   
   entityCacheCurrentStateRuntimeDiskUsage OBJECT-TYPE
      SYNTAX      Counter64
      MAX-ACCESS  read-only
      STATUS      current
      DESCRIPTION "Disks usage"
      ::= { entityCacheCurrentStateRuntimeEntry 25  }
   
   
   entityCacheCurrentStateRuntimeMemoryUsage OBJECT-TYPE
      SYNTAX      Counter64
      MAX-ACCESS  read-only
      STATUS      current
      DESCRIPTION "Disks usage"
      ::= { entityCacheCurrentStateRuntimeEntry 30  }
   
   
   entityCacheCurrentStateRuntimeTotalCurrentEntries OBJECT-TYPE
      SYNTAX      Counter64
      MAX-ACCESS  read-only
      STATUS      current
      DESCRIPTION "Provides a count of the total current number of entries in the entity cache.  Returns the total current number of entries in the entity cache."
      ::= { entityCacheCurrentStateRuntimeEntry 31  }
   
   
   entityCacheCurrentStateRuntimeMinEntryMemorySize OBJECT-TYPE
      SYNTAX      Counter64
      MAX-ACCESS  read-only
      STATUS      current
      DESCRIPTION "Provides the current minimum size of the entries in the entity memory cache.  Returns the current minimum size of the entries in the entity memory cache."
      ::= { entityCacheCurrentStateRuntimeEntry 32  }
   
   
   entityCacheCurrentStateRuntimeAvgPercentPersistent OBJECT-TYPE
      SYNTAX      OCTET STRING
      MAX-ACCESS  read-only
      STATUS      current
      DESCRIPTION "Provides the current average percentage of entries in the entity cache that have been persisted to the disk cache.  Returns current average percentage of entries in the entity cache that have been persisted to the disk cache."
      ::= { entityCacheCurrentStateRuntimeEntry 33  }
   
   
   entityCacheCurrentStateRuntimeAvgTimeout OBJECT-TYPE
      SYNTAX      OCTET STRING
      MAX-ACCESS  read-only
      STATUS      current
      DESCRIPTION "Provides the average amount of time that the entity cache has timed out when trying to retrieve an entity.  Returns the average amount of time that the entity cache has timed out when trying to retrieve an entity."
      ::= { entityCacheCurrentStateRuntimeEntry 34  }
   
   
   entityCacheCurrentStateRuntimeAvgPerEntryDiskSize OBJECT-TYPE
      SYNTAX      OCTET STRING
      MAX-ACCESS  read-only
      STATUS      current
      DESCRIPTION "Provides the current average size of the entries in the entity disk cache.  Returns the current average size of the entries in the entity disk cache."
      ::= { entityCacheCurrentStateRuntimeEntry 35  }
   
   
   entityCacheCurrentStateRuntimeTotalPersistentCurrentEntries OBJECT-TYPE
      SYNTAX      Counter64
      MAX-ACCESS  read-only
      STATUS      current
      DESCRIPTION "Provides a count of the total current number of entries in the cache that have been persisted to disk.  Returns the total current number of entries in the cache that have been persisted to disk."
      ::= { entityCacheCurrentStateRuntimeEntry 36  }
   
   
   entityCacheCurrentStateRuntimeMaxEntryTimeout OBJECT-TYPE
      SYNTAX      OCTET STRING
      MAX-ACCESS  read-only
      STATUS      current
      DESCRIPTION "Provides the largest timeout value for any current entry in the entity cache.  Returns the largest timeout value for any current entry in the entity cache."
      ::= { entityCacheCurrentStateRuntimeEntry 37  }
   
   
   entityCacheCurrentStateRuntimeMaxEntryMemorySize OBJECT-TYPE
      SYNTAX      Counter64
      MAX-ACCESS  read-only
      STATUS      current
      DESCRIPTION "Provides the current maximum size of the entries in the entity memory cache.  Returns the current maximum size of the entries in the entity memory cache."
      ::= { entityCacheCurrentStateRuntimeEntry 38  }
   
   
   entityCacheCurrentStateRuntimeTotalTransientCurrentEntries OBJECT-TYPE
      SYNTAX      Counter64
      MAX-ACCESS  read-only
      STATUS      current
      DESCRIPTION "Provides a count of the total current number of transient (not yet persisted to disk) entries in the entity cache.  Returns the total current number of transient entries in the entity cache."
      ::= { entityCacheCurrentStateRuntimeEntry 39  }
   
   
   entityCacheCurrentStateRuntimeAvgPerEntryMemorySize OBJECT-TYPE
      SYNTAX      OCTET STRING
      MAX-ACCESS  read-only
      STATUS      current
      DESCRIPTION "Provides the current average size of the entries in the entity memory cache.  Returns the current average size of the entries in the entity memory cache."
      ::= { entityCacheCurrentStateRuntimeEntry 40  }
   
   
   entityCacheCurrentStateRuntimeMinEntryTimeout OBJECT-TYPE
      SYNTAX      OCTET STRING
      MAX-ACCESS  read-only
      STATUS      current
      DESCRIPTION "Provides the smallest timeout value for any current entry in the entity cache.  Returns the smallest timeout value for any current entry in the entity cache."
      ::= { entityCacheCurrentStateRuntimeEntry 41  }
   
   
   entityCacheCurrentStateRuntimeAvgPercentTransient OBJECT-TYPE
      SYNTAX      OCTET STRING
      MAX-ACCESS  read-only
      STATUS      current
      DESCRIPTION "Provides the current average percentage of entries in the entity cache that are transient, or have not been persisted.  Returns current average percentage of entries in the entity cache that are transient, or have not been persisted."
      ::= { entityCacheCurrentStateRuntimeEntry 42  }
   
   
   entityCacheRuntimeTable OBJECT-TYPE
      SYNTAX      SEQUENCE OF EntityCacheRuntimeEntry
      MAX-ACCESS  not-accessible
      STATUS      current
      DESCRIPTION "This table is used to monitor an XML Cache."
      ::= { wls 174  }
      
   
   entityCacheRuntimeEntry OBJECT-TYPE
      SYNTAX      EntityCacheRuntimeEntry
      MAX-ACCESS  not-accessible
      STATUS      current
      DESCRIPTION "Entry of entityCacheRuntimeTable"
      INDEX { entityCacheRuntimeIndex}
      ::= { entityCacheRuntimeTable 1 }
      
   EntityCacheRuntimeEntry ::=
      SEQUENCE
      {
         entityCacheRuntimeIndex DisplayString (SIZE (1..16)),
         entityCacheRuntimeObjectName DisplayString (SIZE (1..256)),
         entityCacheRuntimeType DisplayString (SIZE (1..64)),
         entityCacheRuntimeName DisplayString (SIZE (1..64)),
         entityCacheRuntimeParent DisplayString (SIZE (1..256)),
         entityCacheRuntimeAvgPercentTransient INTEGER,
         entityCacheRuntimeAvgPerEntryDiskSize INTEGER,
         entityCacheRuntimeAvgPercentPersistent INTEGER,
         entityCacheRuntimeAvgPerEntryMemorySize INTEGER,
         entityCacheRuntimeAvgTimeout INTEGER,
         entityCacheRuntimeMaxEntryMemorySize Counter64,
         entityCacheRuntimeMaxEntryTimeout INTEGER,
         entityCacheRuntimeMinEntryMemorySize Counter64,
         entityCacheRuntimeMinEntryTimeout INTEGER,
         entityCacheRuntimeTotalCurrentEntries Counter64,
         entityCacheRuntimeTotalPersistentCurrentEntries Counter64,
         entityCacheRuntimeTotalTransientCurrentEntries Counter64
      }
      
   
   entityCacheRuntimeIndex OBJECT-TYPE
      SYNTAX      DisplayString (SIZE (1..16))
      MAX-ACCESS  read-only
      STATUS      current
      DESCRIPTION "Unique value directed from ObjectName which is used as table index"
      ::= { entityCacheRuntimeEntry 1  }
   
   
   entityCacheRuntimeObjectName OBJECT-TYPE
      SYNTAX      DisplayString (SIZE (1..256))
      MAX-ACCESS  read-only
      STATUS      current
      DESCRIPTION "JMX-standard MBean name"
      ::= { entityCacheRuntimeEntry 5  }
   
   
   entityCacheRuntimeType OBJECT-TYPE
      SYNTAX      DisplayString (SIZE (1..64))
      MAX-ACCESS  read-only
      STATUS      current
      DESCRIPTION "BEA-proprietary MBean type"
      ::= { entityCacheRuntimeEntry 10  }
   
   
   entityCacheRuntimeName OBJECT-TYPE
      SYNTAX      DisplayString (SIZE (1..64))
      MAX-ACCESS  read-only
      STATUS      current
      DESCRIPTION "BEA-proprietary MBean name"
      ::= { entityCacheRuntimeEntry 15  }
   
   
   entityCacheRuntimeParent OBJECT-TYPE
      SYNTAX      DisplayString (SIZE (1..256))
      MAX-ACCESS  read-only
      STATUS      current
      DESCRIPTION "BEA-proprietary Parent object's identification, with syntax
      <type>:<name>"
      ::= { entityCacheRuntimeEntry 20  }
   
   
   entityCacheRuntimeAvgPercentTransient OBJECT-TYPE
      SYNTAX      INTEGER
      MAX-ACCESS  read-only
      STATUS      current
      DESCRIPTION "Disks usage"
      ::= { entityCacheRuntimeEntry 25  }
   
   
   entityCacheRuntimeAvgPerEntryDiskSize OBJECT-TYPE
      SYNTAX      INTEGER
      MAX-ACCESS  read-only
      STATUS      current
      DESCRIPTION "Disks usage"
      ::= { entityCacheRuntimeEntry 30  }
   
   
   entityCacheRuntimeAvgPercentPersistent OBJECT-TYPE
      SYNTAX      INTEGER
      MAX-ACCESS  read-only
      STATUS      current
      DESCRIPTION "Disks usage"
      ::= { entityCacheRuntimeEntry 31  }
   
   
   entityCacheRuntimeAvgPerEntryMemorySize OBJECT-TYPE
      SYNTAX      INTEGER
      MAX-ACCESS  read-only
      STATUS      current
      DESCRIPTION "Disks usage"
      ::= { entityCacheRuntimeEntry 32  }
   
   
   entityCacheRuntimeAvgTimeout OBJECT-TYPE
      SYNTAX      INTEGER
      MAX-ACCESS  read-only
      STATUS      current
      DESCRIPTION "Disks usage"
      ::= { entityCacheRuntimeEntry 33  }
   
   
   entityCacheRuntimeMaxEntryMemorySize OBJECT-TYPE
      SYNTAX      Counter64
      MAX-ACCESS  read-only
      STATUS      current
      DESCRIPTION "Disks usage"
      ::= { entityCacheRuntimeEntry 34  }
   
   
   entityCacheRuntimeMaxEntryTimeout OBJECT-TYPE
      SYNTAX      INTEGER
      MAX-ACCESS  read-only
      STATUS      current
      DESCRIPTION "Disks usage"
      ::= { entityCacheRuntimeEntry 35  }
   
   
   entityCacheRuntimeMinEntryMemorySize OBJECT-TYPE
      SYNTAX      Counter64
      MAX-ACCESS  read-only
      STATUS      current
      DESCRIPTION "Disks usage"
      ::= { entityCacheRuntimeEntry 36  }
   
   
   entityCacheRuntimeMinEntryTimeout OBJECT-TYPE
      SYNTAX      INTEGER
      MAX-ACCESS  read-only
      STATUS      current
      DESCRIPTION "Disks usage"
      ::= { entityCacheRuntimeEntry 37  }
   
   
   entityCacheRuntimeTotalCurrentEntries OBJECT-TYPE
      SYNTAX      Counter64
      MAX-ACCESS  read-only
      STATUS      current
      DESCRIPTION "Disks usage"
      ::= { entityCacheRuntimeEntry 38  }
   
   
   entityCacheRuntimeTotalPersistentCurrentEntries OBJECT-TYPE
      SYNTAX      Counter64
      MAX-ACCESS  read-only
      STATUS      current
      DESCRIPTION "Disks usage"
      ::= { entityCacheRuntimeEntry 39  }
   
   
   entityCacheRuntimeTotalTransientCurrentEntries OBJECT-TYPE
      SYNTAX      Counter64
      MAX-ACCESS  read-only
      STATUS      current
      DESCRIPTION "Disks usage"
      ::= { entityCacheRuntimeEntry 40  }
   
   
   executeQueueRuntimeTable OBJECT-TYPE
      SYNTAX      SEQUENCE OF ExecuteQueueRuntimeEntry
      MAX-ACCESS  not-accessible
      STATUS      current
      DESCRIPTION "The execute threads currently assigned to the queue."
      ::= { wls 180  }
      
   
   executeQueueRuntimeEntry OBJECT-TYPE
      SYNTAX      ExecuteQueueRuntimeEntry
      MAX-ACCESS  not-accessible
      STATUS      current
      DESCRIPTION "Entry of executeQueueRuntimeTable"
      INDEX { executeQueueRuntimeIndex}
      ::= { executeQueueRuntimeTable 1 }
      
   ExecuteQueueRuntimeEntry ::=
      SEQUENCE
      {
         executeQueueRuntimeIndex DisplayString (SIZE (1..16)),
         executeQueueRuntimeObjectName DisplayString (SIZE (1..256)),
         executeQueueRuntimeType DisplayString (SIZE (1..64)),
         executeQueueRuntimeName DisplayString (SIZE (1..64)),
         executeQueueRuntimeParent DisplayString (SIZE (1..256)),
         executeQueueRuntimeExecuteThreadCurrentIdleCount INTEGER,
         executeQueueRuntimePendingRequestOldestTime Counter64,
         executeQueueRuntimePendingRequestCurrentCount INTEGER,
         executeQueueRuntimeServicedRequestTotalCount INTEGER,
         executeQueueRuntimeExecuteThreads DisplayString (SIZE (1..2048)),
         executeQueueRuntimeExecuteThreadTotalCount INTEGER
      }
      
   
   executeQueueRuntimeIndex OBJECT-TYPE
      SYNTAX      DisplayString (SIZE (1..16))
      MAX-ACCESS  read-only
      STATUS      current
      DESCRIPTION "Unique value directed from ObjectName which is used as table index"
      ::= { executeQueueRuntimeEntry 1  }
   
   
   executeQueueRuntimeObjectName OBJECT-TYPE
      SYNTAX      DisplayString (SIZE (1..256))
      MAX-ACCESS  read-only
      STATUS      current
      DESCRIPTION "JMX-standard MBean name"
      ::= { executeQueueRuntimeEntry 5  }
   
   
   executeQueueRuntimeType OBJECT-TYPE
      SYNTAX      DisplayString (SIZE (1..64))
      MAX-ACCESS  read-only
      STATUS      current
      DESCRIPTION "BEA-proprietary MBean type"
      ::= { executeQueueRuntimeEntry 10  }
   
   
   executeQueueRuntimeName OBJECT-TYPE
      SYNTAX      DisplayString (SIZE (1..64))
      MAX-ACCESS  read-only
      STATUS      current
      DESCRIPTION "BEA-proprietary MBean name"
      ::= { executeQueueRuntimeEntry 15  }
   
   
   executeQueueRuntimeParent OBJECT-TYPE
      SYNTAX      DisplayString (SIZE (1..256))
      MAX-ACCESS  read-only
      STATUS      current
      DESCRIPTION "BEA-proprietary Parent object's identification, with syntax
      <type>:<name>"
      ::= { executeQueueRuntimeEntry 20  }
   
   
   executeQueueRuntimeExecuteThreadCurrentIdleCount OBJECT-TYPE
      SYNTAX      INTEGER
      MAX-ACCESS  read-only
      STATUS      current
      DESCRIPTION "The number of idle threads assigned to the queue."
      ::= { executeQueueRuntimeEntry 25  }
   
   
   executeQueueRuntimePendingRequestOldestTime OBJECT-TYPE
      SYNTAX      Counter64
      MAX-ACCESS  read-only
      STATUS      current
      DESCRIPTION "the time that the longest waiting request was placed in
      the queue."
      ::= { executeQueueRuntimeEntry 30  }
   
   
   executeQueueRuntimePendingRequestCurrentCount OBJECT-TYPE
      SYNTAX      INTEGER
      MAX-ACCESS  read-only
      STATUS      current
      DESCRIPTION "The number of waiting requests in the queue."
      ::= { executeQueueRuntimeEntry 35  }
   
   
   executeQueueRuntimeServicedRequestTotalCount OBJECT-TYPE
      SYNTAX      INTEGER
      MAX-ACCESS  read-only
      STATUS      current
      DESCRIPTION "The number of requests which have been processed by this
      queue."
      ::= { executeQueueRuntimeEntry 40  }
   
   
   executeQueueRuntimeExecuteThreads OBJECT-TYPE
      SYNTAX      DisplayString (SIZE (1..2048))
      MAX-ACCESS  read-only
      STATUS      current
      DESCRIPTION "The execute threads currently assigned to the queue."
      ::= { executeQueueRuntimeEntry 45  }
   
   
   executeQueueRuntimeExecuteThreadTotalCount OBJECT-TYPE
      SYNTAX      INTEGER
      MAX-ACCESS  read-only
      STATUS      current
      DESCRIPTION "The total number of execute threads assigned to the queue."
      ::= { executeQueueRuntimeEntry 46  }
   
   
   interceptionComponentRuntimeTable OBJECT-TYPE
      SYNTAX      SEQUENCE OF InterceptionComponentRuntimeEntry
      MAX-ACCESS  not-accessible
      STATUS      current
      DESCRIPTION "This table represents an Interception Module Deployment."
      ::= { wls 181  }
      
   
   interceptionComponentRuntimeEntry OBJECT-TYPE
      SYNTAX      InterceptionComponentRuntimeEntry
      MAX-ACCESS  not-accessible
      STATUS      current
      DESCRIPTION "Entry of interceptionComponentRuntimeTable"
      INDEX { interceptionComponentRuntimeIndex}
      ::= { interceptionComponentRuntimeTable 1 }
      
   InterceptionComponentRuntimeEntry ::=
      SEQUENCE
      {
         interceptionComponentRuntimeIndex DisplayString (SIZE (1..16)),
         interceptionComponentRuntimeObjectName DisplayString (SIZE (1..256)),
         interceptionComponentRuntimeType DisplayString (SIZE (1..64)),
         interceptionComponentRuntimeName DisplayString (SIZE (1..64)),
         interceptionComponentRuntimeParent DisplayString (SIZE (1..256)),
         interceptionComponentRuntimeModuleId DisplayString (SIZE (1..256)),
         interceptionComponentRuntimeDeploymentState INTEGER
      }
      
   
   interceptionComponentRuntimeIndex OBJECT-TYPE
      SYNTAX      DisplayString (SIZE (1..16))
      MAX-ACCESS  read-only
      STATUS      current
      DESCRIPTION "Unique value directed from ObjectName which is used as table index"
      ::= { interceptionComponentRuntimeEntry 1  }
   
   
   interceptionComponentRuntimeObjectName OBJECT-TYPE
      SYNTAX      DisplayString (SIZE (1..256))
      MAX-ACCESS  read-only
      STATUS      current
      DESCRIPTION "JMX-standard MBean name"
      ::= { interceptionComponentRuntimeEntry 5  }
   
   
   interceptionComponentRuntimeType OBJECT-TYPE
      SYNTAX      DisplayString (SIZE (1..64))
      MAX-ACCESS  read-only
      STATUS      current
      DESCRIPTION "BEA-proprietary MBean type"
      ::= { interceptionComponentRuntimeEntry 10  }
   
   
   interceptionComponentRuntimeName OBJECT-TYPE
      SYNTAX      DisplayString (SIZE (1..64))
      MAX-ACCESS  read-only
      STATUS      current
      DESCRIPTION "BEA-proprietary MBean name"
      ::= { interceptionComponentRuntimeEntry 15  }
   
   
   interceptionComponentRuntimeParent OBJECT-TYPE
      SYNTAX      DisplayString (SIZE (1..256))
      MAX-ACCESS  read-only
      STATUS      current
      DESCRIPTION "BEA-proprietary Parent object's identification, with syntax
      <type>:<name>"
      ::= { interceptionComponentRuntimeEntry 20  }
   
   
   interceptionComponentRuntimeModuleId OBJECT-TYPE
      SYNTAX      DisplayString (SIZE (1..256))
      MAX-ACCESS  read-only
      STATUS      current
      DESCRIPTION "Typical modules will use the URI for their id."
      ::= { interceptionComponentRuntimeEntry 25  }
   
   
   interceptionComponentRuntimeDeploymentState OBJECT-TYPE
      SYNTAX      INTEGER
      MAX-ACCESS  read-only
      STATUS      current
      DESCRIPTION "Return the current deployment state of the module."
      ::= { interceptionComponentRuntimeEntry 30  }
   
   
   jdbcConnectionPoolRuntimeTable OBJECT-TYPE
      SYNTAX      SEQUENCE OF JdbcConnectionPoolRuntimeEntry
      MAX-ACCESS  not-accessible
      STATUS      current
      DESCRIPTION "This table is used for monitoring a WebLogic JDBC component"
      ::= { wls 190  }
      
   
   jdbcConnectionPoolRuntimeEntry OBJECT-TYPE
      SYNTAX      JdbcConnectionPoolRuntimeEntry
      MAX-ACCESS  not-accessible
      STATUS      current
      DESCRIPTION "Entry of jdbcConnectionPoolRuntimeTable"
      INDEX { jdbcConnectionPoolRuntimeIndex}
      ::= { jdbcConnectionPoolRuntimeTable 1 }
      
   JdbcConnectionPoolRuntimeEntry ::=
      SEQUENCE
      {
         jdbcConnectionPoolRuntimeIndex DisplayString (SIZE (1..16)),
         jdbcConnectionPoolRuntimeObjectName DisplayString (SIZE (1..256)),
         jdbcConnectionPoolRuntimeType DisplayString (SIZE (1..64)),
         jdbcConnectionPoolRuntimeName DisplayString (SIZE (1..64)),
         jdbcConnectionPoolRuntimeParent DisplayString (SIZE (1..256)),
         jdbcConnectionPoolRuntimeActiveConnectionsCurrentCount INTEGER,
         jdbcConnectionPoolRuntimeWaitingForConnectionCurrentCount INTEGER,
         jdbcConnectionPoolRuntimeVersionJDBCDriver DisplayString (SIZE (1..32)),
         jdbcConnectionPoolRuntimeActiveConnectionsHighCount INTEGER,
         jdbcConnectionPoolRuntimeWaitingForConnectionHighCount INTEGER,
         jdbcConnectionPoolRuntimeWaitSecondsHighCount INTEGER,
         jdbcConnectionPoolRuntimeConnectionsTotalCount INTEGER,
         jdbcConnectionPoolRuntimeMaxCapacity INTEGER,
         jdbcConnectionPoolRuntimeActiveConnectionsAverageCount INTEGER,
         jdbcConnectionPoolRuntimeConnectionDelayTime INTEGER,
         jdbcConnectionPoolRuntimeConnectionLeakProfileCount Counter32,
         jdbcConnectionPoolRuntimeCurrCapacity INTEGER,
         jdbcConnectionPoolRuntimeFailuresToReconnectCount INTEGER,
         jdbcConnectionPoolRuntimeHighestNumAvailable INTEGER,
         jdbcConnectionPoolRuntimeHighestNumUnavailable INTEGER,
         jdbcConnectionPoolRuntimeLeakedConnectionCount INTEGER,
         jdbcConnectionPoolRuntimeNumAvailable INTEGER,
         jdbcConnectionPoolRuntimeNumUnavailable INTEGER,
         jdbcConnectionPoolRuntimeStatementProfileCount INTEGER
      }
      
   
   jdbcConnectionPoolRuntimeIndex OBJECT-TYPE
      SYNTAX      DisplayString (SIZE (1..16))
      MAX-ACCESS  read-only
      STATUS      current
      DESCRIPTION "Unique value directed from ObjectName which is used as table index"
      ::= { jdbcConnectionPoolRuntimeEntry 1  }
   
   
   jdbcConnectionPoolRuntimeObjectName OBJECT-TYPE
      SYNTAX      DisplayString (SIZE (1..256))
      MAX-ACCESS  read-only
      STATUS      current
      DESCRIPTION "JMX-standard MBean name"
      ::= { jdbcConnectionPoolRuntimeEntry 5  }
   
   
   jdbcConnectionPoolRuntimeType OBJECT-TYPE
      SYNTAX      DisplayString (SIZE (1..64))
      MAX-ACCESS  read-only
      STATUS      current
      DESCRIPTION "BEA-proprietary MBean type"
      ::= { jdbcConnectionPoolRuntimeEntry 10  }
   
   
   jdbcConnectionPoolRuntimeName OBJECT-TYPE
      SYNTAX      DisplayString (SIZE (1..64))
      MAX-ACCESS  read-only
      STATUS      current
      DESCRIPTION "BEA-proprietary MBean name"
      ::= { jdbcConnectionPoolRuntimeEntry 15  }
   
   
   jdbcConnectionPoolRuntimeParent OBJECT-TYPE
      SYNTAX      DisplayString (SIZE (1..256))
      MAX-ACCESS  read-only
      STATUS      current
      DESCRIPTION "BEA-proprietary Parent object's identification, with syntax
      <type>:<name>"
      ::= { jdbcConnectionPoolRuntimeEntry 20  }
   
   
   jdbcConnectionPoolRuntimeActiveConnectionsCurrentCount OBJECT-TYPE
      SYNTAX      INTEGER
      MAX-ACCESS  read-only
      STATUS      current
      DESCRIPTION "The current total active connections."
      ::= { jdbcConnectionPoolRuntimeEntry 25  }
   
   
   jdbcConnectionPoolRuntimeWaitingForConnectionCurrentCount OBJECT-TYPE
      SYNTAX      INTEGER
      MAX-ACCESS  read-only
      STATUS      current
      DESCRIPTION "The current total waiting for a connection."
      ::= { jdbcConnectionPoolRuntimeEntry 30  }
   
   
   jdbcConnectionPoolRuntimeVersionJDBCDriver OBJECT-TYPE
      SYNTAX      DisplayString (SIZE (1..32))
      MAX-ACCESS  read-only
      STATUS      current
      DESCRIPTION "The version of the JDBC driver, in the format of
      concatenating the Driver class name with 'major: XX, minor: YY'."
      ::= { jdbcConnectionPoolRuntimeEntry 35  }
   
   
   jdbcConnectionPoolRuntimeActiveConnectionsHighCount OBJECT-TYPE
      SYNTAX      INTEGER
      MAX-ACCESS  read-only
      STATUS      current
      DESCRIPTION "The high water mark of active connections in this JDBCConnectionPoolRuntimeMBean.
      The count starts at zero each time the JDBCConnectionPoolRuntimeMBean
      is instantiated."
      ::= { jdbcConnectionPoolRuntimeEntry 40  }
   
   
   jdbcConnectionPoolRuntimeWaitingForConnectionHighCount OBJECT-TYPE
      SYNTAX      INTEGER
      MAX-ACCESS  read-only
      STATUS      current
      DESCRIPTION "The high water mark of waiters for a connection in this JDBCConnectionPoolRuntimeMBean.
      The count starts at zero each time the JDBCConnectionPoolRuntimeMBean
      is instantiated."
      ::= { jdbcConnectionPoolRuntimeEntry 45  }
   
   
   jdbcConnectionPoolRuntimeWaitSecondsHighCount OBJECT-TYPE
      SYNTAX      INTEGER
      MAX-ACCESS  read-only
      STATUS      current
      DESCRIPTION "The number of seconds the longest waiter for a connection waited"
      ::= { jdbcConnectionPoolRuntimeEntry 50  }
   
   
   jdbcConnectionPoolRuntimeConnectionsTotalCount OBJECT-TYPE
      SYNTAX      INTEGER
      MAX-ACCESS  read-only
      STATUS      current
      DESCRIPTION "the total number of JDBC connections in this
      JDBCConnectionPoolRuntimeMBean since the pool is instantiated."
      ::= { jdbcConnectionPoolRuntimeEntry 55  }
   
   
   jdbcConnectionPoolRuntimeMaxCapacity OBJECT-TYPE
      SYNTAX      INTEGER
      MAX-ACCESS  read-only
      STATUS      current
      DESCRIPTION "The maximum capacity of this JDBC pool"
      ::= { jdbcConnectionPoolRuntimeEntry 60  }
   
   
   jdbcConnectionPoolRuntimeActiveConnectionsAverageCount OBJECT-TYPE
      SYNTAX      INTEGER
      MAX-ACCESS  read-only
      STATUS      current
      DESCRIPTION "The running average of active connections in this JDBCConnectionPoolRuntimeMBean"
      ::= { jdbcConnectionPoolRuntimeEntry 61  }
   
   
   jdbcConnectionPoolRuntimeConnectionDelayTime OBJECT-TYPE
      SYNTAX      INTEGER
      MAX-ACCESS  read-only
      STATUS      current
      DESCRIPTION "Averaged time necessary to get a connection from the database"
      ::= { jdbcConnectionPoolRuntimeEntry 62  }
   
   
   jdbcConnectionPoolRuntimeConnectionLeakProfileCount OBJECT-TYPE
      SYNTAX      Counter32
      MAX-ACCESS  read-only
      STATUS      current
      DESCRIPTION "Generated Object."
      ::= { jdbcConnectionPoolRuntimeEntry 63  }
   
   
   jdbcConnectionPoolRuntimeCurrCapacity OBJECT-TYPE
      SYNTAX      INTEGER
      MAX-ACCESS  read-only
      STATUS      current
      DESCRIPTION "Returns the current capacity of this connection pool."
      ::= { jdbcConnectionPoolRuntimeEntry 64  }
   
   
   jdbcConnectionPoolRuntimeFailuresToReconnectCount OBJECT-TYPE
      SYNTAX      INTEGER
      MAX-ACCESS  read-only
      STATUS      current
      DESCRIPTION "Number of cases when a connection pool attempted to refresh a connection to a database and failed"
      ::= { jdbcConnectionPoolRuntimeEntry 65  }
   
   
   jdbcConnectionPoolRuntimeHighestNumAvailable OBJECT-TYPE
      SYNTAX      INTEGER
      MAX-ACCESS  read-only
      STATUS      current
      DESCRIPTION "Returns the highest number of available connections in this pool"
      ::= { jdbcConnectionPoolRuntimeEntry 66  }
   
   
   jdbcConnectionPoolRuntimeHighestNumUnavailable OBJECT-TYPE
      SYNTAX      INTEGER
      MAX-ACCESS  read-only
      STATUS      current
      DESCRIPTION "Returns the highest number of unavailable connections in this pool"
      ::= { jdbcConnectionPoolRuntimeEntry 67  }
   
   
   jdbcConnectionPoolRuntimeLeakedConnectionCount OBJECT-TYPE
      SYNTAX      INTEGER
      MAX-ACCESS  read-only
      STATUS      current
      DESCRIPTION "Number of leaked connections."
      ::= { jdbcConnectionPoolRuntimeEntry 68  }
   
   
   jdbcConnectionPoolRuntimeNumAvailable OBJECT-TYPE
      SYNTAX      INTEGER
      MAX-ACCESS  read-only
      STATUS      current
      DESCRIPTION "Returns the number of available connections in this pool"
      ::= { jdbcConnectionPoolRuntimeEntry 69  }
   
   
   jdbcConnectionPoolRuntimeNumUnavailable OBJECT-TYPE
      SYNTAX      INTEGER
      MAX-ACCESS  read-only
      STATUS      current
      DESCRIPTION "Returns the number of unavailable connections in this pool"
      ::= { jdbcConnectionPoolRuntimeEntry 70  }
   
   
   jdbcConnectionPoolRuntimeStatementProfileCount OBJECT-TYPE
      SYNTAX      INTEGER
      MAX-ACCESS  read-only
      STATUS      current
      DESCRIPTION "Number of the SQL statement profiles in profile storage."
      ::= { jdbcConnectionPoolRuntimeEntry 71  }
   
   
   jdbcDataSourceRuntimeTable OBJECT-TYPE
      SYNTAX      SEQUENCE OF JdbcDataSourceRuntimeEntry
      MAX-ACCESS  not-accessible
      STATUS      current
      DESCRIPTION "This table is used for monitoring a WebLogic JDBC Data Source and its associated connection pool."
      ::= { wls 191  }
      
   
   jdbcDataSourceRuntimeEntry OBJECT-TYPE
      SYNTAX      JdbcDataSourceRuntimeEntry
      MAX-ACCESS  not-accessible
      STATUS      current
      DESCRIPTION "Entry of jdbcDataSourceRuntimeTable"
      INDEX { jdbcDataSourceRuntimeIndex}
      ::= { jdbcDataSourceRuntimeTable 1 }
      
   JdbcDataSourceRuntimeEntry ::=
      SEQUENCE
      {
         jdbcDataSourceRuntimeIndex DisplayString (SIZE (1..16)),
         jdbcDataSourceRuntimeObjectName DisplayString (SIZE (1..256)),
         jdbcDataSourceRuntimeType DisplayString (SIZE (1..64)),
         jdbcDataSourceRuntimeName DisplayString (SIZE (1..64)),
         jdbcDataSourceRuntimeParent DisplayString (SIZE (1..256)),
         jdbcDataSourceRuntimeLeakedConnectionCount INTEGER,
         jdbcDataSourceRuntimeEnabled INTEGER
                     {
                        true(1),
                        false(2)
                     }
         ,
         jdbcDataSourceRuntimeState DisplayString (SIZE (1..64)),
         jdbcDataSourceRuntimeFailuresToReconnectCount INTEGER,
         jdbcDataSourceRuntimeConnectionDelayTime DisplayString (SIZE (1..32)),
         jdbcDataSourceRuntimePrepStmtCacheAccessCount Counter64,
         jdbcDataSourceRuntimePrepStmtCacheAddCount Counter64,
         jdbcDataSourceRuntimePrepStmtCacheDeleteCount Counter64,
         jdbcDataSourceRuntimePrepStmtCacheCurrentSize INTEGER,
         jdbcDataSourceRuntimePrepStmtCacheHitCount INTEGER,
         jdbcDataSourceRuntimePrepStmtCacheMissCount INTEGER,
         jdbcDataSourceRuntimeActiveConnectionsCurrentCount INTEGER,
         jdbcDataSourceRuntimeWaitingForConnectionCurrentCount INTEGER,
         jdbcDataSourceRuntimeVersionJDBCDriver DisplayString (SIZE (1..64)),
         jdbcDataSourceRuntimeActiveConnectionsHighCount INTEGER,
         jdbcDataSourceRuntimeActiveConnectionsAverageCount INTEGER,
         jdbcDataSourceRuntimeReserveRequestCount Counter64,
         jdbcDataSourceRuntimeFailedReserveRequestCount Counter64,
         jdbcDataSourceRuntimeWaitingForConnectionHighCount INTEGER,
         jdbcDataSourceRuntimeWaitingForConnectionTotal Counter64,
         jdbcDataSourceRuntimeWaitingForConnectionSuccessTotal Counter64,
         jdbcDataSourceRuntimeWaitingForConnectionFailureTotal Counter64,
         jdbcDataSourceRuntimeWaitSecondsHighCount INTEGER,
         jdbcDataSourceRuntimeConnectionsTotalCount INTEGER,
         jdbcDataSourceRuntimeCurrCapacity INTEGER,
         jdbcDataSourceRuntimeCurrCapacityHighCount INTEGER,
         jdbcDataSourceRuntimeNumAvailable INTEGER,
         jdbcDataSourceRuntimeHighestNumAvailable INTEGER,
         jdbcDataSourceRuntimeNumUnavailable INTEGER,
         jdbcDataSourceRuntimeHighestNumUnavailable INTEGER,
         jdbcDataSourceRuntimeModuleId OCTET STRING,
         jdbcDataSourceRuntimeDeploymentState INTEGER
      }
      
   
   jdbcDataSourceRuntimeIndex OBJECT-TYPE
      SYNTAX      DisplayString (SIZE (1..16))
      MAX-ACCESS  read-only
      STATUS      current
      DESCRIPTION "Unique value directed from ObjectName which is used as table index"
      ::= { jdbcDataSourceRuntimeEntry 1  }
   
   
   jdbcDataSourceRuntimeObjectName OBJECT-TYPE
      SYNTAX      DisplayString (SIZE (1..256))
      MAX-ACCESS  read-only
      STATUS      current
      DESCRIPTION "JMX-standard MBean name"
      ::= { jdbcDataSourceRuntimeEntry 5  }
   
   
   jdbcDataSourceRuntimeType OBJECT-TYPE
      SYNTAX      DisplayString (SIZE (1..64))
      MAX-ACCESS  read-only
      STATUS      current
      DESCRIPTION "BEA-proprietary MBean type"
      ::= { jdbcDataSourceRuntimeEntry 10  }
   
   
   jdbcDataSourceRuntimeName OBJECT-TYPE
      SYNTAX      DisplayString (SIZE (1..64))
      MAX-ACCESS  read-only
      STATUS      current
      DESCRIPTION "BEA-proprietary MBean name"
      ::= { jdbcDataSourceRuntimeEntry 15  }
   
   
   jdbcDataSourceRuntimeParent OBJECT-TYPE
      SYNTAX      DisplayString (SIZE (1..256))
      MAX-ACCESS  read-only
      STATUS      current
      DESCRIPTION "BEA-proprietary Parent object's identification, with syntax
      <type>:<name>"
      ::= { jdbcDataSourceRuntimeEntry 20  }
   
   
   jdbcDataSourceRuntimeLeakedConnectionCount OBJECT-TYPE
      SYNTAX      INTEGER
      MAX-ACCESS  read-only
      STATUS      current
      DESCRIPTION "Returns the number of leaked connections. A leaked connection is a connection that was reserved from the data source
      but was not returned to the data source by calling close()."
      ::= { jdbcDataSourceRuntimeEntry 25  }
   
   
   jdbcDataSourceRuntimeEnabled OBJECT-TYPE
      SYNTAX      INTEGER
                  {
                     true(1),
                     false(2)
                  }
      
      MAX-ACCESS  read-only
      STATUS      current
      DESCRIPTION "Returns true if the data source is enabled."
      ::= { jdbcDataSourceRuntimeEntry 30  }
   
   
   jdbcDataSourceRuntimeState OBJECT-TYPE
      SYNTAX      DisplayString (SIZE (1..64))
      MAX-ACCESS  read-only
      STATUS      current
      DESCRIPTION "Returns the current state of the data source (Running, Suspended, Shutdown, Unhealthy, Unknown)."
      ::= { jdbcDataSourceRuntimeEntry 35  }
   
   
   jdbcDataSourceRuntimeFailuresToReconnectCount OBJECT-TYPE
      SYNTAX      INTEGER
      MAX-ACCESS  read-only
      STATUS      current
      DESCRIPTION "Returns the number of times that the data source attempted to refresh a database connection and failed."
      ::= { jdbcDataSourceRuntimeEntry 40  }
   
   
   jdbcDataSourceRuntimeConnectionDelayTime OBJECT-TYPE
      SYNTAX      DisplayString (SIZE (1..32))
      MAX-ACCESS  read-only
      STATUS      current
      DESCRIPTION "Returns the average time in milliseconds that it takes to create a physical connection to the database."
      ::= { jdbcDataSourceRuntimeEntry 45  }
   
   
   jdbcDataSourceRuntimePrepStmtCacheAccessCount OBJECT-TYPE
      SYNTAX      Counter64
      MAX-ACCESS  read-only
      STATUS      current
      DESCRIPTION "Returns the cumulative, running count of the number of times that the statement cache was accessed."
      ::= { jdbcDataSourceRuntimeEntry 50  }
   
   
   jdbcDataSourceRuntimePrepStmtCacheAddCount OBJECT-TYPE
      SYNTAX      Counter64
      MAX-ACCESS  read-only
      STATUS      current
      DESCRIPTION "Returns the cumulative, running count of the number of statements added to the statement cache."
      ::= { jdbcDataSourceRuntimeEntry 55  }
   
   
   jdbcDataSourceRuntimePrepStmtCacheDeleteCount OBJECT-TYPE
      SYNTAX      Counter64
      MAX-ACCESS  read-only
      STATUS      current
      DESCRIPTION "Returns the cumulative, running count of statements discarded from the cache."
      ::= { jdbcDataSourceRuntimeEntry 60  }
   
   
   jdbcDataSourceRuntimePrepStmtCacheCurrentSize OBJECT-TYPE
      SYNTAX      INTEGER
      MAX-ACCESS  read-only
      STATUS      current
      DESCRIPTION "Returns the number of prepared and callable statements currently cached in the statement cache."
      ::= { jdbcDataSourceRuntimeEntry 65  }
   
   
   jdbcDataSourceRuntimePrepStmtCacheHitCount OBJECT-TYPE
      SYNTAX      INTEGER
      MAX-ACCESS  read-only
      STATUS      current
      DESCRIPTION "Returns the cumulative, running count of the number of times that statements from the cache were used."
      ::= { jdbcDataSourceRuntimeEntry 70  }
   
   
   jdbcDataSourceRuntimePrepStmtCacheMissCount OBJECT-TYPE
      SYNTAX      INTEGER
      MAX-ACCESS  read-only
      STATUS      current
      DESCRIPTION "Returns the number of times that a statement request could not be satisfied with a statement from the cache."
      ::= { jdbcDataSourceRuntimeEntry 75  }
   
   
   jdbcDataSourceRuntimeActiveConnectionsCurrentCount OBJECT-TYPE
      SYNTAX      INTEGER
      MAX-ACCESS  read-only
      STATUS      current
      DESCRIPTION "Returns the number of connections currently in use by applications."
      ::= { jdbcDataSourceRuntimeEntry 80  }
   
   
   jdbcDataSourceRuntimeWaitingForConnectionCurrentCount OBJECT-TYPE
      SYNTAX      INTEGER
      MAX-ACCESS  read-only
      STATUS      current
      DESCRIPTION "Returns the number of connection requests waiting for a database connection."
      ::= { jdbcDataSourceRuntimeEntry 85  }
   
   
   jdbcDataSourceRuntimeVersionJDBCDriver OBJECT-TYPE
      SYNTAX      DisplayString (SIZE (1..64))
      MAX-ACCESS  read-only
      STATUS      current
      DESCRIPTION "Returns the driver class name and version of the JDBC driver used to create database connections."
      ::= { jdbcDataSourceRuntimeEntry 90  }
   
   
   jdbcDataSourceRuntimeActiveConnectionsHighCount OBJECT-TYPE
      SYNTAX      INTEGER
      MAX-ACCESS  read-only
      STATUS      current
      DESCRIPTION "Returns the Highest number of active database connections in this instance of the data source since the data source was instantiated."
      ::= { jdbcDataSourceRuntimeEntry 95  }
   
   
   jdbcDataSourceRuntimeActiveConnectionsAverageCount OBJECT-TYPE
      SYNTAX      INTEGER
      MAX-ACCESS  read-only
      STATUS      current
      DESCRIPTION "Returns the Average number of active connections in this instance of the data source."
      ::= { jdbcDataSourceRuntimeEntry 100  }
   
   
   jdbcDataSourceRuntimeReserveRequestCount OBJECT-TYPE
      SYNTAX      Counter64
      MAX-ACCESS  read-only
      STATUS      current
      DESCRIPTION "Returns the cumulative, running count of requests for a connection from this data source."
      ::= { jdbcDataSourceRuntimeEntry 105  }
   
   
   jdbcDataSourceRuntimeFailedReserveRequestCount OBJECT-TYPE
      SYNTAX      Counter64
      MAX-ACCESS  read-only
      STATUS      current
      DESCRIPTION "Returns the cumulative, running count of requests for a connection from this data source that could not be fulfilled."
      ::= { jdbcDataSourceRuntimeEntry 110  }
   
   
   jdbcDataSourceRuntimeWaitingForConnectionHighCount OBJECT-TYPE
      SYNTAX      INTEGER
      MAX-ACCESS  read-only
      STATUS      current
      DESCRIPTION "Returns the Highest number of application requests concurrently waiting for a connection from this instance of the data source."
      ::= { jdbcDataSourceRuntimeEntry 115  }
   
   
   jdbcDataSourceRuntimeWaitingForConnectionTotal OBJECT-TYPE
      SYNTAX      Counter64
      MAX-ACCESS  read-only
      STATUS      current
      DESCRIPTION "Returns the cumulative, running count of requests for a connection from this data source that had to wait before getting
      a connection, including those that eventually got a connection and those that did not get a connection."
      ::= { jdbcDataSourceRuntimeEntry 120  }
   
   
   jdbcDataSourceRuntimeWaitingForConnectionSuccessTotal OBJECT-TYPE
      SYNTAX      Counter64
      MAX-ACCESS  read-only
      STATUS      current
      DESCRIPTION "Returns the cumulative, running count of requests for a connection from this data source that had to wait before
      getting a connection and eventually succeeded in getting a connection."
      ::= { jdbcDataSourceRuntimeEntry 125  }
   
   
   jdbcDataSourceRuntimeWaitingForConnectionFailureTotal OBJECT-TYPE
      SYNTAX      Counter64
      MAX-ACCESS  read-only
      STATUS      current
      DESCRIPTION "Returns the cumulative, running count of requests for a connection from this data source that had to wait before
      getting a connection and eventually failed to get a connection."
      ::= { jdbcDataSourceRuntimeEntry 130  }
   
   
   jdbcDataSourceRuntimeWaitSecondsHighCount OBJECT-TYPE
      SYNTAX      INTEGER
      MAX-ACCESS  read-only
      STATUS      current
      DESCRIPTION "Returns the longest connection reserve wait time in seconds."
      ::= { jdbcDataSourceRuntimeEntry 135  }
   
   
   jdbcDataSourceRuntimeConnectionsTotalCount OBJECT-TYPE
      SYNTAX      INTEGER
      MAX-ACCESS  read-only
      STATUS      current
      DESCRIPTION "Returns the cumulative total number of database connections created in this data source since the data source was deployed."
      ::= { jdbcDataSourceRuntimeEntry 140  }
   
   
   jdbcDataSourceRuntimeCurrCapacity OBJECT-TYPE
      SYNTAX      INTEGER
      MAX-ACCESS  read-only
      STATUS      current
      DESCRIPTION "Returns the current count of JDBC connections in the connection pool in the data source."
      ::= { jdbcDataSourceRuntimeEntry 145  }
   
   
   jdbcDataSourceRuntimeCurrCapacityHighCount OBJECT-TYPE
      SYNTAX      INTEGER
      MAX-ACCESS  read-only
      STATUS      current
      DESCRIPTION "Returns the Highest number of database connections available or in use (current capacity) in this instance of the
      data source since the data source was deployed.."
      ::= { jdbcDataSourceRuntimeEntry 150  }
   
   
   jdbcDataSourceRuntimeNumAvailable OBJECT-TYPE
      SYNTAX      INTEGER
      MAX-ACCESS  read-only
      STATUS      current
      DESCRIPTION "Returns the number of database connections currently available (not in use) in this data source."
      ::= { jdbcDataSourceRuntimeEntry 155  }
   
   
   jdbcDataSourceRuntimeHighestNumAvailable OBJECT-TYPE
      SYNTAX      INTEGER
      MAX-ACCESS  read-only
      STATUS      current
      DESCRIPTION "Returns the Highest number of database connections that were available at any time in this instance of the data
      source since the data source was deployed."
      ::= { jdbcDataSourceRuntimeEntry 160  }
   
   
   jdbcDataSourceRuntimeNumUnavailable OBJECT-TYPE
      SYNTAX      INTEGER
      MAX-ACCESS  read-only
      STATUS      current
      DESCRIPTION "Returns the The number of database connections that are currently unavailable (in use or being tested by the system)
      in this instance of the data source."
      ::= { jdbcDataSourceRuntimeEntry 165  }
   
   
   jdbcDataSourceRuntimeHighestNumUnavailable OBJECT-TYPE
      SYNTAX      INTEGER
      MAX-ACCESS  read-only
      STATUS      current
      DESCRIPTION "Returns the Highest number of database connections that were unavailable (in use or being tested by the system)
      in this instance of the data source since the data source was deployed."
      ::= { jdbcDataSourceRuntimeEntry 170  }
   
   
   jdbcDataSourceRuntimeModuleId OBJECT-TYPE
      SYNTAX      OCTET STRING
      MAX-ACCESS  read-only
      STATUS      current
      DESCRIPTION "Returns the identifier for this Component.  The identifier is unique within the application.  Typical modules will use the URI for their id.  Web Modules will return their context-root since the web-uri may not be unique within an EAR."
      ::= { jdbcDataSourceRuntimeEntry 171  }
   
   
   jdbcDataSourceRuntimeDeploymentState OBJECT-TYPE
      SYNTAX      INTEGER
      MAX-ACCESS  read-only
      STATUS      current
      DESCRIPTION "The current deployment state of the module."
      ::= { jdbcDataSourceRuntimeEntry 172  }
   
   
   jmsConnectionRuntimeTable OBJECT-TYPE
      SYNTAX      SEQUENCE OF JmsConnectionRuntimeEntry
      MAX-ACCESS  not-accessible
      STATUS      current
      DESCRIPTION "This table is used for monitoring a WebLogic JMS Connection"
      ::= { wls 200  }
      
   
   jmsConnectionRuntimeEntry OBJECT-TYPE
      SYNTAX      JmsConnectionRuntimeEntry
      MAX-ACCESS  not-accessible
      STATUS      current
      DESCRIPTION "Entry of jmsConnectionRuntimeTable"
      INDEX { jmsConnectionRuntimeIndex}
      ::= { jmsConnectionRuntimeTable 1 }
      
   JmsConnectionRuntimeEntry ::=
      SEQUENCE
      {
         jmsConnectionRuntimeIndex DisplayString (SIZE (1..16)),
         jmsConnectionRuntimeObjectName DisplayString (SIZE (1..256)),
         jmsConnectionRuntimeType DisplayString (SIZE (1..64)),
         jmsConnectionRuntimeName DisplayString (SIZE (1..64)),
         jmsConnectionRuntimeParent DisplayString (SIZE (1..256)),
         jmsConnectionRuntimeClientID DisplayString (SIZE (1..64)),
         jmsConnectionRuntimeSessions DisplayString (SIZE (1..2048)),
         jmsConnectionRuntimeSessionsCurrentCount Counter64,
         jmsConnectionRuntimeSessionsHighCount Counter64,
         jmsConnectionRuntimeSessionsTotalCount Counter64,
         jmsConnectionRuntimeHostAddress OCTET STRING
      }
      
   
   jmsConnectionRuntimeIndex OBJECT-TYPE
      SYNTAX      DisplayString (SIZE (1..16))
      MAX-ACCESS  read-only
      STATUS      current
      DESCRIPTION "Unique value directed from ObjectName which is used as table index"
      ::= { jmsConnectionRuntimeEntry 1  }
   
   
   jmsConnectionRuntimeObjectName OBJECT-TYPE
      SYNTAX      DisplayString (SIZE (1..256))
      MAX-ACCESS  read-only
      STATUS      current
      DESCRIPTION "JMX-standard MBean name"
      ::= { jmsConnectionRuntimeEntry 5  }
   
   
   jmsConnectionRuntimeType OBJECT-TYPE
      SYNTAX      DisplayString (SIZE (1..64))
      MAX-ACCESS  read-only
      STATUS      current
      DESCRIPTION "BEA-proprietary MBean type"
      ::= { jmsConnectionRuntimeEntry 10  }
   
   
   jmsConnectionRuntimeName OBJECT-TYPE
      SYNTAX      DisplayString (SIZE (1..64))
      MAX-ACCESS  read-only
      STATUS      current
      DESCRIPTION "BEA-proprietary MBean name"
      ::= { jmsConnectionRuntimeEntry 15  }
   
   
   jmsConnectionRuntimeParent OBJECT-TYPE
      SYNTAX      DisplayString (SIZE (1..256))
      MAX-ACCESS  read-only
      STATUS      current
      DESCRIPTION "BEA-proprietary Parent object's identification, with syntax
      <type>:<name>"
      ::= { jmsConnectionRuntimeEntry 20  }
   
   
   jmsConnectionRuntimeClientID OBJECT-TYPE
      SYNTAX      DisplayString (SIZE (1..64))
      MAX-ACCESS  read-only
      STATUS      current
      DESCRIPTION "The clientID for this connection"
      ::= { jmsConnectionRuntimeEntry 25  }
   
   
   jmsConnectionRuntimeSessions OBJECT-TYPE
      SYNTAX      DisplayString (SIZE (1..2048))
      MAX-ACCESS  read-only
      STATUS      current
      DESCRIPTION "An array of sessions for this connection"
      ::= { jmsConnectionRuntimeEntry 30  }
   
   
   jmsConnectionRuntimeSessionsCurrentCount OBJECT-TYPE
      SYNTAX      Counter64
      MAX-ACCESS  read-only
      STATUS      current
      DESCRIPTION "The current number of sessions for this connection"
      ::= { jmsConnectionRuntimeEntry 35  }
   
   
   jmsConnectionRuntimeSessionsHighCount OBJECT-TYPE
      SYNTAX      Counter64
      MAX-ACCESS  read-only
      STATUS      current
      DESCRIPTION "The peak number of sessions for this connection
      since the last reset"
      ::= { jmsConnectionRuntimeEntry 40  }
   
   
   jmsConnectionRuntimeSessionsTotalCount OBJECT-TYPE
      SYNTAX      Counter64
      MAX-ACCESS  read-only
      STATUS      current
      DESCRIPTION "The number of sessions on this connection
      since the last reset"
      ::= { jmsConnectionRuntimeEntry 45  }
   
   
   jmsConnectionRuntimeHostAddress OBJECT-TYPE
      SYNTAX      OCTET STRING
      MAX-ACCESS  read-only
      STATUS      current
      DESCRIPTION "The host address of the client JVM as a string."
      ::= { jmsConnectionRuntimeEntry 46  }
   
   
   jmsConsumerRuntimeTable OBJECT-TYPE
      SYNTAX      SEQUENCE OF JmsConsumerRuntimeEntry
      MAX-ACCESS  not-accessible
      STATUS      current
      DESCRIPTION "This table is used for monitoring a WebLogic JMS Consumer"
      ::= { wls 210  }
      
   
   jmsConsumerRuntimeEntry OBJECT-TYPE
      SYNTAX      JmsConsumerRuntimeEntry
      MAX-ACCESS  not-accessible
      STATUS      current
      DESCRIPTION "Entry of jmsConsumerRuntimeTable"
      INDEX { jmsConsumerRuntimeIndex}
      ::= { jmsConsumerRuntimeTable 1 }
      
   JmsConsumerRuntimeEntry ::=
      SEQUENCE
      {
         jmsConsumerRuntimeIndex DisplayString (SIZE (1..16)),
         jmsConsumerRuntimeObjectName DisplayString (SIZE (1..256)),
         jmsConsumerRuntimeType DisplayString (SIZE (1..64)),
         jmsConsumerRuntimeName DisplayString (SIZE (1..64)),
         jmsConsumerRuntimeParent DisplayString (SIZE (1..256)),
         jmsConsumerRuntimeMessagesPendingCount Counter64,
         jmsConsumerRuntimeMessagesReceivedCount Counter64,
         jmsConsumerRuntimeBytesPendingCount Counter64,
         jmsConsumerRuntimeBytesReceivedCount Counter64,
         jmsConsumerRuntimeDestinationName DisplayString (SIZE (1..256)),
         jmsConsumerRuntimeSelector DisplayString (SIZE (1..256)),
         jmsConsumerRuntimeDurable INTEGER
                     {
                        true(1),
                        false(2)
                     }
         ,
         jmsConsumerRuntimeActive INTEGER,
         jmsConsumerRuntimeMemberDestinationName OCTET STRING
      }
      
   
   jmsConsumerRuntimeIndex OBJECT-TYPE
      SYNTAX      DisplayString (SIZE (1..16))
      MAX-ACCESS  read-only
      STATUS      current
      DESCRIPTION "Unique value directed from ObjectName which is used as table index"
      ::= { jmsConsumerRuntimeEntry 1  }
   
   
   jmsConsumerRuntimeObjectName OBJECT-TYPE
      SYNTAX      DisplayString (SIZE (1..256))
      MAX-ACCESS  read-only
      STATUS      current
      DESCRIPTION "JMX-standard MBean name"
      ::= { jmsConsumerRuntimeEntry 5  }
   
   
   jmsConsumerRuntimeType OBJECT-TYPE
      SYNTAX      DisplayString (SIZE (1..64))
      MAX-ACCESS  read-only
      STATUS      current
      DESCRIPTION "BEA-proprietary MBean type"
      ::= { jmsConsumerRuntimeEntry 10  }
   
   
   jmsConsumerRuntimeName OBJECT-TYPE
      SYNTAX      DisplayString (SIZE (1..64))
      MAX-ACCESS  read-only
      STATUS      current
      DESCRIPTION "BEA-proprietary MBean name"
      ::= { jmsConsumerRuntimeEntry 15  }
   
   
   jmsConsumerRuntimeParent OBJECT-TYPE
      SYNTAX      DisplayString (SIZE (1..256))
      MAX-ACCESS  read-only
      STATUS      current
      DESCRIPTION "BEA-proprietary Parent object's identification, with syntax
      <type>:<name>"
      ::= { jmsConsumerRuntimeEntry 20  }
   
   
   jmsConsumerRuntimeMessagesPendingCount OBJECT-TYPE
      SYNTAX      Counter64
      MAX-ACCESS  read-only
      STATUS      current
      DESCRIPTION "The number of messages pending (uncommitted and
      and unacknowledged) by this consumer"
      ::= { jmsConsumerRuntimeEntry 25  }
   
   
   jmsConsumerRuntimeMessagesReceivedCount OBJECT-TYPE
      SYNTAX      Counter64
      MAX-ACCESS  read-only
      STATUS      current
      DESCRIPTION "The number of messages received by this consumer
      since the last reset"
      ::= { jmsConsumerRuntimeEntry 30  }
   
   
   jmsConsumerRuntimeBytesPendingCount OBJECT-TYPE
      SYNTAX      Counter64
      MAX-ACCESS  read-only
      STATUS      current
      DESCRIPTION "The number of bytes pending (uncommitted and
      and unacknowledged) by this consumer"
      ::= { jmsConsumerRuntimeEntry 35  }
   
   
   jmsConsumerRuntimeBytesReceivedCount OBJECT-TYPE
      SYNTAX      Counter64
      MAX-ACCESS  read-only
      STATUS      current
      DESCRIPTION "The number of bytes received by this consumer
      since the last reset"
      ::= { jmsConsumerRuntimeEntry 40  }
   
   
   jmsConsumerRuntimeDestinationName OBJECT-TYPE
      SYNTAX      DisplayString (SIZE (1..256))
      MAX-ACCESS  read-only
      STATUS      current
      DESCRIPTION "The destination for this consumer."
      ::= { jmsConsumerRuntimeEntry 45  }
   
   
   jmsConsumerRuntimeSelector OBJECT-TYPE
      SYNTAX      DisplayString (SIZE (1..256))
      MAX-ACCESS  read-only
      STATUS      current
      DESCRIPTION "The consumer selector."
      ::= { jmsConsumerRuntimeEntry 50  }
   
   
   jmsConsumerRuntimeDurable OBJECT-TYPE
      SYNTAX      INTEGER
                  {
                     true(1),
                     false(2)
                  }
      
      MAX-ACCESS  read-only
      STATUS      current
      DESCRIPTION "A boolean value (true Or false). Is the consumer durable."
      ::= { jmsConsumerRuntimeEntry 55  }
   
   
   jmsConsumerRuntimeActive OBJECT-TYPE
      SYNTAX      INTEGER
      MAX-ACCESS  read-only
      STATUS      current
      DESCRIPTION "Determines if the consumer active."
      ::= { jmsConsumerRuntimeEntry 56  }
   
   
   jmsConsumerRuntimeMemberDestinationName OBJECT-TYPE
      SYNTAX      OCTET STRING
      MAX-ACCESS  read-only
      STATUS      current
      DESCRIPTION "Returns the name of the destination for this consumer. In case of a distributed destination, it will be the name of the member destination."
      ::= { jmsConsumerRuntimeEntry 57  }
   
   
   jmsDestinationRuntimeTable OBJECT-TYPE
      SYNTAX      SEQUENCE OF JmsDestinationRuntimeEntry
      MAX-ACCESS  not-accessible
      STATUS      current
      DESCRIPTION "This table is used for monitoring a WebLogic JMS Destination"
      ::= { wls 220  }
      
   
   jmsDestinationRuntimeEntry OBJECT-TYPE
      SYNTAX      JmsDestinationRuntimeEntry
      MAX-ACCESS  not-accessible
      STATUS      current
      DESCRIPTION "Entry of jmsDestinationRuntimeTable"
      INDEX { jmsDestinationRuntimeIndex}
      ::= { jmsDestinationRuntimeTable 1 }
      
   JmsDestinationRuntimeEntry ::=
      SEQUENCE
      {
         jmsDestinationRuntimeIndex DisplayString (SIZE (1..16)),
         jmsDestinationRuntimeObjectName DisplayString (SIZE (1..256)),
         jmsDestinationRuntimeType DisplayString (SIZE (1..64)),
         jmsDestinationRuntimeName DisplayString (SIZE (1..64)),
         jmsDestinationRuntimeParent DisplayString (SIZE (1..256)),
         jmsDestinationRuntimeConsumersCurrentCount Counter64,
         jmsDestinationRuntimeConsumersHighCount Counter64,
         jmsDestinationRuntimeConsumersTotalCount Counter64,
         jmsDestinationRuntimeMessagesCurrentCount Counter64,
         jmsDestinationRuntimeMessagesPendingCount Counter64,
         jmsDestinationRuntimeMessagesHighCount Counter64,
         jmsDestinationRuntimeMessagesReceivedCount Counter64,
         jmsDestinationRuntimeMessagesThresholdTime Counter64,
         jmsDestinationRuntimeBytesCurrentCount Counter64,
         jmsDestinationRuntimeBytesPendingCount Counter64,
         jmsDestinationRuntimeBytesHighCount Counter64,
         jmsDestinationRuntimeBytesReceivedCount Counter64,
         jmsDestinationRuntimeBytesThresholdTime Counter64,
         jmsDestinationRuntimeDurableSubscribers DisplayString (SIZE (1..2048)),
         jmsDestinationRuntimeProductionPaused OCTET STRING,
         jmsDestinationRuntimeInsertionPaused OCTET STRING,
         jmsDestinationRuntimeConsumptionPausedState OCTET STRING,
         jmsDestinationRuntimeConsumptionPaused OCTET STRING,
         jmsDestinationRuntimeState OCTET STRING,
         jmsDestinationRuntimeInsertionPausedState OCTET STRING,
         jmsDestinationRuntimeDestinationType OCTET STRING,
         jmsDestinationRuntimeProductionPausedState OCTET STRING
      }
      
   
   jmsDestinationRuntimeIndex OBJECT-TYPE
      SYNTAX      DisplayString (SIZE (1..16))
      MAX-ACCESS  read-only
      STATUS      current
      DESCRIPTION "Unique value directed from ObjectName which is used as table index"
      ::= { jmsDestinationRuntimeEntry 1  }
   
   
   jmsDestinationRuntimeObjectName OBJECT-TYPE
      SYNTAX      DisplayString (SIZE (1..256))
      MAX-ACCESS  read-only
      STATUS      current
      DESCRIPTION "JMX-standard MBean name"
      ::= { jmsDestinationRuntimeEntry 5  }
   
   
   jmsDestinationRuntimeType OBJECT-TYPE
      SYNTAX      DisplayString (SIZE (1..64))
      MAX-ACCESS  read-only
      STATUS      current
      DESCRIPTION "BEA-proprietary MBean type"
      ::= { jmsDestinationRuntimeEntry 10  }
   
   
   jmsDestinationRuntimeName OBJECT-TYPE
      SYNTAX      DisplayString (SIZE (1..64))
      MAX-ACCESS  read-only
      STATUS      current
      DESCRIPTION "BEA-proprietary MBean name"
      ::= { jmsDestinationRuntimeEntry 15  }
   
   
   jmsDestinationRuntimeParent OBJECT-TYPE
      SYNTAX      DisplayString (SIZE (1..256))
      MAX-ACCESS  read-only
      STATUS      current
      DESCRIPTION "BEA-proprietary Parent object's identification, with syntax
      <type>:<name>"
      ::= { jmsDestinationRuntimeEntry 20  }
   
   
   jmsDestinationRuntimeConsumersCurrentCount OBJECT-TYPE
      SYNTAX      Counter64
      MAX-ACCESS  read-only
      STATUS      current
      DESCRIPTION "The current number of consumers accessing this destination"
      ::= { jmsDestinationRuntimeEntry 25  }
   
   
   jmsDestinationRuntimeConsumersHighCount OBJECT-TYPE
      SYNTAX      Counter64
      MAX-ACCESS  read-only
      STATUS      current
      DESCRIPTION "The peak number of consumers accessing this destination
      since the last reset"
      ::= { jmsDestinationRuntimeEntry 30  }
   
   
   jmsDestinationRuntimeConsumersTotalCount OBJECT-TYPE
      SYNTAX      Counter64
      MAX-ACCESS  read-only
      STATUS      current
      DESCRIPTION "The total number of consumers accessing this destination
      since the last reset"
      ::= { jmsDestinationRuntimeEntry 35  }
   
   
   jmsDestinationRuntimeMessagesCurrentCount OBJECT-TYPE
      SYNTAX      Counter64
      MAX-ACCESS  read-only
      STATUS      current
      DESCRIPTION "The current number of messages in the destination.  This
      does not include the pending messages."
      ::= { jmsDestinationRuntimeEntry 40  }
   
   
   jmsDestinationRuntimeMessagesPendingCount OBJECT-TYPE
      SYNTAX      Counter64
      MAX-ACCESS  read-only
      STATUS      current
      DESCRIPTION "The number of pending messages in the destination
      Pending messages are over and above the current number of messages."
      ::= { jmsDestinationRuntimeEntry 45  }
   
   
   jmsDestinationRuntimeMessagesHighCount OBJECT-TYPE
      SYNTAX      Counter64
      MAX-ACCESS  read-only
      STATUS      current
      DESCRIPTION "The peak number of messages in the destination
      since the last reset"
      ::= { jmsDestinationRuntimeEntry 50  }
   
   
   jmsDestinationRuntimeMessagesReceivedCount OBJECT-TYPE
      SYNTAX      Counter64
      MAX-ACCESS  read-only
      STATUS      current
      DESCRIPTION "The number of messages received in this destination
      since that reset"
      ::= { jmsDestinationRuntimeEntry 55  }
   
   
   jmsDestinationRuntimeMessagesThresholdTime OBJECT-TYPE
      SYNTAX      Counter64
      MAX-ACCESS  read-only
      STATUS      current
      DESCRIPTION "The amount of time in the threshold condition
      since the last reset"
      ::= { jmsDestinationRuntimeEntry 60  }
   
   
   jmsDestinationRuntimeBytesCurrentCount OBJECT-TYPE
      SYNTAX      Counter64
      MAX-ACCESS  read-only
      STATUS      current
      DESCRIPTION "The current number of bytes stored in the destination.
      This does not include the pending bytes."
      ::= { jmsDestinationRuntimeEntry 65  }
   
   
   jmsDestinationRuntimeBytesPendingCount OBJECT-TYPE
      SYNTAX      Counter64
      MAX-ACCESS  read-only
      STATUS      current
      DESCRIPTION "The number of pending bytes stored in the destination.
      Pending bytes are over and above the current number of bytes."
      ::= { jmsDestinationRuntimeEntry 70  }
   
   
   jmsDestinationRuntimeBytesHighCount OBJECT-TYPE
      SYNTAX      Counter64
      MAX-ACCESS  read-only
      STATUS      current
      DESCRIPTION "The peak number of bytes stored in the destination
      since the last reset"
      ::= { jmsDestinationRuntimeEntry 75  }
   
   
   jmsDestinationRuntimeBytesReceivedCount OBJECT-TYPE
      SYNTAX      Counter64
      MAX-ACCESS  read-only
      STATUS      current
      DESCRIPTION "The number of bytes received in this destination
      since the last reset"
      ::= { jmsDestinationRuntimeEntry 80  }
   
   
   jmsDestinationRuntimeBytesThresholdTime OBJECT-TYPE
      SYNTAX      Counter64
      MAX-ACCESS  read-only
      STATUS      current
      DESCRIPTION "The amount of time in the threshold condition
      since the last reset"
      ::= { jmsDestinationRuntimeEntry 85  }
   
   
   jmsDestinationRuntimeDurableSubscribers OBJECT-TYPE
      SYNTAX      DisplayString (SIZE (1..2048))
      MAX-ACCESS  read-only
      STATUS      current
      DESCRIPTION "An array of durable subscriber runtime mbean for this destination."
      ::= { jmsDestinationRuntimeEntry 90  }
   
   
   jmsDestinationRuntimeProductionPaused OBJECT-TYPE
      SYNTAX      OCTET STRING
      MAX-ACCESS  read-only
      STATUS      current
      DESCRIPTION "Indicates the ProductionPause state of the destination."
      ::= { jmsDestinationRuntimeEntry 91  }
   
   
   jmsDestinationRuntimeInsertionPaused OBJECT-TYPE
      SYNTAX      OCTET STRING
      MAX-ACCESS  read-only
      STATUS      current
      DESCRIPTION "Indicates the InsertionPause state of the destination."
      ::= { jmsDestinationRuntimeEntry 92  }
   
   
   jmsDestinationRuntimeConsumptionPausedState OBJECT-TYPE
      SYNTAX      OCTET STRING
      MAX-ACCESS  read-only
      STATUS      current
      DESCRIPTION "The current consumption pause state of the destination."
      ::= { jmsDestinationRuntimeEntry 93  }
   
   
   jmsDestinationRuntimeConsumptionPaused OBJECT-TYPE
      SYNTAX      OCTET STRING
      MAX-ACCESS  read-only
      STATUS      current
      DESCRIPTION "Indicates the consumption Pause state of the destination."
      ::= { jmsDestinationRuntimeEntry 94  }
   
   
   jmsDestinationRuntimeState OBJECT-TYPE
      SYNTAX      OCTET STRING
      MAX-ACCESS  read-only
      STATUS      current
      DESCRIPTION "The operational state of the destination as a String."
      ::= { jmsDestinationRuntimeEntry 95  }
   
   
   jmsDestinationRuntimeInsertionPausedState OBJECT-TYPE
      SYNTAX      OCTET STRING
      MAX-ACCESS  read-only
      STATUS      current
      DESCRIPTION "The current insertion pause state of the destination."
      ::= { jmsDestinationRuntimeEntry 96  }
   
   
   jmsDestinationRuntimeDestinationType OBJECT-TYPE
      SYNTAX      OCTET STRING
      MAX-ACCESS  read-only
      STATUS      current
      DESCRIPTION "The destination type, either weblogic.management.configuration.JMSConstants.DESTINATION_TYPE_QUEUE or weblogic.management.configuration.JMSConstants.DESTINATION_TYPE_TOPIC depending upon whether the destination is a queue or topic."
      ::= { jmsDestinationRuntimeEntry 97  }
   
   
   jmsDestinationRuntimeProductionPausedState OBJECT-TYPE
      SYNTAX      OCTET STRING
      MAX-ACCESS  read-only
      STATUS      current
      DESCRIPTION "The current production pause state of the destination."
      ::= { jmsDestinationRuntimeEntry 98  }
   
   
   jmsProducerRuntimeTable OBJECT-TYPE
      SYNTAX      SEQUENCE OF JmsProducerRuntimeEntry
      MAX-ACCESS  not-accessible
      STATUS      current
      DESCRIPTION "This table is used for monitoring a WebLogic JMS Producer"
      ::= { wls 230  }
      
   
   jmsProducerRuntimeEntry OBJECT-TYPE
      SYNTAX      JmsProducerRuntimeEntry
      MAX-ACCESS  not-accessible
      STATUS      current
      DESCRIPTION "Entry of jmsProducerRuntimeTable"
      INDEX { jmsProducerRuntimeIndex}
      ::= { jmsProducerRuntimeTable 1 }
      
   JmsProducerRuntimeEntry ::=
      SEQUENCE
      {
         jmsProducerRuntimeIndex DisplayString (SIZE (1..16)),
         jmsProducerRuntimeObjectName DisplayString (SIZE (1..256)),
         jmsProducerRuntimeType DisplayString (SIZE (1..64)),
         jmsProducerRuntimeName DisplayString (SIZE (1..64)),
         jmsProducerRuntimeParent DisplayString (SIZE (1..256)),
         jmsProducerRuntimeMessagesPendingCount Counter64,
         jmsProducerRuntimeMessagesSentCount Counter64,
         jmsProducerRuntimeBytesPendingCount Counter64,
         jmsProducerRuntimeBytesSentCount Counter64
      }
      
   
   jmsProducerRuntimeIndex OBJECT-TYPE
      SYNTAX      DisplayString (SIZE (1..16))
      MAX-ACCESS  read-only
      STATUS      current
      DESCRIPTION "Unique value directed from ObjectName which is used as table index"
      ::= { jmsProducerRuntimeEntry 1  }
   
   
   jmsProducerRuntimeObjectName OBJECT-TYPE
      SYNTAX      DisplayString (SIZE (1..256))
      MAX-ACCESS  read-only
      STATUS      current
      DESCRIPTION "JMX-standard MBean name"
      ::= { jmsProducerRuntimeEntry 5  }
   
   
   jmsProducerRuntimeType OBJECT-TYPE
      SYNTAX      DisplayString (SIZE (1..64))
      MAX-ACCESS  read-only
      STATUS      current
      DESCRIPTION "BEA-proprietary MBean type"
      ::= { jmsProducerRuntimeEntry 10  }
   
   
   jmsProducerRuntimeName OBJECT-TYPE
      SYNTAX      DisplayString (SIZE (1..64))
      MAX-ACCESS  read-only
      STATUS      current
      DESCRIPTION "BEA-proprietary MBean name"
      ::= { jmsProducerRuntimeEntry 15  }
   
   
   jmsProducerRuntimeParent OBJECT-TYPE
      SYNTAX      DisplayString (SIZE (1..256))
      MAX-ACCESS  read-only
      STATUS      current
      DESCRIPTION "BEA-proprietary Parent object's identification, with syntax
      <type>:<name>"
      ::= { jmsProducerRuntimeEntry 20  }
   
   
   jmsProducerRuntimeMessagesPendingCount OBJECT-TYPE
      SYNTAX      Counter64
      MAX-ACCESS  read-only
      STATUS      current
      DESCRIPTION "The number of messages pending (uncommitted and
      and unacknowledged) by this producer"
      ::= { jmsProducerRuntimeEntry 25  }
   
   
   jmsProducerRuntimeMessagesSentCount OBJECT-TYPE
      SYNTAX      Counter64
      MAX-ACCESS  read-only
      STATUS      current
      DESCRIPTION "The number of messages sent by this producer
      since the last reset"
      ::= { jmsProducerRuntimeEntry 30  }
   
   
   jmsProducerRuntimeBytesPendingCount OBJECT-TYPE
      SYNTAX      Counter64
      MAX-ACCESS  read-only
      STATUS      current
      DESCRIPTION "The number of bytes pending (uncommitted and
      and unacknowledged) by this producer"
      ::= { jmsProducerRuntimeEntry 35  }
   
   
   jmsProducerRuntimeBytesSentCount OBJECT-TYPE
      SYNTAX      Counter64
      MAX-ACCESS  read-only
      STATUS      current
      DESCRIPTION "The number of bytes sent by this producer
      since the last reset"
      ::= { jmsProducerRuntimeEntry 40  }
   
   
   jmsPooledConnectionRuntimeTable OBJECT-TYPE
      SYNTAX      SEQUENCE OF JmsPooledConnectionRuntimeEntry
      MAX-ACCESS  not-accessible
      STATUS      current
      DESCRIPTION "This table is used for monitoring a WebLogic JMS Producer"
      ::= { wls 231  }
      
   
   jmsPooledConnectionRuntimeEntry OBJECT-TYPE
      SYNTAX      JmsPooledConnectionRuntimeEntry
      MAX-ACCESS  not-accessible
      STATUS      current
      DESCRIPTION "Entry of jmsPooledConnectionRuntimeTable"
      INDEX { jmsPooledConnectionRuntimeIndex}
      ::= { jmsPooledConnectionRuntimeTable 1 }
      
   JmsPooledConnectionRuntimeEntry ::=
      SEQUENCE
      {
         jmsPooledConnectionRuntimeIndex DisplayString (SIZE (1..16)),
         jmsPooledConnectionRuntimeObjectName DisplayString (SIZE (1..256)),
         jmsPooledConnectionRuntimeType DisplayString (SIZE (1..64)),
         jmsPooledConnectionRuntimeName DisplayString (SIZE (1..64)),
         jmsPooledConnectionRuntimeParent DisplayString (SIZE (1..256)),
         jmsPooledConnectionRuntimeAverageReserved INTEGER,
         jmsPooledConnectionRuntimeCreationDelayTime INTEGER,
         jmsPooledConnectionRuntimeCurrCapacity INTEGER,
         jmsPooledConnectionRuntimeHighestNumAvailable INTEGER,
         jmsPooledConnectionRuntimeHighestNumReserved INTEGER,
         jmsPooledConnectionRuntimeNumAvailable INTEGER,
         jmsPooledConnectionRuntimeHighestNumWaiters Counter32,
         jmsPooledConnectionRuntimeHighestWaitSeconds INTEGER,
         jmsPooledConnectionRuntimeMaxCapacity INTEGER,
         jmsPooledConnectionRuntimeNumConnectionObjects INTEGER,
         jmsPooledConnectionRuntimeNumFailuresToRefresh INTEGER,
         jmsPooledConnectionRuntimeNumLeaked INTEGER,
         jmsPooledConnectionRuntimeNumReserved INTEGER,
         jmsPooledConnectionRuntimeNumUnavailable INTEGER,
         jmsPooledConnectionRuntimeNumWaiters INTEGER,
         jmsPooledConnectionRuntimeTotalNumAllocated INTEGER,
         jmsPooledConnectionRuntimeTotalNumDestroyed INTEGER,
         jmsPooledConnectionRuntimeHighestNumUnavailable INTEGER
      }
      
   
   jmsPooledConnectionRuntimeIndex OBJECT-TYPE
      SYNTAX      DisplayString (SIZE (1..16))
      MAX-ACCESS  read-only
      STATUS      current
      DESCRIPTION "Unique value directed from ObjectName which is used as table index"
      ::= { jmsPooledConnectionRuntimeEntry 1  }
   
   
   jmsPooledConnectionRuntimeObjectName OBJECT-TYPE
      SYNTAX      DisplayString (SIZE (1..256))
      MAX-ACCESS  read-only
      STATUS      current
      DESCRIPTION "JMX-standard MBean name"
      ::= { jmsPooledConnectionRuntimeEntry 5  }
   
   
   jmsPooledConnectionRuntimeType OBJECT-TYPE
      SYNTAX      DisplayString (SIZE (1..64))
      MAX-ACCESS  read-only
      STATUS      current
      DESCRIPTION "BEA-proprietary MBean type"
      ::= { jmsPooledConnectionRuntimeEntry 10  }
   
   
   jmsPooledConnectionRuntimeName OBJECT-TYPE
      SYNTAX      DisplayString (SIZE (1..64))
      MAX-ACCESS  read-only
      STATUS      current
      DESCRIPTION "BEA-proprietary MBean name"
      ::= { jmsPooledConnectionRuntimeEntry 15  }
   
   
   jmsPooledConnectionRuntimeParent OBJECT-TYPE
      SYNTAX      DisplayString (SIZE (1..256))
      MAX-ACCESS  read-only
      STATUS      current
      DESCRIPTION "BEA-proprietary Parent object's identification, with syntax
      <type>:<name>"
      ::= { jmsPooledConnectionRuntimeEntry 20  }
   
   
   jmsPooledConnectionRuntimeAverageReserved OBJECT-TYPE
      SYNTAX      INTEGER
      MAX-ACCESS  read-only
      STATUS      current
      DESCRIPTION "Gets the averageReserved attribute of the JMSPooledConnectionRuntimeMBean object"
      ::= { jmsPooledConnectionRuntimeEntry 21  }
   
   
   jmsPooledConnectionRuntimeCreationDelayTime OBJECT-TYPE
      SYNTAX      INTEGER
      MAX-ACCESS  read-only
      STATUS      current
      DESCRIPTION "Gets the creationDelayTime attribute of the JMSPooledConnectionRuntimeMBean object"
      ::= { jmsPooledConnectionRuntimeEntry 22  }
   
   
   jmsPooledConnectionRuntimeCurrCapacity OBJECT-TYPE
      SYNTAX      INTEGER
      MAX-ACCESS  read-only
      STATUS      current
      DESCRIPTION "Gets the currCapacity attribute of the JMSPooledConnectionRuntimeMBean object"
      ::= { jmsPooledConnectionRuntimeEntry 23  }
   
   
   jmsPooledConnectionRuntimeHighestNumAvailable OBJECT-TYPE
      SYNTAX      INTEGER
      MAX-ACCESS  read-only
      STATUS      current
      DESCRIPTION "ets the highestNumAvailable attribute of the JMSPooledConnectionRuntimeMBean object"
      ::= { jmsPooledConnectionRuntimeEntry 24  }
   
   
   jmsPooledConnectionRuntimeHighestNumReserved OBJECT-TYPE
      SYNTAX      INTEGER
      MAX-ACCESS  read-only
      STATUS      current
      DESCRIPTION "The highestNumReserved value"
      ::= { jmsPooledConnectionRuntimeEntry 25  }
   
   
   jmsPooledConnectionRuntimeNumAvailable OBJECT-TYPE
      SYNTAX      INTEGER
      MAX-ACCESS  read-only
      STATUS      current
      DESCRIPTION "The numAvailable value"
      ::= { jmsPooledConnectionRuntimeEntry 26  }
   
   
   jmsPooledConnectionRuntimeHighestNumWaiters OBJECT-TYPE
      SYNTAX      Counter32
      MAX-ACCESS  read-only
      STATUS      current
      DESCRIPTION "he highestNumWaiters value"
      ::= { jmsPooledConnectionRuntimeEntry 27  }
   
   
   jmsPooledConnectionRuntimeHighestWaitSeconds OBJECT-TYPE
      SYNTAX      INTEGER
      MAX-ACCESS  read-only
      STATUS      current
      DESCRIPTION "The highestWaitSeconds value"
      ::= { jmsPooledConnectionRuntimeEntry 28  }
   
   
   jmsPooledConnectionRuntimeMaxCapacity OBJECT-TYPE
      SYNTAX      INTEGER
      MAX-ACCESS  read-only
      STATUS      current
      DESCRIPTION "Gets the maxCapacity attribute of the JMSPooledConnectionRuntimeMBean object"
      ::= { jmsPooledConnectionRuntimeEntry 29  }
   
   
   jmsPooledConnectionRuntimeNumConnectionObjects OBJECT-TYPE
      SYNTAX      INTEGER
      MAX-ACCESS  read-only
      STATUS      current
      DESCRIPTION "Gets the numConnectionObjects attribute of the JMSPooledConnectionRuntimeMBean object"
      ::= { jmsPooledConnectionRuntimeEntry 30  }
   
   
   jmsPooledConnectionRuntimeNumFailuresToRefresh OBJECT-TYPE
      SYNTAX      INTEGER
      MAX-ACCESS  read-only
      STATUS      current
      DESCRIPTION "The numFailuresToRefresh value"
      ::= { jmsPooledConnectionRuntimeEntry 31  }
   
   
   jmsPooledConnectionRuntimeNumLeaked OBJECT-TYPE
      SYNTAX      INTEGER
      MAX-ACCESS  read-only
      STATUS      current
      DESCRIPTION "The numFailuresToRefresh value"
      ::= { jmsPooledConnectionRuntimeEntry 32  }
   
   
   jmsPooledConnectionRuntimeNumReserved OBJECT-TYPE
      SYNTAX      INTEGER
      MAX-ACCESS  read-only
      STATUS      current
      DESCRIPTION "The numReserved value"
      ::= { jmsPooledConnectionRuntimeEntry 33  }
   
   
   jmsPooledConnectionRuntimeNumUnavailable OBJECT-TYPE
      SYNTAX      INTEGER
      MAX-ACCESS  read-only
      STATUS      current
      DESCRIPTION "The numUnavailable value"
      ::= { jmsPooledConnectionRuntimeEntry 34  }
   
   
   jmsPooledConnectionRuntimeNumWaiters OBJECT-TYPE
      SYNTAX      INTEGER
      MAX-ACCESS  read-only
      STATUS      current
      DESCRIPTION "The numWaiters value"
      ::= { jmsPooledConnectionRuntimeEntry 35  }
   
   
   jmsPooledConnectionRuntimeTotalNumAllocated OBJECT-TYPE
      SYNTAX      INTEGER
      MAX-ACCESS  read-only
      STATUS      current
      DESCRIPTION "The totalNumAllocated value"
      ::= { jmsPooledConnectionRuntimeEntry 36  }
   
   
   jmsPooledConnectionRuntimeTotalNumDestroyed OBJECT-TYPE
      SYNTAX      INTEGER
      MAX-ACCESS  read-only
      STATUS      current
      DESCRIPTION "The totalNumDestroyed value"
      ::= { jmsPooledConnectionRuntimeEntry 37  }
   
   
   jmsPooledConnectionRuntimeHighestNumUnavailable OBJECT-TYPE
      SYNTAX      INTEGER
      MAX-ACCESS  read-only
      STATUS      current
      DESCRIPTION "The highest number of unusable JMS sessions in this instance of the session pool since it was instantiated."
      ::= { jmsPooledConnectionRuntimeEntry 38  }
   
   
   jmsRuntimeTable OBJECT-TYPE
      SYNTAX      SEQUENCE OF JmsRuntimeEntry
      MAX-ACCESS  not-accessible
      STATUS      current
      DESCRIPTION "This table is used for monitoring a WebLogic JMS Service."
      ::= { wls 240  }
      
   
   jmsRuntimeEntry OBJECT-TYPE
      SYNTAX      JmsRuntimeEntry
      MAX-ACCESS  not-accessible
      STATUS      current
      DESCRIPTION "Entry of jmsRuntimeTable"
      INDEX { jmsRuntimeIndex}
      ::= { jmsRuntimeTable 1 }
      
   JmsRuntimeEntry ::=
      SEQUENCE
      {
         jmsRuntimeIndex      DisplayString (SIZE (1..16)),
         jmsRuntimeObjectName DisplayString (SIZE (1..256)),
         jmsRuntimeType       DisplayString (SIZE (1..64)),
         jmsRuntimeName       DisplayString (SIZE (1..64)),
         jmsRuntimeParent     DisplayString (SIZE (1..256)),
         jmsRuntimeConnections DisplayString (SIZE (1..2048)),
         jmsRuntimeConnectionsCurrentCount Counter64,
         jmsRuntimeConnectionsHighCount Counter64,
         jmsRuntimeConnectionsTotalCount Counter64,
         jmsRuntimeJMSServers DisplayString (SIZE (1..2048)),
         jmsRuntimeJMSServersCurrentCount Counter64,
         jmsRuntimeJMSServersHighCount Counter64,
         jmsRuntimeJMSServersTotalCount Counter64
      }
      
   
   jmsRuntimeIndex OBJECT-TYPE
      SYNTAX      DisplayString (SIZE (1..16))
      MAX-ACCESS  read-only
      STATUS      current
      DESCRIPTION "Unique value directed from ObjectName which is used as table index"
      ::= { jmsRuntimeEntry 1  }
   
   
   jmsRuntimeObjectName OBJECT-TYPE
      SYNTAX      DisplayString (SIZE (1..256))
      MAX-ACCESS  read-only
      STATUS      current
      DESCRIPTION "JMX-standard MBean name"
      ::= { jmsRuntimeEntry 5  }
   
   
   jmsRuntimeType OBJECT-TYPE
      SYNTAX      DisplayString (SIZE (1..64))
      MAX-ACCESS  read-only
      STATUS      current
      DESCRIPTION "BEA-proprietary MBean type"
      ::= { jmsRuntimeEntry 10  }
   
   
   jmsRuntimeName OBJECT-TYPE
      SYNTAX      DisplayString (SIZE (1..64))
      MAX-ACCESS  read-only
      STATUS      current
      DESCRIPTION "BEA-proprietary MBean name"
      ::= { jmsRuntimeEntry 15  }
   
   
   jmsRuntimeParent OBJECT-TYPE
      SYNTAX      DisplayString (SIZE (1..256))
      MAX-ACCESS  read-only
      STATUS      current
      DESCRIPTION "BEA-proprietary Parent object's identification, with syntax
      <type>:<name>"
      ::= { jmsRuntimeEntry 20  }
   
   
   jmsRuntimeConnections OBJECT-TYPE
      SYNTAX      DisplayString (SIZE (1..2048))
      MAX-ACCESS  read-only
      STATUS      current
      DESCRIPTION "The connections to this JMS server"
      ::= { jmsRuntimeEntry 25  }
   
   
   jmsRuntimeConnectionsCurrentCount OBJECT-TYPE
      SYNTAX      Counter64
      MAX-ACCESS  read-only
      STATUS      current
      DESCRIPTION "The current number of connection to this JMS server"
      ::= { jmsRuntimeEntry 30  }
   
   
   jmsRuntimeConnectionsHighCount OBJECT-TYPE
      SYNTAX      Counter64
      MAX-ACCESS  read-only
      STATUS      current
      DESCRIPTION "The peak number of connections to this JMS server
      since the last reset"
      ::= { jmsRuntimeEntry 35  }
   
   
   jmsRuntimeConnectionsTotalCount OBJECT-TYPE
      SYNTAX      Counter64
      MAX-ACCESS  read-only
      STATUS      current
      DESCRIPTION "The total number of connections made to this JMS server
      since the last reset"
      ::= { jmsRuntimeEntry 40  }
   
   
   jmsRuntimeJMSServers OBJECT-TYPE
      SYNTAX      DisplayString (SIZE (1..2048))
      MAX-ACCESS  read-only
      STATUS      current
      DESCRIPTION "The JMSServers in the JMS service."
      ::= { jmsRuntimeEntry 45  }
   
   
   jmsRuntimeJMSServersCurrentCount OBJECT-TYPE
      SYNTAX      Counter64
      MAX-ACCESS  read-only
      STATUS      current
      DESCRIPTION "the current number of JMSServers connected to thi JMS Services"
      ::= { jmsRuntimeEntry 50  }
   
   
   jmsRuntimeJMSServersHighCount OBJECT-TYPE
      SYNTAX      Counter64
      MAX-ACCESS  read-only
      STATUS      current
      DESCRIPTION "The peak number of JMSServers connected to this JMSService 
      since the server is up"
      ::= { jmsRuntimeEntry 55  }
   
   
   jmsRuntimeJMSServersTotalCount OBJECT-TYPE
      SYNTAX      Counter64
      MAX-ACCESS  read-only
      STATUS      current
      DESCRIPTION "The number of JMSServers connections made to thisJMS Service 
      since the server is up"
      ::= { jmsRuntimeEntry 60  }
   
   
   jmsServerRuntimeTable OBJECT-TYPE
      SYNTAX      SEQUENCE OF JmsServerRuntimeEntry
      MAX-ACCESS  not-accessible
      STATUS      current
      DESCRIPTION "This table is used for monitoring a WebLogic JMS Server"
      ::= { wls 250  }
      
   
   jmsServerRuntimeEntry OBJECT-TYPE
      SYNTAX      JmsServerRuntimeEntry
      MAX-ACCESS  not-accessible
      STATUS      current
      DESCRIPTION "Entry of jmsServerRuntimeTable"
      INDEX { jmsServerRuntimeIndex}
      ::= { jmsServerRuntimeTable 1 }
      
   JmsServerRuntimeEntry ::=
      SEQUENCE
      {
         jmsServerRuntimeIndex DisplayString (SIZE (1..16)),
         jmsServerRuntimeObjectName DisplayString (SIZE (1..256)),
         jmsServerRuntimeType DisplayString (SIZE (1..64)),
         jmsServerRuntimeName DisplayString (SIZE (1..64)),
         jmsServerRuntimeParent DisplayString (SIZE (1..256)),
         jmsServerRuntimeSessionPoolRuntimes DisplayString (SIZE (1..2048)),
         jmsServerRuntimeSessionPoolsCurrentCount Counter64,
         jmsServerRuntimeSessionPoolsHighCount Counter64,
         jmsServerRuntimeSessionPoolsTotalCount Counter64,
         jmsServerRuntimeDestinations DisplayString (SIZE (1..2048)),
         jmsServerRuntimeDestinationsCurrentCount Counter64,
         jmsServerRuntimeDestinationsHighCount Counter64,
         jmsServerRuntimeDestinationsTotalCount Counter64,
         jmsServerRuntimeMessagesCurrentCount Counter64,
         jmsServerRuntimeMessagesPendingCount Counter64,
         jmsServerRuntimeMessagesHighCount Counter64,
         jmsServerRuntimeMessagesReceivedCount Counter64,
         jmsServerRuntimeMessagesThresholdTime Counter64,
         jmsServerRuntimeBytesCurrentCount Counter64,
         jmsServerRuntimeBytesPendingCount Counter64,
         jmsServerRuntimeBytesHighCount Counter64,
         jmsServerRuntimeBytesReceivedCount Counter64,
         jmsServerRuntimeBytesThresholdTime Counter64,
         jmsServerRuntimeMessagesPagedInTotalCount INTEGER,
         jmsServerRuntimeProductionPaused OCTET STRING,
         jmsServerRuntimeInsertionPaused OCTET STRING,
         jmsServerRuntimeConsumptionPausedState OCTET STRING,
         jmsServerRuntimeConsumptionPaused OCTET STRING,
         jmsServerRuntimeBytesPageableCurrentCount Counter64,
         jmsServerRuntimeMessagesPagedOutTotalCount INTEGER,
         jmsServerRuntimeInsertionPausedState OCTET STRING,
         jmsServerRuntimeMessagesPageableCurrentCount INTEGER,
         jmsServerRuntimeProductionPausedState OCTET STRING,
         jmsServerRuntimeBytesPagedOutTotalCount Counter64,
         jmsServerRuntimeBytesPagedInTotalCount Counter64
      }
      
   
   jmsServerRuntimeIndex OBJECT-TYPE
      SYNTAX      DisplayString (SIZE (1..16))
      MAX-ACCESS  read-only
      STATUS      current
      DESCRIPTION "Unique value directed from ObjectName which is used as table index"
      ::= { jmsServerRuntimeEntry 1  }
   
   
   jmsServerRuntimeObjectName OBJECT-TYPE
      SYNTAX      DisplayString (SIZE (1..256))
      MAX-ACCESS  read-only
      STATUS      current
      DESCRIPTION "JMX-standard MBean name"
      ::= { jmsServerRuntimeEntry 5  }
   
   
   jmsServerRuntimeType OBJECT-TYPE
      SYNTAX      DisplayString (SIZE (1..64))
      MAX-ACCESS  read-only
      STATUS      current
      DESCRIPTION "BEA-proprietary MBean type"
      ::= { jmsServerRuntimeEntry 10  }
   
   
   jmsServerRuntimeName OBJECT-TYPE
      SYNTAX      DisplayString (SIZE (1..64))
      MAX-ACCESS  read-only
      STATUS      current
      DESCRIPTION "BEA-proprietary MBean name"
      ::= { jmsServerRuntimeEntry 15  }
   
   
   jmsServerRuntimeParent OBJECT-TYPE
      SYNTAX      DisplayString (SIZE (1..256))
      MAX-ACCESS  read-only
      STATUS      current
      DESCRIPTION "BEA-proprietary Parent object's identification, with syntax
      <type>:<name>"
      ::= { jmsServerRuntimeEntry 20  }
   
   
   jmsServerRuntimeSessionPoolRuntimes OBJECT-TYPE
      SYNTAX      DisplayString (SIZE (1..2048))
      MAX-ACCESS  read-only
      STATUS      current
      DESCRIPTION "The session pools on this JMS Server"
      ::= { jmsServerRuntimeEntry 25  }
   
   
   jmsServerRuntimeSessionPoolsCurrentCount OBJECT-TYPE
      SYNTAX      Counter64
      MAX-ACCESS  read-only
      STATUS      current
      DESCRIPTION "The current number of session pools running on this JMS Server"
      ::= { jmsServerRuntimeEntry 30  }
   
   
   jmsServerRuntimeSessionPoolsHighCount OBJECT-TYPE
      SYNTAX      Counter64
      MAX-ACCESS  read-only
      STATUS      current
      DESCRIPTION "The peak number of session pools on this JMS Server
      since the last reset"
      ::= { jmsServerRuntimeEntry 35  }
   
   
   jmsServerRuntimeSessionPoolsTotalCount OBJECT-TYPE
      SYNTAX      Counter64
      MAX-ACCESS  read-only
      STATUS      current
      DESCRIPTION "The number of session pools instantiated on this JMS Server
      since the last reset"
      ::= { jmsServerRuntimeEntry 40  }
   
   
   jmsServerRuntimeDestinations OBJECT-TYPE
      SYNTAX      DisplayString (SIZE (1..2048))
      MAX-ACCESS  read-only
      STATUS      current
      DESCRIPTION "An array of destinations on this JMS server"
      ::= { jmsServerRuntimeEntry 45  }
   
   
   jmsServerRuntimeDestinationsCurrentCount OBJECT-TYPE
      SYNTAX      Counter64
      MAX-ACCESS  read-only
      STATUS      current
      DESCRIPTION "The current number of destinations for this JMS server"
      ::= { jmsServerRuntimeEntry 50  }
   
   
   jmsServerRuntimeDestinationsHighCount OBJECT-TYPE
      SYNTAX      Counter64
      MAX-ACCESS  read-only
      STATUS      current
      DESCRIPTION "The peak number of destinations on this JMS server
      since the last reset"
      ::= { jmsServerRuntimeEntry 55  }
   
   
   jmsServerRuntimeDestinationsTotalCount OBJECT-TYPE
      SYNTAX      Counter64
      MAX-ACCESS  read-only
      STATUS      current
      DESCRIPTION "The number of destinations instantiated on this JMS server
      since the last reset"
      ::= { jmsServerRuntimeEntry 60  }
   
   
   jmsServerRuntimeMessagesCurrentCount OBJECT-TYPE
      SYNTAX      Counter64
      MAX-ACCESS  read-only
      STATUS      current
      DESCRIPTION "The current number of messages stored on this JMS server.
      This does not include the pending messages."
      ::= { jmsServerRuntimeEntry 65  }
   
   
   jmsServerRuntimeMessagesPendingCount OBJECT-TYPE
      SYNTAX      Counter64
      MAX-ACCESS  read-only
      STATUS      current
      DESCRIPTION "The current number of messages pending (unacknowledged or uncommitted) stored on this JMS server. 
      Pending messages are over and above the current number of messages."
      ::= { jmsServerRuntimeEntry 70  }
   
   
   jmsServerRuntimeMessagesHighCount OBJECT-TYPE
      SYNTAX      Counter64
      MAX-ACCESS  read-only
      STATUS      current
      DESCRIPTION "The peak number of messages stored in 
      the JMS server since the last reset."
      ::= { jmsServerRuntimeEntry 75  }
   
   
   jmsServerRuntimeMessagesReceivedCount OBJECT-TYPE
      SYNTAX      Counter64
      MAX-ACCESS  read-only
      STATUS      current
      DESCRIPTION "The number of messages received on this 
      JMS Server since the last reset."
      ::= { jmsServerRuntimeEntry 80  }
   
   
   jmsServerRuntimeMessagesThresholdTime OBJECT-TYPE
      SYNTAX      Counter64
      MAX-ACCESS  read-only
      STATUS      current
      DESCRIPTION "The amount of time in the threshold condition
      since the last reset."
      ::= { jmsServerRuntimeEntry 85  }
   
   
   jmsServerRuntimeBytesCurrentCount OBJECT-TYPE
      SYNTAX      Counter64
      MAX-ACCESS  read-only
      STATUS      current
      DESCRIPTION "The current number of bytes stored in this JMS Server.
      This does not include the pending bytes."
      ::= { jmsServerRuntimeEntry 90  }
   
   
   jmsServerRuntimeBytesPendingCount OBJECT-TYPE
      SYNTAX      Counter64
      MAX-ACCESS  read-only
      STATUS      current
      DESCRIPTION "The number of pending bytes stored in this JMS Server.
      Pending bytes are over and above the current number of bytes."
      ::= { jmsServerRuntimeEntry 95  }
   
   
   jmsServerRuntimeBytesHighCount OBJECT-TYPE
      SYNTAX      Counter64
      MAX-ACCESS  read-only
      STATUS      current
      DESCRIPTION "The peak number of bytes stored in this JMS Server
      since the last reset."
      ::= { jmsServerRuntimeEntry 100  }
   
   
   jmsServerRuntimeBytesReceivedCount OBJECT-TYPE
      SYNTAX      Counter64
      MAX-ACCESS  read-only
      STATUS      current
      DESCRIPTION "The number of bytes received in this JMS Server
      since the last reset."
      ::= { jmsServerRuntimeEntry 105  }
   
   
   jmsServerRuntimeBytesThresholdTime OBJECT-TYPE
      SYNTAX      Counter64
      MAX-ACCESS  read-only
      STATUS      current
      DESCRIPTION "The amount of time in the threshold condition
      since the last reset."
      ::= { jmsServerRuntimeEntry 110  }
   
   
   jmsServerRuntimeMessagesPagedInTotalCount OBJECT-TYPE
      SYNTAX      INTEGER
      MAX-ACCESS  read-only
      STATUS      current
      DESCRIPTION "Return the total number of messages that were read from the paging directory since the JMS server was started."
      ::= { jmsServerRuntimeEntry 111  }
   
   
   jmsServerRuntimeProductionPaused OBJECT-TYPE
      SYNTAX      OCTET STRING
      MAX-ACCESS  read-only
      STATUS      current
      DESCRIPTION "Returns the current production paused state of the JMSServer as boolean value."
      ::= { jmsServerRuntimeEntry 112  }
   
   
   jmsServerRuntimeInsertionPaused OBJECT-TYPE
      SYNTAX      OCTET STRING
      MAX-ACCESS  read-only
      STATUS      current
      DESCRIPTION "Returns the current insertion paused state of the JMSServer as boolean value."
      ::= { jmsServerRuntimeEntry 113  }
   
   
   jmsServerRuntimeConsumptionPausedState OBJECT-TYPE
      SYNTAX      OCTET STRING
      MAX-ACCESS  read-only
      STATUS      current
      DESCRIPTION "Returns the current consumption paused state of the JMSServer as string value."
      ::= { jmsServerRuntimeEntry 114  }
   
   
   jmsServerRuntimeConsumptionPaused OBJECT-TYPE
      SYNTAX      OCTET STRING
      MAX-ACCESS  read-only
      STATUS      current
      DESCRIPTION "Returns the current consumption paused state of the JMSServer as boolean value."
      ::= { jmsServerRuntimeEntry 115  }
   
   
   jmsServerRuntimeBytesPageableCurrentCount OBJECT-TYPE
      SYNTAX      Counter64
      MAX-ACCESS  read-only
      STATUS      current
      DESCRIPTION "Return the total number of bytes in all the messages that are currently available to be paged out, but which have not yet been paged out. The JMS server attempts to keep this number smaller than the 'MessageBufferSize' parameter."
      ::= { jmsServerRuntimeEntry 116  }
   
   
   jmsServerRuntimeMessagesPagedOutTotalCount OBJECT-TYPE
      SYNTAX      INTEGER
      MAX-ACCESS  read-only
      STATUS      current
      DESCRIPTION "Return the total number of messages that were written to the paging directory since the JMS server was started."
      ::= { jmsServerRuntimeEntry 117  }
   
   
   jmsServerRuntimeInsertionPausedState OBJECT-TYPE
      SYNTAX      OCTET STRING
      MAX-ACCESS  read-only
      STATUS      current
      DESCRIPTION "Returns the current insertion paused state of the JMSServer as string value."
      ::= { jmsServerRuntimeEntry 118  }
   
   
   jmsServerRuntimeMessagesPageableCurrentCount OBJECT-TYPE
      SYNTAX      INTEGER
      MAX-ACCESS  read-only
      STATUS      current
      DESCRIPTION "Return the number of messages that are currently available for paging in this JMS server but have not yet been paged out. Note that due to internal implementation details, this count may be zero even if 'PageableByteCurrentCount' is zero."
      ::= { jmsServerRuntimeEntry 119  }
   
   
   jmsServerRuntimeProductionPausedState OBJECT-TYPE
      SYNTAX      OCTET STRING
      MAX-ACCESS  read-only
      STATUS      current
      DESCRIPTION "Returns the current production paused state of the JMSServer as string value."
      ::= { jmsServerRuntimeEntry 120  }
   
   
   jmsServerRuntimeBytesPagedOutTotalCount OBJECT-TYPE
      SYNTAX      Counter64
      MAX-ACCESS  read-only
      STATUS      current
      DESCRIPTION "Return the total number of bytes that were written to the paging directory since the JMS server was started."
      ::= { jmsServerRuntimeEntry 121  }
   
   
   jmsServerRuntimeBytesPagedInTotalCount OBJECT-TYPE
      SYNTAX      Counter64
      MAX-ACCESS  read-only
      STATUS      current
      DESCRIPTION "Return the total number of bytes that were read from the paging directory since the JMS server was started."
      ::= { jmsServerRuntimeEntry 122  }
   
   
   jmsSessionPoolRuntimeTable OBJECT-TYPE
      SYNTAX      SEQUENCE OF JmsSessionPoolRuntimeEntry
      MAX-ACCESS  not-accessible
      STATUS      current
      DESCRIPTION "This table is used for monitoring a WebLogic JMS Session Pool"
      ::= { wls 260  }
      
   
   jmsSessionPoolRuntimeEntry OBJECT-TYPE
      SYNTAX      JmsSessionPoolRuntimeEntry
      MAX-ACCESS  not-accessible
      STATUS      current
      DESCRIPTION "Entry of jmsSessionPoolRuntimeTable"
      INDEX { jmsSessionPoolRuntimeIndex}
      ::= { jmsSessionPoolRuntimeTable 1 }
      
   JmsSessionPoolRuntimeEntry ::=
      SEQUENCE
      {
         jmsSessionPoolRuntimeIndex DisplayString (SIZE (1..16)),
         jmsSessionPoolRuntimeObjectName DisplayString (SIZE (1..256)),
         jmsSessionPoolRuntimeType DisplayString (SIZE (1..64)),
         jmsSessionPoolRuntimeName DisplayString (SIZE (1..64)),
         jmsSessionPoolRuntimeParent DisplayString (SIZE (1..256)),
         jmsSessionPoolRuntimeJMSServer DisplayString (SIZE (1..256)),
         jmsSessionPoolRuntimeConnectionConsumers DisplayString (SIZE (1..2048)),
         jmsSessionPoolRuntimeConnectionConsumersCurrentCount Counter64,
         jmsSessionPoolRuntimeConnectionConsumersHighCount Counter64,
         jmsSessionPoolRuntimeConnectionConsumersTotalCount Counter64
      }
      
   
   jmsSessionPoolRuntimeIndex OBJECT-TYPE
      SYNTAX      DisplayString (SIZE (1..16))
      MAX-ACCESS  read-only
      STATUS      current
      DESCRIPTION "Unique value directed from ObjectName which is used as table index"
      ::= { jmsSessionPoolRuntimeEntry 1  }
   
   
   jmsSessionPoolRuntimeObjectName OBJECT-TYPE
      SYNTAX      DisplayString (SIZE (1..256))
      MAX-ACCESS  read-only
      STATUS      current
      DESCRIPTION "JMX-standard MBean name"
      ::= { jmsSessionPoolRuntimeEntry 5  }
   
   
   jmsSessionPoolRuntimeType OBJECT-TYPE
      SYNTAX      DisplayString (SIZE (1..64))
      MAX-ACCESS  read-only
      STATUS      current
      DESCRIPTION "BEA-proprietary MBean type"
      ::= { jmsSessionPoolRuntimeEntry 10  }
   
   
   jmsSessionPoolRuntimeName OBJECT-TYPE
      SYNTAX      DisplayString (SIZE (1..64))
      MAX-ACCESS  read-only
      STATUS      current
      DESCRIPTION "BEA-proprietary MBean name"
      ::= { jmsSessionPoolRuntimeEntry 15  }
   
   
   jmsSessionPoolRuntimeParent OBJECT-TYPE
      SYNTAX      DisplayString (SIZE (1..256))
      MAX-ACCESS  read-only
      STATUS      current
      DESCRIPTION "BEA-proprietary Parent object's identification, with syntax
      <type>:<name>"
      ::= { jmsSessionPoolRuntimeEntry 20  }
   
   
   jmsSessionPoolRuntimeJMSServer OBJECT-TYPE
      SYNTAX      DisplayString (SIZE (1..256))
      MAX-ACCESS  read-only
      STATUS      current
      DESCRIPTION "The JMS server for this session pool"
      ::= { jmsSessionPoolRuntimeEntry 25  }
   
   
   jmsSessionPoolRuntimeConnectionConsumers OBJECT-TYPE
      SYNTAX      DisplayString (SIZE (1..2048))
      MAX-ACCESS  read-only
      STATUS      current
      DESCRIPTION "The connection consumer for this session pool"
      ::= { jmsSessionPoolRuntimeEntry 30  }
   
   
   jmsSessionPoolRuntimeConnectionConsumersCurrentCount OBJECT-TYPE
      SYNTAX      Counter64
      MAX-ACCESS  read-only
      STATUS      current
      DESCRIPTION "The current number of connection consumers for this session pool"
      ::= { jmsSessionPoolRuntimeEntry 35  }
   
   
   jmsSessionPoolRuntimeConnectionConsumersHighCount OBJECT-TYPE
      SYNTAX      Counter64
      MAX-ACCESS  read-only
      STATUS      current
      DESCRIPTION "The peak number of simultaneous connection consumers for this
      session pool"
      ::= { jmsSessionPoolRuntimeEntry 40  }
   
   
   jmsSessionPoolRuntimeConnectionConsumersTotalCount OBJECT-TYPE
      SYNTAX      Counter64
      MAX-ACCESS  read-only
      STATUS      current
      DESCRIPTION "The total number of connection consumers made by this session pool
      since the last reset"
      ::= { jmsSessionPoolRuntimeEntry 45  }
   
   
   jmsSessionRuntimeTable OBJECT-TYPE
      SYNTAX      SEQUENCE OF JmsSessionRuntimeEntry
      MAX-ACCESS  not-accessible
      STATUS      current
      DESCRIPTION "This table is used for monitoring a WebLogic JMS Session Pool"
      ::= { wls 270  }
      
   
   jmsSessionRuntimeEntry OBJECT-TYPE
      SYNTAX      JmsSessionRuntimeEntry
      MAX-ACCESS  not-accessible
      STATUS      current
      DESCRIPTION "Entry of jmsSessionRuntimeTable"
      INDEX { jmsSessionRuntimeIndex}
      ::= { jmsSessionRuntimeTable 1 }
      
   JmsSessionRuntimeEntry ::=
      SEQUENCE
      {
         jmsSessionRuntimeIndex DisplayString (SIZE (1..16)),
         jmsSessionRuntimeObjectName DisplayString (SIZE (1..256)),
         jmsSessionRuntimeType DisplayString (SIZE (1..64)),
         jmsSessionRuntimeName DisplayString (SIZE (1..64)),
         jmsSessionRuntimeParent DisplayString (SIZE (1..256)),
         jmsSessionRuntimeConsumers DisplayString (SIZE (1..2048)),
         jmsSessionRuntimeConsumersCurrentCount Counter64,
         jmsSessionRuntimeConsumersHighCount Counter64,
         jmsSessionRuntimeConsumersTotalCount Counter64,
         jmsSessionRuntimeProducers DisplayString (SIZE (1..2048)),
         jmsSessionRuntimeProducersCurrentCount Counter64,
         jmsSessionRuntimeProducersHighCount Counter64,
         jmsSessionRuntimeProducersTotalCount Counter64,
         jmsSessionRuntimeTransacted INTEGER
                     {
                        true(1),
                        false(2)
                     }
         ,
         jmsSessionRuntimeAcknowledgeMode DisplayString (SIZE (1..32)),
         jmsSessionRuntimeMessagesPendingCount Counter64,
         jmsSessionRuntimeMessagesSentCount Counter64,
         jmsSessionRuntimeMessagesReceivedCount Counter64,
         jmsSessionRuntimeBytesPendingCount Counter64,
         jmsSessionRuntimeBytesSentCount Counter64,
         jmsSessionRuntimeBytesReceivedCount Counter64
      }
      
   
   jmsSessionRuntimeIndex OBJECT-TYPE
      SYNTAX      DisplayString (SIZE (1..16))
      MAX-ACCESS  read-only
      STATUS      current
      DESCRIPTION "Unique value directed from ObjectName which is used as table index"
      ::= { jmsSessionRuntimeEntry 1  }
   
   
   jmsSessionRuntimeObjectName OBJECT-TYPE
      SYNTAX      DisplayString (SIZE (1..256))
      MAX-ACCESS  read-only
      STATUS      current
      DESCRIPTION "JMX-standard MBean name"
      ::= { jmsSessionRuntimeEntry 5  }
   
   
   jmsSessionRuntimeType OBJECT-TYPE
      SYNTAX      DisplayString (SIZE (1..64))
      MAX-ACCESS  read-only
      STATUS      current
      DESCRIPTION "BEA-proprietary MBean type"
      ::= { jmsSessionRuntimeEntry 10  }
   
   
   jmsSessionRuntimeName OBJECT-TYPE
      SYNTAX      DisplayString (SIZE (1..64))
      MAX-ACCESS  read-only
      STATUS      current
      DESCRIPTION "BEA-proprietary MBean name"
      ::= { jmsSessionRuntimeEntry 15  }
   
   
   jmsSessionRuntimeParent OBJECT-TYPE
      SYNTAX      DisplayString (SIZE (1..256))
      MAX-ACCESS  read-only
      STATUS      current
      DESCRIPTION "BEA-proprietary Parent object's identification, with syntax
      <type>:<name>"
      ::= { jmsSessionRuntimeEntry 20  }
   
   
   jmsSessionRuntimeConsumers OBJECT-TYPE
      SYNTAX      DisplayString (SIZE (1..2048))
      MAX-ACCESS  read-only
      STATUS      current
      DESCRIPTION "An array of consumers for this session"
      ::= { jmsSessionRuntimeEntry 25  }
   
   
   jmsSessionRuntimeConsumersCurrentCount OBJECT-TYPE
      SYNTAX      Counter64
      MAX-ACCESS  read-only
      STATUS      current
      DESCRIPTION "The current number of consumers for this session"
      ::= { jmsSessionRuntimeEntry 30  }
   
   
   jmsSessionRuntimeConsumersHighCount OBJECT-TYPE
      SYNTAX      Counter64
      MAX-ACCESS  read-only
      STATUS      current
      DESCRIPTION "The peak number of consumers for this session
      since the last reset"
      ::= { jmsSessionRuntimeEntry 35  }
   
   
   jmsSessionRuntimeConsumersTotalCount OBJECT-TYPE
      SYNTAX      Counter64
      MAX-ACCESS  read-only
      STATUS      current
      DESCRIPTION "The number of consumers instantiated by this session
      since the last reset"
      ::= { jmsSessionRuntimeEntry 40  }
   
   
   jmsSessionRuntimeProducers OBJECT-TYPE
      SYNTAX      DisplayString (SIZE (1..2048))
      MAX-ACCESS  read-only
      STATUS      current
      DESCRIPTION "An array of producers for this session"
      ::= { jmsSessionRuntimeEntry 45  }
   
   
   jmsSessionRuntimeProducersCurrentCount OBJECT-TYPE
      SYNTAX      Counter64
      MAX-ACCESS  read-only
      STATUS      current
      DESCRIPTION "The current number of producers for this session"
      ::= { jmsSessionRuntimeEntry 50  }
   
   
   jmsSessionRuntimeProducersHighCount OBJECT-TYPE
      SYNTAX      Counter64
      MAX-ACCESS  read-only
      STATUS      current
      DESCRIPTION "The peak number of producers for this session
      since the last reset"
      ::= { jmsSessionRuntimeEntry 55  }
   
   
   jmsSessionRuntimeProducersTotalCount OBJECT-TYPE
      SYNTAX      Counter64
      MAX-ACCESS  read-only
      STATUS      current
      DESCRIPTION "The number of producers for this session
      since the last reset"
      ::= { jmsSessionRuntimeEntry 60  }
   
   
   jmsSessionRuntimeTransacted OBJECT-TYPE
      SYNTAX      INTEGER
                  {
                     true(1),
                     false(2)
                  }
      
      MAX-ACCESS  read-only
      STATUS      current
      DESCRIPTION "A boolean value (true Or false). Is the session transacted"
      ::= { jmsSessionRuntimeEntry 65  }
   
   
   jmsSessionRuntimeAcknowledgeMode OBJECT-TYPE
      SYNTAX      DisplayString (SIZE (1..32))
      MAX-ACCESS  read-only
      STATUS      current
      DESCRIPTION "The acknowledge mode as one of
      'AUTO_ACKNOWLEDGE'
      'CLIENT_ACKNOWLEDGE'
      'DUPS_OK_ACKNOWLEDGE'
      'NO_ACKNOWLEDGE'"
      ::= { jmsSessionRuntimeEntry 70  }
   
   
   jmsSessionRuntimeMessagesPendingCount OBJECT-TYPE
      SYNTAX      Counter64
      MAX-ACCESS  read-only
      STATUS      current
      DESCRIPTION "The number of messages pending (uncommitted and
      and unacknowledged) for this session"
      ::= { jmsSessionRuntimeEntry 75  }
   
   
   jmsSessionRuntimeMessagesSentCount OBJECT-TYPE
      SYNTAX      Counter64
      MAX-ACCESS  read-only
      STATUS      current
      DESCRIPTION "The number of bytes sent by this session
      since the last reset"
      ::= { jmsSessionRuntimeEntry 80  }
   
   
   jmsSessionRuntimeMessagesReceivedCount OBJECT-TYPE
      SYNTAX      Counter64
      MAX-ACCESS  read-only
      STATUS      current
      DESCRIPTION "The number of messages sent by this session
      since the last reset"
      ::= { jmsSessionRuntimeEntry 85  }
   
   
   jmsSessionRuntimeBytesPendingCount OBJECT-TYPE
      SYNTAX      Counter64
      MAX-ACCESS  read-only
      STATUS      current
      DESCRIPTION "The number of bytes pending (uncommitted and
      and unacknowledged) for this session"
      ::= { jmsSessionRuntimeEntry 90  }
   
   
   jmsSessionRuntimeBytesSentCount OBJECT-TYPE
      SYNTAX      Counter64
      MAX-ACCESS  read-only
      STATUS      current
      DESCRIPTION "The number of bytes sent by this session
      since the last reset"
      ::= { jmsSessionRuntimeEntry 95  }
   
   
   jmsSessionRuntimeBytesReceivedCount OBJECT-TYPE
      SYNTAX      Counter64
      MAX-ACCESS  read-only
      STATUS      current
      DESCRIPTION "The number of bytes received by this session
      since the last reset"
      ::= { jmsSessionRuntimeEntry 100  }
   
   
   jmsComponentRuntimeTable OBJECT-TYPE
      SYNTAX      SEQUENCE OF JmsComponentRuntimeEntry
      MAX-ACCESS  not-accessible
      STATUS      current
      DESCRIPTION "This table represents a JMS Module Deployment."
      ::= { wls 271  }
      
   
   jmsComponentRuntimeEntry OBJECT-TYPE
      SYNTAX      JmsComponentRuntimeEntry
      MAX-ACCESS  not-accessible
      STATUS      current
      DESCRIPTION "Entry of jmsComponentRuntimeTable"
      INDEX { jmsComponentRuntimeIndex}
      ::= { jmsComponentRuntimeTable 1 }
      
   JmsComponentRuntimeEntry ::=
      SEQUENCE
      {
         jmsComponentRuntimeIndex DisplayString (SIZE (1..16)),
         jmsComponentRuntimeObjectName DisplayString (SIZE (1..256)),
         jmsComponentRuntimeType DisplayString (SIZE (1..64)),
         jmsComponentRuntimeName DisplayString (SIZE (1..64)),
         jmsComponentRuntimeParent DisplayString (SIZE (1..256)),
         jmsComponentRuntimeModuleId DisplayString (SIZE (1..256)),
         jmsComponentRuntimeDeploymentState INTEGER
      }
      
   
   jmsComponentRuntimeIndex OBJECT-TYPE
      SYNTAX      DisplayString (SIZE (1..16))
      MAX-ACCESS  read-only
      STATUS      current
      DESCRIPTION "Unique value directed from ObjectName which is used as table index"
      ::= { jmsComponentRuntimeEntry 1  }
   
   
   jmsComponentRuntimeObjectName OBJECT-TYPE
      SYNTAX      DisplayString (SIZE (1..256))
      MAX-ACCESS  read-only
      STATUS      current
      DESCRIPTION "JMX-standard MBean name"
      ::= { jmsComponentRuntimeEntry 5  }
   
   
   jmsComponentRuntimeType OBJECT-TYPE
      SYNTAX      DisplayString (SIZE (1..64))
      MAX-ACCESS  read-only
      STATUS      current
      DESCRIPTION "BEA-proprietary MBean type"
      ::= { jmsComponentRuntimeEntry 10  }
   
   
   jmsComponentRuntimeName OBJECT-TYPE
      SYNTAX      DisplayString (SIZE (1..64))
      MAX-ACCESS  read-only
      STATUS      current
      DESCRIPTION "BEA-proprietary MBean name"
      ::= { jmsComponentRuntimeEntry 15  }
   
   
   jmsComponentRuntimeParent OBJECT-TYPE
      SYNTAX      DisplayString (SIZE (1..256))
      MAX-ACCESS  read-only
      STATUS      current
      DESCRIPTION "BEA-proprietary Parent object's identification, with syntax
      <type>:<name>"
      ::= { jmsComponentRuntimeEntry 20  }
   
   
   jmsComponentRuntimeModuleId OBJECT-TYPE
      SYNTAX      DisplayString (SIZE (1..256))
      MAX-ACCESS  read-only
      STATUS      current
      DESCRIPTION "Typical modules will use the URI for their id."
      ::= { jmsComponentRuntimeEntry 25  }
   
   
   jmsComponentRuntimeDeploymentState OBJECT-TYPE
      SYNTAX      INTEGER
      MAX-ACCESS  read-only
      STATUS      current
      DESCRIPTION "Return the current deployment state of the module."
      ::= { jmsComponentRuntimeEntry 30  }
   
   
   joltConnectionPoolRuntimeTable OBJECT-TYPE
      SYNTAX      SEQUENCE OF JoltConnectionPoolRuntimeEntry
      MAX-ACCESS  not-accessible
      STATUS      current
      DESCRIPTION "This table is used for monitoring a WebLogic Jolt Connection Pool"
      ::= { wls 280  }
      
   
   joltConnectionPoolRuntimeEntry OBJECT-TYPE
      SYNTAX      JoltConnectionPoolRuntimeEntry
      MAX-ACCESS  not-accessible
      STATUS      current
      DESCRIPTION "Entry of joltConnectionPoolRuntimeTable"
      INDEX { joltConnectionPoolRuntimeIndex}
      ::= { joltConnectionPoolRuntimeTable 1 }
      
   JoltConnectionPoolRuntimeEntry ::=
      SEQUENCE
      {
         joltConnectionPoolRuntimeIndex DisplayString (SIZE (1..16)),
         joltConnectionPoolRuntimeObjectName DisplayString (SIZE (1..256)),
         joltConnectionPoolRuntimeType DisplayString (SIZE (1..64)),
         joltConnectionPoolRuntimeName DisplayString (SIZE (1..64)),
         joltConnectionPoolRuntimeParent DisplayString (SIZE (1..256)),
         joltConnectionPoolRuntimePoolName DisplayString (SIZE (1..64)),
         joltConnectionPoolRuntimeMaxCapacity INTEGER,
         joltConnectionPoolRuntimePoolState DisplayString (SIZE (1..16)),
         joltConnectionPoolRuntimeSecurityContextPropagation INTEGER
                     {
                        true(1),
                        false(2)
                     }
         ,
         joltConnectionPoolRuntimeConnections DisplayString (SIZE (1..2048))
      }
      
   
   joltConnectionPoolRuntimeIndex OBJECT-TYPE
      SYNTAX      DisplayString (SIZE (1..16))
      MAX-ACCESS  read-only
      STATUS      current
      DESCRIPTION "Unique value directed from ObjectName which is used as table index"
      ::= { joltConnectionPoolRuntimeEntry 1  }
   
   
   joltConnectionPoolRuntimeObjectName OBJECT-TYPE
      SYNTAX      DisplayString (SIZE (1..256))
      MAX-ACCESS  read-only
      STATUS      current
      DESCRIPTION "JMX-standard MBean name"
      ::= { joltConnectionPoolRuntimeEntry 5  }
   
   
   joltConnectionPoolRuntimeType OBJECT-TYPE
      SYNTAX      DisplayString (SIZE (1..64))
      MAX-ACCESS  read-only
      STATUS      current
      DESCRIPTION "BEA-proprietary MBean type"
      ::= { joltConnectionPoolRuntimeEntry 10  }
   
   
   joltConnectionPoolRuntimeName OBJECT-TYPE
      SYNTAX      DisplayString (SIZE (1..64))
      MAX-ACCESS  read-only
      STATUS      current
      DESCRIPTION "BEA-proprietary MBean name"
      ::= { joltConnectionPoolRuntimeEntry 15  }
   
   
   joltConnectionPoolRuntimeParent OBJECT-TYPE
      SYNTAX      DisplayString (SIZE (1..256))
      MAX-ACCESS  read-only
      STATUS      current
      DESCRIPTION "BEA-proprietary Parent object's identification, with syntax
      <type>:<name>"
      ::= { joltConnectionPoolRuntimeEntry 20  }
   
   
   joltConnectionPoolRuntimePoolName OBJECT-TYPE
      SYNTAX      DisplayString (SIZE (1..64))
      MAX-ACCESS  read-only
      STATUS      current
      DESCRIPTION "The configured name of this Jolt pool."
      ::= { joltConnectionPoolRuntimeEntry 25  }
   
   
   joltConnectionPoolRuntimeMaxCapacity OBJECT-TYPE
      SYNTAX      INTEGER
      MAX-ACCESS  read-only
      STATUS      current
      DESCRIPTION "The maximum connections configured for this Jolt pool."
      ::= { joltConnectionPoolRuntimeEntry 30  }
   
   
   joltConnectionPoolRuntimePoolState OBJECT-TYPE
      SYNTAX      DisplayString (SIZE (1..16))
      MAX-ACCESS  read-only
      STATUS      current
      DESCRIPTION "The pool state as one of
      'Active'
      'Suspended'"
      ::= { joltConnectionPoolRuntimeEntry 35  }
   
   
   joltConnectionPoolRuntimeSecurityContextPropagation OBJECT-TYPE
      SYNTAX      INTEGER
                  {
                     true(1),
                     false(2)
                  }
      
      MAX-ACCESS  read-only
      STATUS      current
      DESCRIPTION "A boolean value (true Or false). Is the security context propagated"
      ::= { joltConnectionPoolRuntimeEntry 40  }
   
   
   joltConnectionPoolRuntimeConnections OBJECT-TYPE
      SYNTAX      DisplayString (SIZE (1..2048))
      MAX-ACCESS  read-only
      STATUS      current
      DESCRIPTION "An array of JoltConnectionRuntimeMBeans that each
      represents the statistics for a Jolt Connection."
      ::= { joltConnectionPoolRuntimeEntry 45  }
   
   
   joltConnectionRuntimeTable OBJECT-TYPE
      SYNTAX      SEQUENCE OF JoltConnectionRuntimeEntry
      MAX-ACCESS  not-accessible
      STATUS      current
      DESCRIPTION "This table is used for monitoring individual WebLogic Jolt connections"
      ::= { wls 290  }
      
   
   joltConnectionRuntimeEntry OBJECT-TYPE
      SYNTAX      JoltConnectionRuntimeEntry
      MAX-ACCESS  not-accessible
      STATUS      current
      DESCRIPTION "Entry of joltConnectionRuntimeTable"
      INDEX { joltConnectionRuntimeIndex}
      ::= { joltConnectionRuntimeTable 1 }
      
   JoltConnectionRuntimeEntry ::=
      SEQUENCE
      {
         joltConnectionRuntimeIndex DisplayString (SIZE (1..16)),
         joltConnectionRuntimeObjectName DisplayString (SIZE (1..256)),
         joltConnectionRuntimeType DisplayString (SIZE (1..64)),
         joltConnectionRuntimeName DisplayString (SIZE (1..64)),
         joltConnectionRuntimeParent DisplayString (SIZE (1..256)),
         joltConnectionRuntimeAddress DisplayString (SIZE (1..256)),
         joltConnectionRuntimeLastAccessTime DisplayString (SIZE (1..32)),
         joltConnectionRuntimeAlive INTEGER
                     {
                        true(1),
                        false(2)
                     }
         ,
         joltConnectionRuntimeRequestCount INTEGER,
         joltConnectionRuntimePendingRequestCount INTEGER,
         joltConnectionRuntimeErrorCount INTEGER,
         joltConnectionRuntimeInTransaction INTEGER
                     {
                        true(1),
                        false(2)
                     }
      }
      
   
   joltConnectionRuntimeIndex OBJECT-TYPE
      SYNTAX      DisplayString (SIZE (1..16))
      MAX-ACCESS  read-only
      STATUS      current
      DESCRIPTION "Unique value directed from ObjectName which is used as table index"
      ::= { joltConnectionRuntimeEntry 1  }
   
   
   joltConnectionRuntimeObjectName OBJECT-TYPE
      SYNTAX      DisplayString (SIZE (1..256))
      MAX-ACCESS  read-only
      STATUS      current
      DESCRIPTION "JMX-standard MBean name"
      ::= { joltConnectionRuntimeEntry 5  }
   
   
   joltConnectionRuntimeType OBJECT-TYPE
      SYNTAX      DisplayString (SIZE (1..64))
      MAX-ACCESS  read-only
      STATUS      current
      DESCRIPTION "BEA-proprietary MBean type"
      ::= { joltConnectionRuntimeEntry 10  }
   
   
   joltConnectionRuntimeName OBJECT-TYPE
      SYNTAX      DisplayString (SIZE (1..64))
      MAX-ACCESS  read-only
      STATUS      current
      DESCRIPTION "BEA-proprietary MBean name"
      ::= { joltConnectionRuntimeEntry 15  }
   
   
   joltConnectionRuntimeParent OBJECT-TYPE
      SYNTAX      DisplayString (SIZE (1..256))
      MAX-ACCESS  read-only
      STATUS      current
      DESCRIPTION "BEA-proprietary Parent object's identification, with syntax
      <type>:<name>"
      ::= { joltConnectionRuntimeEntry 20  }
   
   
   joltConnectionRuntimeAddress OBJECT-TYPE
      SYNTAX      DisplayString (SIZE (1..256))
      MAX-ACCESS  read-only
      STATUS      current
      DESCRIPTION "The connection Address"
      ::= { joltConnectionRuntimeEntry 25  }
   
   
   joltConnectionRuntimeLastAccessTime OBJECT-TYPE
      SYNTAX      DisplayString (SIZE (1..32))
      MAX-ACCESS  read-only
      STATUS      current
      DESCRIPTION "The Last Access Date and Time"
      ::= { joltConnectionRuntimeEntry 30  }
   
   
   joltConnectionRuntimeAlive OBJECT-TYPE
      SYNTAX      INTEGER
                  {
                     true(1),
                     false(2)
                  }
      
      MAX-ACCESS  read-only
      STATUS      current
      DESCRIPTION "A boolean value (true Or false).  the Connection Alive indicator"
      ::= { joltConnectionRuntimeEntry 35  }
   
   
   joltConnectionRuntimeRequestCount OBJECT-TYPE
      SYNTAX      INTEGER
      MAX-ACCESS  read-only
      STATUS      current
      DESCRIPTION "The Request Count"
      ::= { joltConnectionRuntimeEntry 40  }
   
   
   joltConnectionRuntimePendingRequestCount OBJECT-TYPE
      SYNTAX      INTEGER
      MAX-ACCESS  read-only
      STATUS      current
      DESCRIPTION "The Pending Request Count"
      ::= { joltConnectionRuntimeEntry 45  }
   
   
   joltConnectionRuntimeErrorCount OBJECT-TYPE
      SYNTAX      INTEGER
      MAX-ACCESS  read-only
      STATUS      current
      DESCRIPTION "The Request Error Count"
      ::= { joltConnectionRuntimeEntry 50  }
   
   
   joltConnectionRuntimeInTransaction OBJECT-TYPE
      SYNTAX      INTEGER
                  {
                     true(1),
                     false(2)
                  }
      
      MAX-ACCESS  read-only
      STATUS      current
      DESCRIPTION "A boolean value (true Or false). Returns the Connection in Transaction indicator"
      ::= { joltConnectionRuntimeEntry 55  }
   
   
   joltConnectionServiceRuntimeTable OBJECT-TYPE
      SYNTAX      SEQUENCE OF JoltConnectionServiceRuntimeEntry
      MAX-ACCESS  not-accessible
      STATUS      current
      DESCRIPTION "This table is used for monitoring a WebLogic Jolt component"
      ::= { wls 300  }
      
   
   joltConnectionServiceRuntimeEntry OBJECT-TYPE
      SYNTAX      JoltConnectionServiceRuntimeEntry
      MAX-ACCESS  not-accessible
      STATUS      current
      DESCRIPTION "Entry of joltConnectionServiceRuntimeTable"
      INDEX { joltConnectionServiceRuntimeIndex}
      ::= { joltConnectionServiceRuntimeTable 1 }
      
   JoltConnectionServiceRuntimeEntry ::=
      SEQUENCE
      {
         joltConnectionServiceRuntimeIndex DisplayString (SIZE (1..16)),
         joltConnectionServiceRuntimeObjectName DisplayString (SIZE (1..256)),
         joltConnectionServiceRuntimeType DisplayString (SIZE (1..64)),
         joltConnectionServiceRuntimeName DisplayString (SIZE (1..64)),
         joltConnectionServiceRuntimeParent DisplayString (SIZE (1..256)),
         joltConnectionServiceRuntimeConnectionPoolCount INTEGER,
         joltConnectionServiceRuntimeConnectionPools DisplayString (SIZE (1..2048))
      }
      
   
   joltConnectionServiceRuntimeIndex OBJECT-TYPE
      SYNTAX      DisplayString (SIZE (1..16))
      MAX-ACCESS  read-only
      STATUS      current
      DESCRIPTION "Unique value directed from ObjectName which is used as table index"
      ::= { joltConnectionServiceRuntimeEntry 1  }
   
   
   joltConnectionServiceRuntimeObjectName OBJECT-TYPE
      SYNTAX      DisplayString (SIZE (1..256))
      MAX-ACCESS  read-only
      STATUS      current
      DESCRIPTION "JMX-standard MBean name"
      ::= { joltConnectionServiceRuntimeEntry 5  }
   
   
   joltConnectionServiceRuntimeType OBJECT-TYPE
      SYNTAX      DisplayString (SIZE (1..64))
      MAX-ACCESS  read-only
      STATUS      current
      DESCRIPTION "BEA-proprietary MBean type"
      ::= { joltConnectionServiceRuntimeEntry 10  }
   
   
   joltConnectionServiceRuntimeName OBJECT-TYPE
      SYNTAX      DisplayString (SIZE (1..64))
      MAX-ACCESS  read-only
      STATUS      current
      DESCRIPTION "BEA-proprietary MBean name"
      ::= { joltConnectionServiceRuntimeEntry 15  }
   
   
   joltConnectionServiceRuntimeParent OBJECT-TYPE
      SYNTAX      DisplayString (SIZE (1..256))
      MAX-ACCESS  read-only
      STATUS      current
      DESCRIPTION "BEA-proprietary Parent object's identification, with syntax
      <type>:<name>"
      ::= { joltConnectionServiceRuntimeEntry 20  }
   
   
   joltConnectionServiceRuntimeConnectionPoolCount OBJECT-TYPE
      SYNTAX      INTEGER
      MAX-ACCESS  read-only
      STATUS      current
      DESCRIPTION "The number of configured Jolt connection pools."
      ::= { joltConnectionServiceRuntimeEntry 25  }
   
   
   joltConnectionServiceRuntimeConnectionPools OBJECT-TYPE
      SYNTAX      DisplayString (SIZE (1..2048))
      MAX-ACCESS  read-only
      STATUS      current
      DESCRIPTION "An array of JoltConnectionPoolRuntimeMBeans that each
      represents the statistics for a Jolt Connection Pool."
      ::= { joltConnectionServiceRuntimeEntry 30  }
   
   
   jrockitRuntimeTable OBJECT-TYPE
      SYNTAX      SEQUENCE OF JrockitRuntimeEntry
      MAX-ACCESS  not-accessible
      STATUS      current
      DESCRIPTION "This table is used for monitoring a WebLogic Jolt component"
      ::= { wls 302  }
      
   
   jrockitRuntimeEntry OBJECT-TYPE
      SYNTAX      JrockitRuntimeEntry
      MAX-ACCESS  not-accessible
      STATUS      current
      DESCRIPTION "Entry of jrockitRuntimeTable"
      INDEX { jrockitRuntimeIndex}
      ::= { jrockitRuntimeTable 1 }
      
   JrockitRuntimeEntry ::=
      SEQUENCE
      {
         jrockitRuntimeIndex  DisplayString (SIZE (1..16)),
         jrockitRuntimeObjectName DisplayString (SIZE (1..256)),
         jrockitRuntimeType   DisplayString (SIZE (1..64)),
         jrockitRuntimeName   DisplayString (SIZE (1..64)),
         jrockitRuntimeParent DisplayString (SIZE (1..256)),
         jrockitRuntimeAllProcessorsAverageLoad INTEGER,
         jrockitRuntimeFreeHeap Counter64,
         jrockitRuntimeFreePhysicalMemory Counter64,
         jrockitRuntimeGcAlgorithm DisplayString,
         jrockitRuntimeJVMDescription DisplayString,
         jrockitRuntimeJvmProcessorLoad INTEGER,
         jrockitRuntimeLastGCEnd Counter64,
         jrockitRuntimeLastGCStart Counter64,
         jrockitRuntimeNumberOfDaemonThreads INTEGER,
         jrockitRuntimeNumberOfProcessors INTEGER,
         jrockitRuntimeThreadStackDump DisplayString,
         jrockitRuntimeTotalGarbageCollectionCount Counter64,
         jrockitRuntimeTotalGarbageCollectionTime Counter64,
         jrockitRuntimeTotalHeap Counter64,
         jrockitRuntimeTotalNumberOfThreads INTEGER,
         jrockitRuntimeTotalNurserySize Counter64,
         jrockitRuntimeTotalPhysicalMemory Counter64,
         jrockitRuntimeUptime Counter64,
         jrockitRuntimeUsedHeap Counter64,
         jrockitRuntimeUsedPhysicalMemory Counter64,
         jrockitRuntimeVendor DisplayString,
         jrockitRuntimeVersion DisplayString,
         jrockitRuntimeConcurrent INTEGER,
         jrockitRuntimeGCHandlesCompaction INTEGER,
         jrockitRuntimeGenerational INTEGER,
         jrockitRuntimeIncremental INTEGER,
         jrockitRuntimeParallel INTEGER,
         jrockitRuntimeJavaVendor OCTET STRING,
         jrockitRuntimeHeapSizeCurrent Counter64,
         jrockitRuntimeHeapFreePercent INTEGER,
         jrockitRuntimeHeapSizeMax Counter64,
         jrockitRuntimeOSName OCTET STRING,
         jrockitRuntimeJavaVersion OCTET STRING,
         jrockitRuntimeOSVersion OCTET STRING,
         jrockitRuntimeHeapFreeCurrent Counter64,
         jrockitRuntimeJavaVMVendor OCTET STRING
      }
      
   
   jrockitRuntimeIndex OBJECT-TYPE
      SYNTAX      DisplayString (SIZE (1..16))
      MAX-ACCESS  read-only
      STATUS      current
      DESCRIPTION "Unique value directed from ObjectName which is used as table index"
      ::= { jrockitRuntimeEntry 1  }
   
   
   jrockitRuntimeObjectName OBJECT-TYPE
      SYNTAX      DisplayString (SIZE (1..256))
      MAX-ACCESS  read-only
      STATUS      current
      DESCRIPTION "JMX-standard MBean name"
      ::= { jrockitRuntimeEntry 5  }
   
   
   jrockitRuntimeType OBJECT-TYPE
      SYNTAX      DisplayString (SIZE (1..64))
      MAX-ACCESS  read-only
      STATUS      current
      DESCRIPTION "BEA-proprietary MBean type"
      ::= { jrockitRuntimeEntry 10  }
   
   
   jrockitRuntimeName OBJECT-TYPE
      SYNTAX      DisplayString (SIZE (1..64))
      MAX-ACCESS  read-only
      STATUS      current
      DESCRIPTION "BEA-proprietary MBean name"
      ::= { jrockitRuntimeEntry 15  }
   
   
   jrockitRuntimeParent OBJECT-TYPE
      SYNTAX      DisplayString (SIZE (1..256))
      MAX-ACCESS  read-only
      STATUS      current
      DESCRIPTION "BEA-proprietary Parent object's identification, with syntax
      <type>:<name>"
      ::= { jrockitRuntimeEntry 20  }
   
   
   jrockitRuntimeAllProcessorsAverageLoad OBJECT-TYPE
      SYNTAX      INTEGER
      MAX-ACCESS  read-only
      STATUS      current
      DESCRIPTION "represents a snapshot of the average load of all processors"
      ::= { jrockitRuntimeEntry 21  }
   
   
   jrockitRuntimeFreeHeap OBJECT-TYPE
      SYNTAX      Counter64
      MAX-ACCESS  read-only
      STATUS      current
      DESCRIPTION "Bytes of free Java heap memory."
      ::= { jrockitRuntimeEntry 22  }
   
   
   jrockitRuntimeFreePhysicalMemory OBJECT-TYPE
      SYNTAX      Counter64
      MAX-ACCESS  read-only
      STATUS      current
      DESCRIPTION "Bytes of free physical memory"
      ::= { jrockitRuntimeEntry 23  }
   
   
   jrockitRuntimeGcAlgorithm OBJECT-TYPE
      SYNTAX      DisplayString
      MAX-ACCESS  read-only
      STATUS      current
      DESCRIPTION "Type of garbage collector being used by the VM"
      ::= { jrockitRuntimeEntry 24  }
   
   
   jrockitRuntimeJVMDescription OBJECT-TYPE
      SYNTAX      DisplayString
      MAX-ACCESS  read-only
      STATUS      current
      DESCRIPTION "A description of the JVM as a String."
      ::= { jrockitRuntimeEntry 25  }
   
   
   jrockitRuntimeJvmProcessorLoad OBJECT-TYPE
      SYNTAX      INTEGER
      MAX-ACCESS  read-only
      STATUS      current
      DESCRIPTION "double that indicates the average load that the VM is placing on all processors."
      ::= { jrockitRuntimeEntry 26  }
   
   
   jrockitRuntimeLastGCEnd OBJECT-TYPE
      SYNTAX      Counter64
      MAX-ACCESS  read-only
      STATUS      current
      DESCRIPTION "the time the last GC ended."
      ::= { jrockitRuntimeEntry 27  }
   
   
   jrockitRuntimeLastGCStart OBJECT-TYPE
      SYNTAX      Counter64
      MAX-ACCESS  read-only
      STATUS      current
      DESCRIPTION "The time the last GC started"
      ::= { jrockitRuntimeEntry 28  }
   
   
   jrockitRuntimeNumberOfDaemonThreads OBJECT-TYPE
      SYNTAX      INTEGER
      MAX-ACCESS  read-only
      STATUS      current
      DESCRIPTION "the total number of daemon Java threads running in the VM."
      ::= { jrockitRuntimeEntry 29  }
   
   
   jrockitRuntimeNumberOfProcessors OBJECT-TYPE
      SYNTAX      INTEGER
      MAX-ACCESS  read-only
      STATUS      current
      DESCRIPTION "he number of processors on the VM's host computer."
      ::= { jrockitRuntimeEntry 30  }
   
   
   jrockitRuntimeThreadStackDump OBJECT-TYPE
      SYNTAX      DisplayString
      MAX-ACCESS  read-only
      STATUS      current
      DESCRIPTION "a stack dump of all live threads in the VM"
      ::= { jrockitRuntimeEntry 31  }
   
   
   jrockitRuntimeTotalGarbageCollectionCount OBJECT-TYPE
      SYNTAX      Counter64
      MAX-ACCESS  read-only
      STATUS      current
      DESCRIPTION "The number of GCs perfomed so far"
      ::= { jrockitRuntimeEntry 32  }
   
   
   jrockitRuntimeTotalGarbageCollectionTime OBJECT-TYPE
      SYNTAX      Counter64
      MAX-ACCESS  read-only
      STATUS      current
      DESCRIPTION "Indicates the number of milliseconds that the Virtual Machine has spent on all garbage collection runs since the VM was started."
      ::= { jrockitRuntimeEntry 33  }
   
   
   jrockitRuntimeTotalHeap OBJECT-TYPE
      SYNTAX      Counter64
      MAX-ACCESS  read-only
      STATUS      current
      DESCRIPTION "Bytes of memory allocated to the Java heap"
      ::= { jrockitRuntimeEntry 34  }
   
   
   jrockitRuntimeTotalNumberOfThreads OBJECT-TYPE
      SYNTAX      INTEGER
      MAX-ACCESS  read-only
      STATUS      current
      DESCRIPTION "the number of Java threads running in the VM"
      ::= { jrockitRuntimeEntry 35  }
   
   
   jrockitRuntimeTotalNurserySize OBJECT-TYPE
      SYNTAX      Counter64
      MAX-ACCESS  read-only
      STATUS      current
      DESCRIPTION "Bytes allocated to the nursery"
      ::= { jrockitRuntimeEntry 36  }
   
   
   jrockitRuntimeTotalPhysicalMemory OBJECT-TYPE
      SYNTAX      Counter64
      MAX-ACCESS  read-only
      STATUS      current
      DESCRIPTION "Bytes of physical memory on the host computer"
      ::= { jrockitRuntimeEntry 37  }
   
   
   jrockitRuntimeUptime OBJECT-TYPE
      SYNTAX      Counter64
      MAX-ACCESS  read-only
      STATUS      current
      DESCRIPTION "The uptime (in milliseconds) of the VM"
      ::= { jrockitRuntimeEntry 38  }
   
   
   jrockitRuntimeUsedHeap OBJECT-TYPE
      SYNTAX      Counter64
      MAX-ACCESS  read-only
      STATUS      current
      DESCRIPTION "Bytes of Java heap memory that is being used"
      ::= { jrockitRuntimeEntry 39  }
   
   
   jrockitRuntimeUsedPhysicalMemory OBJECT-TYPE
      SYNTAX      Counter64
      MAX-ACCESS  read-only
      STATUS      current
      DESCRIPTION "Bytes of physical memory being used."
      ::= { jrockitRuntimeEntry 40  }
   
   
   jrockitRuntimeVendor OBJECT-TYPE
      SYNTAX      DisplayString
      MAX-ACCESS  read-only
      STATUS      current
      DESCRIPTION "The name of the vendor as a String"
      ::= { jrockitRuntimeEntry 41  }
   
   
   jrockitRuntimeVersion OBJECT-TYPE
      SYNTAX      DisplayString
      MAX-ACCESS  read-only
      STATUS      current
      DESCRIPTION "The current version of the JVM as a String"
      ::= { jrockitRuntimeEntry 42  }
   
   
   jrockitRuntimeConcurrent OBJECT-TYPE
      SYNTAX      INTEGER
      MAX-ACCESS  read-only
      STATUS      current
      DESCRIPTION "true if this GC runs in a separate concurrent thread."
      ::= { jrockitRuntimeEntry 43  }
   
   
   jrockitRuntimeGCHandlesCompaction OBJECT-TYPE
      SYNTAX      INTEGER
      MAX-ACCESS  read-only
      STATUS      current
      DESCRIPTION "true if this garbage collector compacts the Java heap"
      ::= { jrockitRuntimeEntry 44  }
   
   
   jrockitRuntimeGenerational OBJECT-TYPE
      SYNTAX      INTEGER
      MAX-ACCESS  read-only
      STATUS      current
      DESCRIPTION "true if this GC has a nursery."
      ::= { jrockitRuntimeEntry 45  }
   
   
   jrockitRuntimeIncremental OBJECT-TYPE
      SYNTAX      INTEGER
      MAX-ACCESS  read-only
      STATUS      current
      DESCRIPTION "true if this GC is incremental"
      ::= { jrockitRuntimeEntry 46  }
   
   
   jrockitRuntimeParallel OBJECT-TYPE
      SYNTAX      INTEGER
      MAX-ACCESS  read-only
      STATUS      current
      DESCRIPTION "true if this GC runs in parallel on multiple processors"
      ::= { jrockitRuntimeEntry 47  }
   
   
   jrockitRuntimeJavaVendor OBJECT-TYPE
      SYNTAX      OCTET STRING
      MAX-ACCESS  read-only
      STATUS      current
      DESCRIPTION "Returns the vendor of Java.  The vendor of Java that this server runs."
      ::= { jrockitRuntimeEntry 48  }
   
   
   jrockitRuntimeHeapSizeCurrent OBJECT-TYPE
      SYNTAX      Counter64
      MAX-ACCESS  read-only
      STATUS      current
      DESCRIPTION "The current size (in bytes) of the JVM heap."
      ::= { jrockitRuntimeEntry 49  }
   
   
   jrockitRuntimeHeapFreePercent OBJECT-TYPE
      SYNTAX      INTEGER
      MAX-ACCESS  read-only
      STATUS      current
      DESCRIPTION "Percentage of the maximum memory that is free."
      ::= { jrockitRuntimeEntry 50  }
   
   
   jrockitRuntimeHeapSizeMax OBJECT-TYPE
      SYNTAX      Counter64
      MAX-ACCESS  read-only
      STATUS      current
      DESCRIPTION "The maximum free memory configured for this JVM."
      ::= { jrockitRuntimeEntry 51  }
   
   
   jrockitRuntimeOSName OBJECT-TYPE
      SYNTAX      OCTET STRING
      MAX-ACCESS  read-only
      STATUS      current
      DESCRIPTION "Returns the operating system on which the JVM is running.  The operating system on which the JVM is running."
      ::= { jrockitRuntimeEntry 52  }
   
   
   jrockitRuntimeJavaVersion OBJECT-TYPE
      SYNTAX      OCTET STRING
      MAX-ACCESS  read-only
      STATUS      current
      DESCRIPTION "The Java version of the JVM."
      ::= { jrockitRuntimeEntry 53  }
   
   
   jrockitRuntimeOSVersion OBJECT-TYPE
      SYNTAX      OCTET STRING
      MAX-ACCESS  read-only
      STATUS      current
      DESCRIPTION "The version of the operating system on which the JVM is running."
      ::= { jrockitRuntimeEntry 54  }
   
   
   jrockitRuntimeHeapFreeCurrent OBJECT-TYPE
      SYNTAX      Counter64
      MAX-ACCESS  read-only
      STATUS      current
      DESCRIPTION "The current amount of memory (in bytes) that is available in the JVM heap."
      ::= { jrockitRuntimeEntry 55  }
   
   
   jrockitRuntimeJavaVMVendor OBJECT-TYPE
      SYNTAX      OCTET STRING
      MAX-ACCESS  read-only
      STATUS      current
      DESCRIPTION "Returns the vendor of the JVM.  The vendor of the JVM that this server runs.  system property java.vm.vendor is returned"
      ::= { jrockitRuntimeEntry 56  }
   
   
   jtaRuntimeTable OBJECT-TYPE
      SYNTAX      SEQUENCE OF JtaRuntimeEntry
      MAX-ACCESS  not-accessible
      STATUS      current
      DESCRIPTION "This table is used for accessing transaction
      runtime characteristics within a WebLogic server."
      ::= { wls 310  }
      
   
   jtaRuntimeEntry OBJECT-TYPE
      SYNTAX      JtaRuntimeEntry
      MAX-ACCESS  not-accessible
      STATUS      current
      DESCRIPTION "Entry of jtaRuntimeTable"
      INDEX { jtaRuntimeIndex}
      ::= { jtaRuntimeTable 1 }
      
   JtaRuntimeEntry ::=
      SEQUENCE
      {
         jtaRuntimeIndex      DisplayString (SIZE (1..16)),
         jtaRuntimeObjectName DisplayString (SIZE (1..256)),
         jtaRuntimeType       DisplayString (SIZE (1..64)),
         jtaRuntimeName       DisplayString (SIZE (1..64)),
         jtaRuntimeParent     DisplayString (SIZE (1..256)),
         jtaRuntimeTransactionTotalCount Counter64,
         jtaRuntimeTransactionCommittedTotalCount Counter64,
         jtaRuntimeTransactionRolledBackTotalCount Counter64,
         jtaRuntimeTransactionHeuristicsTotalCount Counter64,
         jtaRuntimeTransactionRolledBackResourceTotalCount Counter64,
         jtaRuntimeTransactionRolledBackAppTotalCount Counter64,
         jtaRuntimeTransactionRolledBackSystemTotalCount Counter64,
         jtaRuntimeSecondsActiveTotalCount Counter64,
         jtaRuntimeTransactionRolledBackTimeoutTotalCount Counter64,
         jtaRuntimeTransactionNameRuntimeMBeans DisplayString (SIZE (1..2048)),
         jtaRuntimeTransactionResourceRuntimeMBeans DisplayString (SIZE (1..2048)),
         jtaRuntimeActiveTransactionsTotalCount INTEGER,
         jtaRuntimeTransactionAbandonedTotalCount Counter64
      }
      
   
   jtaRuntimeIndex OBJECT-TYPE
      SYNTAX      DisplayString (SIZE (1..16))
      MAX-ACCESS  read-only
      STATUS      current
      DESCRIPTION "Unique value directed from ObjectName which is used as table index"
      ::= { jtaRuntimeEntry 1  }
   
   
   jtaRuntimeObjectName OBJECT-TYPE
      SYNTAX      DisplayString (SIZE (1..256))
      MAX-ACCESS  read-only
      STATUS      current
      DESCRIPTION "JMX-standard MBean name"
      ::= { jtaRuntimeEntry 5  }
   
   
   jtaRuntimeType OBJECT-TYPE
      SYNTAX      DisplayString (SIZE (1..64))
      MAX-ACCESS  read-only
      STATUS      current
      DESCRIPTION "BEA-proprietary MBean type"
      ::= { jtaRuntimeEntry 10  }
   
   
   jtaRuntimeName OBJECT-TYPE
      SYNTAX      DisplayString (SIZE (1..64))
      MAX-ACCESS  read-only
      STATUS      current
      DESCRIPTION "BEA-proprietary MBean name"
      ::= { jtaRuntimeEntry 15  }
   
   
   jtaRuntimeParent OBJECT-TYPE
      SYNTAX      DisplayString (SIZE (1..256))
      MAX-ACCESS  read-only
      STATUS      current
      DESCRIPTION "BEA-proprietary Parent object's identification, with syntax
      <type>:<name>"
      ::= { jtaRuntimeEntry 20  }
   
   
   jtaRuntimeTransactionTotalCount OBJECT-TYPE
      SYNTAX      Counter64
      MAX-ACCESS  read-only
      STATUS      current
      DESCRIPTION "The total number of transactions processed.
      This total includes all committed, rolled back
      and heuristic transaction completions."
      ::= { jtaRuntimeEntry 25  }
   
   
   jtaRuntimeTransactionCommittedTotalCount OBJECT-TYPE
      SYNTAX      Counter64
      MAX-ACCESS  read-only
      STATUS      current
      DESCRIPTION "The number of committed transactions."
      ::= { jtaRuntimeEntry 30  }
   
   
   jtaRuntimeTransactionRolledBackTotalCount OBJECT-TYPE
      SYNTAX      Counter64
      MAX-ACCESS  read-only
      STATUS      current
      DESCRIPTION "The number of transactions that were rolled back."
      ::= { jtaRuntimeEntry 35  }
   
   
   jtaRuntimeTransactionHeuristicsTotalCount OBJECT-TYPE
      SYNTAX      Counter64
      MAX-ACCESS  read-only
      STATUS      current
      DESCRIPTION "The number of transactions that completed with a
      heuristic status."
      ::= { jtaRuntimeEntry 40  }
   
   
   jtaRuntimeTransactionRolledBackResourceTotalCount OBJECT-TYPE
      SYNTAX      Counter64
      MAX-ACCESS  read-only
      STATUS      current
      DESCRIPTION "Returns the number of transactions that were rolled back
      due to a resource error."
      ::= { jtaRuntimeEntry 45  }
   
   
   jtaRuntimeTransactionRolledBackAppTotalCount OBJECT-TYPE
      SYNTAX      Counter64
      MAX-ACCESS  read-only
      STATUS      current
      DESCRIPTION "The number of transactions that were rolled back
      due to an application error."
      ::= { jtaRuntimeEntry 50  }
   
   
   jtaRuntimeTransactionRolledBackSystemTotalCount OBJECT-TYPE
      SYNTAX      Counter64
      MAX-ACCESS  read-only
      STATUS      current
      DESCRIPTION "The number of transactions that were rolled back
      due to an internal system error."
      ::= { jtaRuntimeEntry 55  }
   
   
   jtaRuntimeSecondsActiveTotalCount OBJECT-TYPE
      SYNTAX      Counter64
      MAX-ACCESS  read-only
      STATUS      current
      DESCRIPTION "The total number of seconds for all committed
      transactions."
      ::= { jtaRuntimeEntry 60  }
   
   
   jtaRuntimeTransactionRolledBackTimeoutTotalCount OBJECT-TYPE
      SYNTAX      Counter64
      MAX-ACCESS  read-only
      STATUS      current
      DESCRIPTION "The total number of seconds for all committed
      transactions."
      ::= { jtaRuntimeEntry 65  }
   
   
   jtaRuntimeTransactionNameRuntimeMBeans OBJECT-TYPE
      SYNTAX      DisplayString (SIZE (1..2048))
      MAX-ACCESS  read-only
      STATUS      current
      DESCRIPTION "An array of TransactionNameRuntimeMBeans that represent
      statistics for all transactions in the server, categorized by
      transaction name"
      ::= { jtaRuntimeEntry 70  }
   
   
   jtaRuntimeTransactionResourceRuntimeMBeans OBJECT-TYPE
      SYNTAX      DisplayString (SIZE (1..2048))
      MAX-ACCESS  read-only
      STATUS      current
      DESCRIPTION "An array of TransactionResourceRuntimeMBeans that each
      represents the statistics for a transaction resource."
      ::= { jtaRuntimeEntry 75  }
   
   
   jtaRuntimeActiveTransactionsTotalCount OBJECT-TYPE
      SYNTAX      INTEGER
      MAX-ACCESS  read-only
      STATUS      current
      DESCRIPTION "The number of active transactions on the server."
      ::= { jtaRuntimeEntry 76  }
   
   
   jtaRuntimeTransactionAbandonedTotalCount OBJECT-TYPE
      SYNTAX      Counter64
      MAX-ACCESS  read-only
      STATUS      current
      DESCRIPTION "The total number of transactions that were abandoned since the server was started."
      ::= { jtaRuntimeEntry 77  }
   
   
   jtaRecoveryRuntimeTable OBJECT-TYPE
      SYNTAX      SEQUENCE OF JtaRecoveryRuntimeEntry
      MAX-ACCESS  not-accessible
      STATUS      current
      DESCRIPTION "This table is used for accessing transaction
      runtime characteristics within a WebLogic server."
      ::= { wls 311  }
      
   
   jtaRecoveryRuntimeEntry OBJECT-TYPE
      SYNTAX      JtaRecoveryRuntimeEntry
      MAX-ACCESS  not-accessible
      STATUS      current
      DESCRIPTION "Entry of jtaRecoveryRuntimeTable"
      INDEX { jtaRecoveryRuntimeIndex}
      ::= { jtaRecoveryRuntimeTable 1 }
      
   JtaRecoveryRuntimeEntry ::=
      SEQUENCE
      {
         jtaRecoveryRuntimeIndex DisplayString (SIZE (1..16)),
         jtaRecoveryRuntimeObjectName DisplayString (SIZE (1..256)),
         jtaRecoveryRuntimeType DisplayString (SIZE (1..64)),
         jtaRecoveryRuntimeName DisplayString (SIZE (1..64)),
         jtaRecoveryRuntimeParent DisplayString (SIZE (1..256)),
         jtaRecoveryRuntimeInitialRecoveredTransactionTotalCount INTEGER,
         jtaRecoveryRuntimeRecoveredTransactionCompletionPercent INTEGER,
         jtaRecoveryRuntimeActive INTEGER
      }
      
   
   jtaRecoveryRuntimeIndex OBJECT-TYPE
      SYNTAX      DisplayString (SIZE (1..16))
      MAX-ACCESS  read-only
      STATUS      current
      DESCRIPTION "Unique value directed from ObjectName which is used as table index"
      ::= { jtaRecoveryRuntimeEntry 1  }
   
   
   jtaRecoveryRuntimeObjectName OBJECT-TYPE
      SYNTAX      DisplayString (SIZE (1..256))
      MAX-ACCESS  read-only
      STATUS      current
      DESCRIPTION "JMX-standard MBean name"
      ::= { jtaRecoveryRuntimeEntry 5  }
   
   
   jtaRecoveryRuntimeType OBJECT-TYPE
      SYNTAX      DisplayString (SIZE (1..64))
      MAX-ACCESS  read-only
      STATUS      current
      DESCRIPTION "BEA-proprietary MBean type"
      ::= { jtaRecoveryRuntimeEntry 10  }
   
   
   jtaRecoveryRuntimeName OBJECT-TYPE
      SYNTAX      DisplayString (SIZE (1..64))
      MAX-ACCESS  read-only
      STATUS      current
      DESCRIPTION "BEA-proprietary MBean name"
      ::= { jtaRecoveryRuntimeEntry 15  }
   
   
   jtaRecoveryRuntimeParent OBJECT-TYPE
      SYNTAX      DisplayString (SIZE (1..256))
      MAX-ACCESS  read-only
      STATUS      current
      DESCRIPTION "BEA-proprietary Parent object's identification, with syntax
      <type>:<name>"
      ::= { jtaRecoveryRuntimeEntry 20  }
   
   
   jtaRecoveryRuntimeInitialRecoveredTransactionTotalCount OBJECT-TYPE
      SYNTAX      INTEGER
      MAX-ACCESS  read-only
      STATUS      current
      DESCRIPTION "Returns the total number of transactions that are recovered from
      the Transaction Log initially."
      ::= { jtaRecoveryRuntimeEntry 25  }
   
   
   jtaRecoveryRuntimeRecoveredTransactionCompletionPercent OBJECT-TYPE
      SYNTAX      INTEGER
      MAX-ACCESS  read-only
      STATUS      current
      DESCRIPTION "Returns the percentage of the initially recovered transactions that
      are completed."
      ::= { jtaRecoveryRuntimeEntry 30  }
   
   
   jtaRecoveryRuntimeActive OBJECT-TYPE
      SYNTAX      INTEGER
      MAX-ACCESS  read-only
      STATUS      current
      DESCRIPTION "Returns whether the Transaction Recovery Service is currently activated on this server."
      ::= { jtaRecoveryRuntimeEntry 35  }
   
   
   libraryRuntimeTable OBJECT-TYPE
      SYNTAX      SEQUENCE OF LibraryRuntimeEntry
      MAX-ACCESS  not-accessible
      STATUS      current
      DESCRIPTION "This table represents all Library Modules deployed in the server."
      ::= { wls 320  }
      
   
   libraryRuntimeEntry OBJECT-TYPE
      SYNTAX      LibraryRuntimeEntry
      MAX-ACCESS  not-accessible
      STATUS      current
      DESCRIPTION "Entry of libraryRuntimeTable"
      INDEX { libraryRuntimeIndex}
      ::= { libraryRuntimeTable 1 }
      
   LibraryRuntimeEntry ::=
      SEQUENCE
      {
         libraryRuntimeIndex  DisplayString (SIZE (1..16)),
         libraryRuntimeObjectName DisplayString (SIZE (1..256)),
         libraryRuntimeType   DisplayString (SIZE (1..64)),
         libraryRuntimeName   DisplayString (SIZE (1..64)),
         libraryRuntimeParent DisplayString (SIZE (1..256)),
         libraryRuntimeLibraryName DisplayString (SIZE (1..64)),
         libraryRuntimeSpecificationVersion DisplayString (SIZE (1..64)),
         libraryRuntimeImplementationVersion DisplayString (SIZE (1..64)),
         libraryRuntimeReferenced INTEGER
                     {
                        true(1),
                        false(2)
                     }
         ,
         libraryRuntimeLibraryIdentifier OCTET STRING
      }
      
   
   libraryRuntimeIndex OBJECT-TYPE
      SYNTAX      DisplayString (SIZE (1..16))
      MAX-ACCESS  read-only
      STATUS      current
      DESCRIPTION "Unique value directed from ObjectName which is used as table index"
      ::= { libraryRuntimeEntry 1  }
   
   
   libraryRuntimeObjectName OBJECT-TYPE
      SYNTAX      DisplayString (SIZE (1..256))
      MAX-ACCESS  read-only
      STATUS      current
      DESCRIPTION "JMX-standard MBean name"
      ::= { libraryRuntimeEntry 5  }
   
   
   libraryRuntimeType OBJECT-TYPE
      SYNTAX      DisplayString (SIZE (1..64))
      MAX-ACCESS  read-only
      STATUS      current
      DESCRIPTION "BEA-proprietary MBean type"
      ::= { libraryRuntimeEntry 10  }
   
   
   libraryRuntimeName OBJECT-TYPE
      SYNTAX      DisplayString (SIZE (1..64))
      MAX-ACCESS  read-only
      STATUS      current
      DESCRIPTION "BEA-proprietary MBean name"
      ::= { libraryRuntimeEntry 15  }
   
   
   libraryRuntimeParent OBJECT-TYPE
      SYNTAX      DisplayString (SIZE (1..256))
      MAX-ACCESS  read-only
      STATUS      current
      DESCRIPTION "BEA-proprietary Parent object's identification, with syntax
      <type>:<name>"
      ::= { libraryRuntimeEntry 20  }
   
   
   libraryRuntimeLibraryName OBJECT-TYPE
      SYNTAX      DisplayString (SIZE (1..64))
      MAX-ACCESS  read-only
      STATUS      current
      DESCRIPTION ""
      ::= { libraryRuntimeEntry 25  }
   
   
   libraryRuntimeSpecificationVersion OBJECT-TYPE
      SYNTAX      DisplayString (SIZE (1..64))
      MAX-ACCESS  read-only
      STATUS      current
      DESCRIPTION ""
      ::= { libraryRuntimeEntry 30  }
   
   
   libraryRuntimeImplementationVersion OBJECT-TYPE
      SYNTAX      DisplayString (SIZE (1..64))
      MAX-ACCESS  read-only
      STATUS      current
      DESCRIPTION ""
      ::= { libraryRuntimeEntry 35  }
   
   
   libraryRuntimeReferenced OBJECT-TYPE
      SYNTAX      INTEGER
                  {
                     true(1),
                     false(2)
                  }
      
      MAX-ACCESS  read-only
      STATUS      current
      DESCRIPTION "Returns true if this Library is referenced by one or more referencers. Typically a Library Referencer is a deployed application."
      ::= { libraryRuntimeEntry 40  }
   
   
   libraryRuntimeLibraryIdentifier OBJECT-TYPE
      SYNTAX      OCTET STRING
      MAX-ACCESS  read-only
      STATUS      current
      DESCRIPTION "Returns this Library's Identifier  The library identifier uniquely identifies this library version across all versions of all deployed applications and deployed libraries. If the library is not versioned, the library identifier is the same as the library name."
      ::= { libraryRuntimeEntry 41  }
   
   
   persistentStoreRuntimeTable OBJECT-TYPE
      SYNTAX      SEQUENCE OF PersistentStoreRuntimeEntry
      MAX-ACCESS  not-accessible
      STATUS      current
      DESCRIPTION "This table represents information about the Persistent Store."
      ::= { wls 330  }
      
   
   persistentStoreRuntimeEntry OBJECT-TYPE
      SYNTAX      PersistentStoreRuntimeEntry
      MAX-ACCESS  not-accessible
      STATUS      current
      DESCRIPTION "Entry of persistentStoreRuntimeTable"
      INDEX { persistentStoreRuntimeIndex}
      ::= { persistentStoreRuntimeTable 1 }
      
   PersistentStoreRuntimeEntry ::=
      SEQUENCE
      {
         persistentStoreRuntimeIndex DisplayString (SIZE (1..16)),
         persistentStoreRuntimeObjectName DisplayString (SIZE (1..256)),
         persistentStoreRuntimeType DisplayString (SIZE (1..64)),
         persistentStoreRuntimeName DisplayString (SIZE (1..64)),
         persistentStoreRuntimeParent DisplayString (SIZE (1..256)),
         persistentStoreRuntimeCreateCount Counter64,
         persistentStoreRuntimeReadCount Counter64,
         persistentStoreRuntimeUpdateCount Counter64,
         persistentStoreRuntimeDeleteCount Counter64,
         persistentStoreRuntimeObjectCount Counter64,
         persistentStoreRuntimePhysicalWriteCount Counter64
      }
      
   
   persistentStoreRuntimeIndex OBJECT-TYPE
      SYNTAX      DisplayString (SIZE (1..16))
      MAX-ACCESS  read-only
      STATUS      current
      DESCRIPTION "Unique value directed from ObjectName which is used as table index"
      ::= { persistentStoreRuntimeEntry 1  }
   
   
   persistentStoreRuntimeObjectName OBJECT-TYPE
      SYNTAX      DisplayString (SIZE (1..256))
      MAX-ACCESS  read-only
      STATUS      current
      DESCRIPTION "JMX-standard MBean name"
      ::= { persistentStoreRuntimeEntry 5  }
   
   
   persistentStoreRuntimeType OBJECT-TYPE
      SYNTAX      DisplayString (SIZE (1..64))
      MAX-ACCESS  read-only
      STATUS      current
      DESCRIPTION "BEA-proprietary MBean type"
      ::= { persistentStoreRuntimeEntry 10  }
   
   
   persistentStoreRuntimeName OBJECT-TYPE
      SYNTAX      DisplayString (SIZE (1..64))
      MAX-ACCESS  read-only
      STATUS      current
      DESCRIPTION "BEA-proprietary MBean name"
      ::= { persistentStoreRuntimeEntry 15  }
   
   
   persistentStoreRuntimeParent OBJECT-TYPE
      SYNTAX      DisplayString (SIZE (1..256))
      MAX-ACCESS  read-only
      STATUS      current
      DESCRIPTION "BEA-proprietary Parent object's identification, with syntax
      <type>:<name>"
      ::= { persistentStoreRuntimeEntry 20  }
   
   
   persistentStoreRuntimeCreateCount OBJECT-TYPE
      SYNTAX      Counter64
      MAX-ACCESS  read-only
      STATUS      current
      DESCRIPTION "Returns the Number of create requests issued by this store."
      ::= { persistentStoreRuntimeEntry 25  }
   
   
   persistentStoreRuntimeReadCount OBJECT-TYPE
      SYNTAX      Counter64
      MAX-ACCESS  read-only
      STATUS      current
      DESCRIPTION "Returns the Number of read requests issued by this store."
      ::= { persistentStoreRuntimeEntry 30  }
   
   
   persistentStoreRuntimeUpdateCount OBJECT-TYPE
      SYNTAX      Counter64
      MAX-ACCESS  read-only
      STATUS      current
      DESCRIPTION "Returns the Number of update requests issued by this store."
      ::= { persistentStoreRuntimeEntry 35  }
   
   
   persistentStoreRuntimeDeleteCount OBJECT-TYPE
      SYNTAX      Counter64
      MAX-ACCESS  read-only
      STATUS      current
      DESCRIPTION "Returns the Number of delete requests issued by this store."
      ::= { persistentStoreRuntimeEntry 40  }
   
   
   persistentStoreRuntimeObjectCount OBJECT-TYPE
      SYNTAX      Counter64
      MAX-ACCESS  read-only
      STATUS      current
      DESCRIPTION "Returns the Number of objects contained in the store."
      ::= { persistentStoreRuntimeEntry 45  }
   
   
   persistentStoreRuntimePhysicalWriteCount OBJECT-TYPE
      SYNTAX      Counter64
      MAX-ACCESS  read-only
      STATUS      current
      DESCRIPTION "Returns the Number of times the store flushed its data to durable storage."
      ::= { persistentStoreRuntimeEntry 50  }
   
   
   persistentStoreConnectionRuntimeTable OBJECT-TYPE
      SYNTAX      SEQUENCE OF PersistentStoreConnectionRuntimeEntry
      MAX-ACCESS  not-accessible
      STATUS      current
      DESCRIPTION "This table represents information about the Persistent Store connections."
      ::= { wls 331  }
      
   
   persistentStoreConnectionRuntimeEntry OBJECT-TYPE
      SYNTAX      PersistentStoreConnectionRuntimeEntry
      MAX-ACCESS  not-accessible
      STATUS      current
      DESCRIPTION "Entry of persistentStoreConnectionRuntimeTable"
      INDEX { persistentStoreConnectionRuntimeIndex}
      ::= { persistentStoreConnectionRuntimeTable 1 }
      
   PersistentStoreConnectionRuntimeEntry ::=
      SEQUENCE
      {
         persistentStoreConnectionRuntimeIndex DisplayString (SIZE (1..16)),
         persistentStoreConnectionRuntimeObjectName DisplayString (SIZE (1..256)),
         persistentStoreConnectionRuntimeType DisplayString (SIZE (1..64)),
         persistentStoreConnectionRuntimeName DisplayString (SIZE (1..64)),
         persistentStoreConnectionRuntimeParent DisplayString (SIZE (1..256)),
         persistentStoreConnectionRuntimeCreateCount Counter64,
         persistentStoreConnectionRuntimeReadCount Counter64,
         persistentStoreConnectionRuntimeUpdateCount Counter64,
         persistentStoreConnectionRuntimeDeleteCount Counter64,
         persistentStoreConnectionRuntimeObjectCount Counter64
      }
      
   
   persistentStoreConnectionRuntimeIndex OBJECT-TYPE
      SYNTAX      DisplayString (SIZE (1..16))
      MAX-ACCESS  read-only
      STATUS      current
      DESCRIPTION "Unique value directed from ObjectName which is used as table index"
      ::= { persistentStoreConnectionRuntimeEntry 1  }
   
   
   persistentStoreConnectionRuntimeObjectName OBJECT-TYPE
      SYNTAX      DisplayString (SIZE (1..256))
      MAX-ACCESS  read-only
      STATUS      current
      DESCRIPTION "JMX-standard MBean name"
      ::= { persistentStoreConnectionRuntimeEntry 5  }
   
   
   persistentStoreConnectionRuntimeType OBJECT-TYPE
      SYNTAX      DisplayString (SIZE (1..64))
      MAX-ACCESS  read-only
      STATUS      current
      DESCRIPTION "BEA-proprietary MBean type"
      ::= { persistentStoreConnectionRuntimeEntry 10  }
   
   
   persistentStoreConnectionRuntimeName OBJECT-TYPE
      SYNTAX      DisplayString (SIZE (1..64))
      MAX-ACCESS  read-only
      STATUS      current
      DESCRIPTION "BEA-proprietary MBean name"
      ::= { persistentStoreConnectionRuntimeEntry 15  }
   
   
   persistentStoreConnectionRuntimeParent OBJECT-TYPE
      SYNTAX      DisplayString (SIZE (1..256))
      MAX-ACCESS  read-only
      STATUS      current
      DESCRIPTION "BEA-proprietary Parent object's identification, with syntax
      <type>:<name>"
      ::= { persistentStoreConnectionRuntimeEntry 20  }
   
   
   persistentStoreConnectionRuntimeCreateCount OBJECT-TYPE
      SYNTAX      Counter64
      MAX-ACCESS  read-only
      STATUS      current
      DESCRIPTION "Returns the Number of create requests issued by this connection."
      ::= { persistentStoreConnectionRuntimeEntry 25  }
   
   
   persistentStoreConnectionRuntimeReadCount OBJECT-TYPE
      SYNTAX      Counter64
      MAX-ACCESS  read-only
      STATUS      current
      DESCRIPTION "Returns the Number of read requests issued by this connection."
      ::= { persistentStoreConnectionRuntimeEntry 30  }
   
   
   persistentStoreConnectionRuntimeUpdateCount OBJECT-TYPE
      SYNTAX      Counter64
      MAX-ACCESS  read-only
      STATUS      current
      DESCRIPTION "Returns the Number of update requests issued by this connection."
      ::= { persistentStoreConnectionRuntimeEntry 35  }
   
   
   persistentStoreConnectionRuntimeDeleteCount OBJECT-TYPE
      SYNTAX      Counter64
      MAX-ACCESS  read-only
      STATUS      current
      DESCRIPTION "Returns the Number of delete requests issued by this connection."
      ::= { persistentStoreConnectionRuntimeEntry 40  }
   
   
   persistentStoreConnectionRuntimeObjectCount OBJECT-TYPE
      SYNTAX      Counter64
      MAX-ACCESS  read-only
      STATUS      current
      DESCRIPTION "Returns the Number of objects contained in this connection."
      ::= { persistentStoreConnectionRuntimeEntry 45  }
   
   
   jvmRuntimeTable OBJECT-TYPE
      SYNTAX      SEQUENCE OF JvmRuntimeEntry
      MAX-ACCESS  not-accessible
      STATUS      current
      DESCRIPTION "This table contains a runtime information about java virtual machine (jvm)."
      ::= { wls 340  }
      
   
   jvmRuntimeEntry OBJECT-TYPE
      SYNTAX      JvmRuntimeEntry
      MAX-ACCESS  not-accessible
      STATUS      current
      DESCRIPTION "Entry of jvmRuntimeTable"
      INDEX { jvmRuntimeIndex}
      ::= { jvmRuntimeTable 1 }
      
   JvmRuntimeEntry ::=
      SEQUENCE
      {
         jvmRuntimeIndex      DisplayString (SIZE (1..16)),
         jvmRuntimeObjectName DisplayString (SIZE (1..256)),
         jvmRuntimeType       DisplayString (SIZE (1..64)),
         jvmRuntimeName       DisplayString (SIZE (1..64)),
         jvmRuntimeParent     DisplayString (SIZE (1..256)),
         jvmRuntimeHeapFreeCurrent Counter64,
         jvmRuntimeHeapSizeCurrent Counter64,
         jvmRuntimeJavaVersion DisplayString (SIZE (1..32)),
         jvmRuntimeJavaVendor DisplayString (SIZE (1..32)),
         jvmRuntimeOSName     DisplayString (SIZE (1..32)),
         jvmRuntimeOSVersion  DisplayString (SIZE (1..32))
      }
      
   
   jvmRuntimeIndex OBJECT-TYPE
      SYNTAX      DisplayString (SIZE (1..16))
      MAX-ACCESS  read-only
      STATUS      current
      DESCRIPTION "Unique value directed from ObjectName which is used as table index"
      ::= { jvmRuntimeEntry 1  }
   
   
   jvmRuntimeObjectName OBJECT-TYPE
      SYNTAX      DisplayString (SIZE (1..256))
      MAX-ACCESS  read-only
      STATUS      current
      DESCRIPTION "JMX-standard MBean name"
      ::= { jvmRuntimeEntry 5  }
   
   
   jvmRuntimeType OBJECT-TYPE
      SYNTAX      DisplayString (SIZE (1..64))
      MAX-ACCESS  read-only
      STATUS      current
      DESCRIPTION "BEA-proprietary MBean type"
      ::= { jvmRuntimeEntry 10  }
   
   
   jvmRuntimeName OBJECT-TYPE
      SYNTAX      DisplayString (SIZE (1..64))
      MAX-ACCESS  read-only
      STATUS      current
      DESCRIPTION "BEA-proprietary MBean name"
      ::= { jvmRuntimeEntry 15  }
   
   
   jvmRuntimeParent OBJECT-TYPE
      SYNTAX      DisplayString (SIZE (1..256))
      MAX-ACCESS  read-only
      STATUS      current
      DESCRIPTION "BEA-proprietary Parent object's identification, with syntax
      <type>:<name>"
      ::= { jvmRuntimeEntry 20  }
   
   
   jvmRuntimeHeapFreeCurrent OBJECT-TYPE
      SYNTAX      Counter64
      MAX-ACCESS  read-only
      STATUS      current
      DESCRIPTION "The current amount of free memory in the JVM heap in bytes."
      ::= { jvmRuntimeEntry 25  }
   
   
   jvmRuntimeHeapSizeCurrent OBJECT-TYPE
      SYNTAX      Counter64
      MAX-ACCESS  read-only
      STATUS      current
      DESCRIPTION "The current size of the JVM heap in bytes"
      ::= { jvmRuntimeEntry 30  }
   
   
   jvmRuntimeJavaVersion OBJECT-TYPE
      SYNTAX      DisplayString (SIZE (1..32))
      MAX-ACCESS  read-only
      STATUS      current
      DESCRIPTION "The Java version of the JVM."
      ::= { jvmRuntimeEntry 35  }
   
   
   jvmRuntimeJavaVendor OBJECT-TYPE
      SYNTAX      DisplayString (SIZE (1..32))
      MAX-ACCESS  read-only
      STATUS      current
      DESCRIPTION "The vendor of the JVM."
      ::= { jvmRuntimeEntry 40  }
   
   
   jvmRuntimeOSName OBJECT-TYPE
      SYNTAX      DisplayString (SIZE (1..32))
      MAX-ACCESS  read-only
      STATUS      current
      DESCRIPTION "The OS upon which the JVM is running."
      ::= { jvmRuntimeEntry 45  }
   
   
   jvmRuntimeOSVersion OBJECT-TYPE
      SYNTAX      DisplayString (SIZE (1..32))
      MAX-ACCESS  read-only
      STATUS      current
      DESCRIPTION "The OS version upon which the JVM is running."
      ::= { jvmRuntimeEntry 50  }
   
   
   logBroadcasterRuntimeTable OBJECT-TYPE
      SYNTAX      SEQUENCE OF LogBroadcasterRuntimeEntry
      MAX-ACCESS  not-accessible
      STATUS      current
      DESCRIPTION "This table broadcasts JMX notifications for each log message generated in
      the local WLS server. There is exactly one implementation of this MBean
      in each WLS server. JMX listeners can register to this MBean and receive
      log notifications. The type of the notification generated is 
      WebLogicLogNotification."
      ::= { wls 350  }
      
   
   logBroadcasterRuntimeEntry OBJECT-TYPE
      SYNTAX      LogBroadcasterRuntimeEntry
      MAX-ACCESS  not-accessible
      STATUS      current
      DESCRIPTION "Entry of logBroadcasterRuntimeTable"
      INDEX { logBroadcasterRuntimeIndex}
      ::= { logBroadcasterRuntimeTable 1 }
      
   LogBroadcasterRuntimeEntry ::=
      SEQUENCE
      {
         logBroadcasterRuntimeIndex DisplayString (SIZE (1..16)),
         logBroadcasterRuntimeObjectName DisplayString (SIZE (1..256)),
         logBroadcasterRuntimeType DisplayString (SIZE (1..64)),
         logBroadcasterRuntimeName DisplayString (SIZE (1..64)),
         logBroadcasterRuntimeParent DisplayString (SIZE (1..256)),
         logBroadcasterRuntimeMessagesLogged Counter64
      }
      
   
   logBroadcasterRuntimeIndex OBJECT-TYPE
      SYNTAX      DisplayString (SIZE (1..16))
      MAX-ACCESS  read-only
      STATUS      current
      DESCRIPTION "Unique value directed from ObjectName which is used as table index"
      ::= { logBroadcasterRuntimeEntry 1  }
   
   
   logBroadcasterRuntimeObjectName OBJECT-TYPE
      SYNTAX      DisplayString (SIZE (1..256))
      MAX-ACCESS  read-only
      STATUS      current
      DESCRIPTION "JMX-standard MBean name"
      ::= { logBroadcasterRuntimeEntry 5  }
   
   
   logBroadcasterRuntimeType OBJECT-TYPE
      SYNTAX      DisplayString (SIZE (1..64))
      MAX-ACCESS  read-only
      STATUS      current
      DESCRIPTION "BEA-proprietary MBean type"
      ::= { logBroadcasterRuntimeEntry 10  }
   
   
   logBroadcasterRuntimeName OBJECT-TYPE
      SYNTAX      DisplayString (SIZE (1..64))
      MAX-ACCESS  read-only
      STATUS      current
      DESCRIPTION "BEA-proprietary MBean name"
      ::= { logBroadcasterRuntimeEntry 15  }
   
   
   logBroadcasterRuntimeParent OBJECT-TYPE
      SYNTAX      DisplayString (SIZE (1..256))
      MAX-ACCESS  read-only
      STATUS      current
      DESCRIPTION "BEA-proprietary Parent object's identification, with syntax
      <type>:<name>"
      ::= { logBroadcasterRuntimeEntry 20  }
   
   
   logBroadcasterRuntimeMessagesLogged OBJECT-TYPE
      SYNTAX      Counter64
      MAX-ACCESS  read-only
      STATUS      current
      DESCRIPTION "Number of total log messages generated by this instance of the WebLogic server."
      ::= { logBroadcasterRuntimeEntry 25  }
   
   
   messageDrivenEJBRuntimeTable OBJECT-TYPE
      SYNTAX      SEQUENCE OF MessageDrivenEJBRuntimeEntry
      MAX-ACCESS  not-accessible
      STATUS      current
      DESCRIPTION "Provides values for Runtime MessageDriven EJB's"
      ::= { wls 351  }
      
   
   messageDrivenEJBRuntimeEntry OBJECT-TYPE
      SYNTAX      MessageDrivenEJBRuntimeEntry
      MAX-ACCESS  not-accessible
      STATUS      current
      DESCRIPTION "Entry of messageDrivenEJBRuntimeTable"
      INDEX { messageDrivenEJBRuntimeIndex}
      ::= { messageDrivenEJBRuntimeTable 1 }
      
   MessageDrivenEJBRuntimeEntry ::=
      SEQUENCE
      {
         messageDrivenEJBRuntimeIndex DisplayString (SIZE (1..16)),
         messageDrivenEJBRuntimeObjectName DisplayString (SIZE (1..256)),
         messageDrivenEJBRuntimeType DisplayString (SIZE (1..64)),
         messageDrivenEJBRuntimeName DisplayString (SIZE (1..64)),
         messageDrivenEJBRuntimeParent DisplayString (SIZE (1..256)),
         messageDrivenEJBRuntimeJMSConnectionAlive INTEGER,
         messageDrivenEJBRuntimeLastExceptionAsString OCTET STRING,
         messageDrivenEJBRuntimeDestination OCTET STRING,
         messageDrivenEJBRuntimeMDBStatus OCTET STRING,
         messageDrivenEJBRuntimeEJBName OCTET STRING,
         messageDrivenEJBRuntimeConnectionStatus OCTET STRING,
         messageDrivenEJBRuntimeSuspendCount INTEGER,
         messageDrivenEJBRuntimeProcessedMessageCount Counter64,
         messageDrivenEJBRuntimeJmsClientID OCTET STRING
      }
      
   
   messageDrivenEJBRuntimeIndex OBJECT-TYPE
      SYNTAX      DisplayString (SIZE (1..16))
      MAX-ACCESS  read-only
      STATUS      current
      DESCRIPTION "Unique value directed from ObjectName which is used as table index"
      ::= { messageDrivenEJBRuntimeEntry 1  }
   
   
   messageDrivenEJBRuntimeObjectName OBJECT-TYPE
      SYNTAX      DisplayString (SIZE (1..256))
      MAX-ACCESS  read-only
      STATUS      current
      DESCRIPTION "JMX-standard MBean name"
      ::= { messageDrivenEJBRuntimeEntry 5  }
   
   
   messageDrivenEJBRuntimeType OBJECT-TYPE
      SYNTAX      DisplayString (SIZE (1..64))
      MAX-ACCESS  read-only
      STATUS      current
      DESCRIPTION "BEA-proprietary MBean type"
      ::= { messageDrivenEJBRuntimeEntry 10  }
   
   
   messageDrivenEJBRuntimeName OBJECT-TYPE
      SYNTAX      DisplayString (SIZE (1..64))
      MAX-ACCESS  read-only
      STATUS      current
      DESCRIPTION "BEA-proprietary MBean name"
      ::= { messageDrivenEJBRuntimeEntry 15  }
   
   
   messageDrivenEJBRuntimeParent OBJECT-TYPE
      SYNTAX      DisplayString (SIZE (1..256))
      MAX-ACCESS  read-only
      STATUS      current
      DESCRIPTION "BEA-proprietary Parent object's identification, with syntax
      <type>:<name>"
      ::= { messageDrivenEJBRuntimeEntry 20  }
   
   
   messageDrivenEJBRuntimeJMSConnectionAlive OBJECT-TYPE
      SYNTAX      INTEGER
      MAX-ACCESS  read-only
      STATUS      current
      DESCRIPTION "Is jms connection alive."
      ::= { messageDrivenEJBRuntimeEntry 25  }
   
   
   messageDrivenEJBRuntimeLastExceptionAsString OBJECT-TYPE
      SYNTAX      OCTET STRING
      MAX-ACCESS  read-only
      STATUS      current
      DESCRIPTION "Provides the last exception as String this MDB encountered"
      ::= { messageDrivenEJBRuntimeEntry 26  }
   
   
   messageDrivenEJBRuntimeDestination OBJECT-TYPE
      SYNTAX      OCTET STRING
      MAX-ACCESS  read-only
      STATUS      current
      DESCRIPTION "Provides a count of the Message Driven Bean destination"
      ::= { messageDrivenEJBRuntimeEntry 27  }
   
   
   messageDrivenEJBRuntimeMDBStatus OBJECT-TYPE
      SYNTAX      OCTET STRING
      MAX-ACCESS  read-only
      STATUS      current
      DESCRIPTION "Provides the Message Driven Bean status.  MDBStatus is used after the MDB is connected to the destination. MDBStatus can be Running or Suspended."
      ::= { messageDrivenEJBRuntimeEntry 28  }
   
   
   messageDrivenEJBRuntimeEJBName OBJECT-TYPE
      SYNTAX      OCTET STRING
      MAX-ACCESS  read-only
      STATUS      current
      DESCRIPTION "Provides the ejb-name for this EJB as defined in the ejb-jar.xml deployment descriptor."
      ::= { messageDrivenEJBRuntimeEntry 29  }
   
   
   messageDrivenEJBRuntimeConnectionStatus OBJECT-TYPE
      SYNTAX      OCTET STRING
      MAX-ACCESS  read-only
      STATUS      current
      DESCRIPTION "Provides the connection status for the Message Driven Bean. ConnectionStatus can be Connected or Reconnecting."
      ::= { messageDrivenEJBRuntimeEntry 30  }
   
   
   messageDrivenEJBRuntimeSuspendCount OBJECT-TYPE
      SYNTAX      INTEGER
      MAX-ACCESS  read-only
      STATUS      current
      DESCRIPTION "Provides a count of the total number of times this MDB is suspended by the user or the EJB container."
      ::= { messageDrivenEJBRuntimeEntry 31  }
   
   
   messageDrivenEJBRuntimeProcessedMessageCount OBJECT-TYPE
      SYNTAX      Counter64
      MAX-ACCESS  read-only
      STATUS      current
      DESCRIPTION "Provides a count of the total number of messages processed by this Message Driven Bean."
      ::= { messageDrivenEJBRuntimeEntry 32  }
   
   
   messageDrivenEJBRuntimeJmsClientID OBJECT-TYPE
      SYNTAX      OCTET STRING
      MAX-ACCESS  read-only
      STATUS      current
      DESCRIPTION "Provides a count of the Message Driven Bean jmsClientID"
      ::= { messageDrivenEJBRuntimeEntry 33  }
   
   
   messagingBridgeRuntimeTable OBJECT-TYPE
      SYNTAX      SEQUENCE OF MessagingBridgeRuntimeEntry
      MAX-ACCESS  not-accessible
      STATUS      current
      DESCRIPTION "This class is used for monitoring a WebLogic messaging bridge."
      ::= { wls 354  }
      
   
   messagingBridgeRuntimeEntry OBJECT-TYPE
      SYNTAX      MessagingBridgeRuntimeEntry
      MAX-ACCESS  not-accessible
      STATUS      current
      DESCRIPTION "Entry of messagingBridgeRuntimeTable"
      INDEX { messagingBridgeRuntimeIndex}
      ::= { messagingBridgeRuntimeTable 1 }
      
   MessagingBridgeRuntimeEntry ::=
      SEQUENCE
      {
         messagingBridgeRuntimeIndex DisplayString (SIZE (1..16)),
         messagingBridgeRuntimeObjectName DisplayString (SIZE (1..256)),
         messagingBridgeRuntimeType DisplayString (SIZE (1..64)),
         messagingBridgeRuntimeName DisplayString (SIZE (1..64)),
         messagingBridgeRuntimeParent DisplayString (SIZE (1..256)),
         messagingBridgeRuntimeState DisplayString,
         messagingBridgeRuntimeDescription DisplayString
      }
      
   
   messagingBridgeRuntimeIndex OBJECT-TYPE
      SYNTAX      DisplayString (SIZE (1..16))
      MAX-ACCESS  read-only
      STATUS      current
      DESCRIPTION "Unique value directed from ObjectName which is used as table index"
      ::= { messagingBridgeRuntimeEntry 1  }
   
   
   messagingBridgeRuntimeObjectName OBJECT-TYPE
      SYNTAX      DisplayString (SIZE (1..256))
      MAX-ACCESS  read-only
      STATUS      current
      DESCRIPTION "JMX-standard MBean name"
      ::= { messagingBridgeRuntimeEntry 5  }
   
   
   messagingBridgeRuntimeType OBJECT-TYPE
      SYNTAX      DisplayString (SIZE (1..64))
      MAX-ACCESS  read-only
      STATUS      current
      DESCRIPTION "BEA-proprietary MBean type"
      ::= { messagingBridgeRuntimeEntry 10  }
   
   
   messagingBridgeRuntimeName OBJECT-TYPE
      SYNTAX      DisplayString (SIZE (1..64))
      MAX-ACCESS  read-only
      STATUS      current
      DESCRIPTION "BEA-proprietary MBean name"
      ::= { messagingBridgeRuntimeEntry 15  }
   
   
   messagingBridgeRuntimeParent OBJECT-TYPE
      SYNTAX      DisplayString (SIZE (1..256))
      MAX-ACCESS  read-only
      STATUS      current
      DESCRIPTION "BEA-proprietary Parent object's identification, with syntax
      <type>:<name>"
      ::= { messagingBridgeRuntimeEntry 20  }
   
   
   messagingBridgeRuntimeState OBJECT-TYPE
      SYNTAX      DisplayString
      MAX-ACCESS  read-only
      STATUS      current
      DESCRIPTION "Returns the state of the messaging bridge"
      ::= { messagingBridgeRuntimeEntry 21  }
   
   
   messagingBridgeRuntimeDescription OBJECT-TYPE
      SYNTAX      DisplayString
      MAX-ACCESS  read-only
      STATUS      current
      DESCRIPTION "Returns the reason if the messaging bridge is not running"
      ::= { messagingBridgeRuntimeEntry 22  }
   
   
   nonXAResourceRuntimeTable OBJECT-TYPE
      SYNTAX      SEQUENCE OF NonXAResourceRuntimeEntry
      MAX-ACCESS  not-accessible
      STATUS      current
      DESCRIPTION "This table is used for accessing transaction
      runtime characteristics within a WebLogic server for NonXAResources."
      ::= { wls 356  }
      
   
   nonXAResourceRuntimeEntry OBJECT-TYPE
      SYNTAX      NonXAResourceRuntimeEntry
      MAX-ACCESS  not-accessible
      STATUS      current
      DESCRIPTION "Entry of nonXAResourceRuntimeTable"
      INDEX { nonXAResourceRuntimeIndex}
      ::= { nonXAResourceRuntimeTable 1 }
      
   NonXAResourceRuntimeEntry ::=
      SEQUENCE
      {
         nonXAResourceRuntimeIndex DisplayString (SIZE (1..16)),
         nonXAResourceRuntimeObjectName DisplayString (SIZE (1..256)),
         nonXAResourceRuntimeType DisplayString (SIZE (1..64)),
         nonXAResourceRuntimeName DisplayString (SIZE (1..64)),
         nonXAResourceRuntimeParent DisplayString (SIZE (1..256)),
         nonXAResourceRuntimeTransactionTotalCount Counter64,
         nonXAResourceRuntimeTransactionCommittedTotalCount Counter64,
         nonXAResourceRuntimeTransactionRolledBackTotalCount Counter64,
         nonXAResourceRuntimeTransactionHeuristicsTotalCount Counter64,
         nonXAResourceRuntimeNonXAResourceName DisplayString (SIZE (1..256))
      }
      
   
   nonXAResourceRuntimeIndex OBJECT-TYPE
      SYNTAX      DisplayString (SIZE (1..16))
      MAX-ACCESS  read-only
      STATUS      current
      DESCRIPTION "Unique value directed from ObjectName which is used as table index"
      ::= { nonXAResourceRuntimeEntry 1  }
   
   
   nonXAResourceRuntimeObjectName OBJECT-TYPE
      SYNTAX      DisplayString (SIZE (1..256))
      MAX-ACCESS  read-only
      STATUS      current
      DESCRIPTION "JMX-standard MBean name"
      ::= { nonXAResourceRuntimeEntry 5  }
   
   
   nonXAResourceRuntimeType OBJECT-TYPE
      SYNTAX      DisplayString (SIZE (1..64))
      MAX-ACCESS  read-only
      STATUS      current
      DESCRIPTION "BEA-proprietary MBean type"
      ::= { nonXAResourceRuntimeEntry 10  }
   
   
   nonXAResourceRuntimeName OBJECT-TYPE
      SYNTAX      DisplayString (SIZE (1..64))
      MAX-ACCESS  read-only
      STATUS      current
      DESCRIPTION "BEA-proprietary MBean name"
      ::= { nonXAResourceRuntimeEntry 15  }
   
   
   nonXAResourceRuntimeParent OBJECT-TYPE
      SYNTAX      DisplayString (SIZE (1..256))
      MAX-ACCESS  read-only
      STATUS      current
      DESCRIPTION "BEA-proprietary Parent object's identification, with syntax
      <type>:<name>"
      ::= { nonXAResourceRuntimeEntry 20  }
   
   
   nonXAResourceRuntimeTransactionTotalCount OBJECT-TYPE
      SYNTAX      Counter64
      MAX-ACCESS  read-only
      STATUS      current
      DESCRIPTION "The total number of transactions processed.
      This total includes all committed, rolled back
      and heuristic transaction completions."
      ::= { nonXAResourceRuntimeEntry 25  }
   
   
   nonXAResourceRuntimeTransactionCommittedTotalCount OBJECT-TYPE
      SYNTAX      Counter64
      MAX-ACCESS  read-only
      STATUS      current
      DESCRIPTION "The number of committed transactions."
      ::= { nonXAResourceRuntimeEntry 30  }
   
   
   nonXAResourceRuntimeTransactionRolledBackTotalCount OBJECT-TYPE
      SYNTAX      Counter64
      MAX-ACCESS  read-only
      STATUS      current
      DESCRIPTION "The number of transactions that were rolled back."
      ::= { nonXAResourceRuntimeEntry 35  }
   
   
   nonXAResourceRuntimeTransactionHeuristicsTotalCount OBJECT-TYPE
      SYNTAX      Counter64
      MAX-ACCESS  read-only
      STATUS      current
      DESCRIPTION "The number of transactions that completed with a
      heuristic status."
      ::= { nonXAResourceRuntimeEntry 40  }
   
   
   nonXAResourceRuntimeNonXAResourceName OBJECT-TYPE
      SYNTAX      DisplayString (SIZE (1..256))
      MAX-ACCESS  read-only
      STATUS      current
      DESCRIPTION "Returns the resource name."
      ::= { nonXAResourceRuntimeEntry 45  }
   
   
   serverRuntimeTable OBJECT-TYPE
      SYNTAX      SEQUENCE OF ServerRuntimeEntry
      MAX-ACCESS  not-accessible
      STATUS      current
      DESCRIPTION "Generated SNMP Table."
      ::= { wls 360  }
      
   
   serverRuntimeEntry OBJECT-TYPE
      SYNTAX      ServerRuntimeEntry
      MAX-ACCESS  not-accessible
      STATUS      current
      DESCRIPTION "Entry of serverRuntimeTable"
      INDEX { serverRuntimeIndex}
      ::= { serverRuntimeTable 1 }
      
   ServerRuntimeEntry ::=
      SEQUENCE
      {
         serverRuntimeIndex   DisplayString (SIZE (1..16)),
         serverRuntimeObjectName DisplayString (SIZE (1..256)),
         serverRuntimeType    DisplayString (SIZE (1..64)),
         serverRuntimeName    DisplayString (SIZE (1..64)),
         serverRuntimeParent  DisplayString (SIZE (1..256)),
         serverRuntimeActivationTime Counter64,
         serverRuntimeListenAddress DisplayString (SIZE (1..256)),
         serverRuntimeListenPort INTEGER,
         serverRuntimeSSLListenAddress DisplayString (SIZE (1..256)),
         serverRuntimeJVMID   DisplayString (SIZE (1..64)),
         serverRuntimeOpenSocketsCurrentCount INTEGER,
         serverRuntimeRestartsTotalCount INTEGER,
         serverRuntimeState   DisplayString (SIZE (1..16)),
         serverRuntimeWeblogicVersion DisplayString (SIZE (1..16)),
         serverRuntimeAdminServerHost DisplayString (SIZE (1..256)),
         serverRuntimeAdminServerListenPort INTEGER,
         serverRuntimeClusterRuntime DisplayString (SIZE (1..256)),
         serverRuntimeAdministrationPort INTEGER,
         serverRuntimeSocketsOpenedTotalCount Counter64,
         serverRuntimeSSLListenPort INTEGER,
         serverRuntimeAdministrationPortEnabled INTEGER,
         serverRuntimeAdminServer INTEGER,
         serverRuntimeAdminServerListenPortSecure INTEGER,
         serverRuntimeListenPortEnabled INTEGER,
         serverRuntimeSSLListenPortEnabled INTEGER,
         serverRuntimeRestartRequired OCTET STRING,
         serverRuntimeServerClasspath OCTET STRING,
         serverRuntimeCurrentMachine OCTET STRING,
         serverRuntimeAdministrationURL OCTET STRING,
         serverRuntimeDefaultURL OCTET STRING,
         serverRuntimeStateVal INTEGER,
         serverRuntimeCurrentDirectory OCTET STRING
      }
      
   
   serverRuntimeIndex OBJECT-TYPE
      SYNTAX      DisplayString (SIZE (1..16))
      MAX-ACCESS  read-only
      STATUS      current
      DESCRIPTION "Unique value directed from ObjectName which is used as table index"
      ::= { serverRuntimeEntry 1  }
   
   
   serverRuntimeObjectName OBJECT-TYPE
      SYNTAX      DisplayString (SIZE (1..256))
      MAX-ACCESS  read-only
      STATUS      current
      DESCRIPTION "JMX-standard MBean name"
      ::= { serverRuntimeEntry 5  }
   
   
   serverRuntimeType OBJECT-TYPE
      SYNTAX      DisplayString (SIZE (1..64))
      MAX-ACCESS  read-only
      STATUS      current
      DESCRIPTION "BEA-proprietary MBean type"
      ::= { serverRuntimeEntry 10  }
   
   
   serverRuntimeName OBJECT-TYPE
      SYNTAX      DisplayString (SIZE (1..64))
      MAX-ACCESS  read-only
      STATUS      current
      DESCRIPTION "BEA-proprietary MBean name"
      ::= { serverRuntimeEntry 15  }
   
   
   serverRuntimeParent OBJECT-TYPE
      SYNTAX      DisplayString (SIZE (1..256))
      MAX-ACCESS  read-only
      STATUS      current
      DESCRIPTION "BEA-proprietary Parent object's identification, with syntax
      <type>:<name>"
      ::= { serverRuntimeEntry 20  }
   
   
   serverRuntimeActivationTime OBJECT-TYPE
      SYNTAX      Counter64
      MAX-ACCESS  read-only
      STATUS      current
      DESCRIPTION "Return the time when the server was started."
      ::= { serverRuntimeEntry 25  }
   
   
   serverRuntimeListenAddress OBJECT-TYPE
      SYNTAX      DisplayString (SIZE (1..256))
      MAX-ACCESS  read-only
      STATUS      current
      DESCRIPTION "Return the address on which this server is listening for
      connections. For example this might return the string:
              santiago/172.17.9.220"
      ::= { serverRuntimeEntry 30  }
   
   
   serverRuntimeListenPort OBJECT-TYPE
      SYNTAX      INTEGER
      MAX-ACCESS  read-only
      STATUS      current
      DESCRIPTION "Return the port on which this server is listening for connections."
      ::= { serverRuntimeEntry 35  }
   
   
   serverRuntimeSSLListenAddress OBJECT-TYPE
      SYNTAX      DisplayString (SIZE (1..256))
      MAX-ACCESS  read-only
      STATUS      current
      DESCRIPTION "Return the address on which this server is listening for
      connections. For example this might return the string:
      santiago/172.17.9.220"
      ::= { serverRuntimeEntry 40  }
   
   
   serverRuntimeJVMID OBJECT-TYPE
      SYNTAX      DisplayString (SIZE (1..64))
      MAX-ACCESS  read-only
      STATUS      current
      DESCRIPTION "Return the JVMID of the server."
      ::= { serverRuntimeEntry 45  }
   
   
   serverRuntimeOpenSocketsCurrentCount OBJECT-TYPE
      SYNTAX      INTEGER
      MAX-ACCESS  read-only
      STATUS      current
      DESCRIPTION "Return the current number sockets registered for socket muxing on this 
      server."
      ::= { serverRuntimeEntry 50  }
   
   
   serverRuntimeRestartsTotalCount OBJECT-TYPE
      SYNTAX      INTEGER
      MAX-ACCESS  read-only
      STATUS      current
      DESCRIPTION "Return the total number of restarts for this server since the cluster
      was last activated."
      ::= { serverRuntimeEntry 55  }
   
   
   serverRuntimeState OBJECT-TYPE
      SYNTAX      DisplayString (SIZE (1..16))
      MAX-ACCESS  read-only
      STATUS      current
      DESCRIPTION "Return the current state of the server.  Legal values are
      Initializing, Suspended, Running, ShuttingDown."
      ::= { serverRuntimeEntry 60  }
   
   
   serverRuntimeWeblogicVersion OBJECT-TYPE
      SYNTAX      DisplayString (SIZE (1..16))
      MAX-ACCESS  read-only
      STATUS      current
      DESCRIPTION "Return the version of the server"
      ::= { serverRuntimeEntry 65  }
   
   
   serverRuntimeAdminServerHost OBJECT-TYPE
      SYNTAX      DisplayString (SIZE (1..256))
      MAX-ACCESS  read-only
      STATUS      current
      DESCRIPTION "Return the address on which admin server is listening for
      connections. For example this might return the string:
      santiago"
      ::= { serverRuntimeEntry 70  }
   
   
   serverRuntimeAdminServerListenPort OBJECT-TYPE
      SYNTAX      INTEGER
      MAX-ACCESS  read-only
      STATUS      current
      DESCRIPTION "Return the port on which admin server is listening for
      connections."
      ::= { serverRuntimeEntry 75  }
   
   
   serverRuntimeClusterRuntime OBJECT-TYPE
      SYNTAX      DisplayString (SIZE (1..256))
      MAX-ACCESS  read-only
      STATUS      current
      DESCRIPTION "Return an mbean which represents this server's view of its cluster, if any."
      ::= { serverRuntimeEntry 80  }
   
   
   serverRuntimeAdministrationPort OBJECT-TYPE
      SYNTAX      INTEGER
      MAX-ACCESS  read-only
      STATUS      current
      DESCRIPTION "Return the administration port on which this server is listening for"
      ::= { serverRuntimeEntry 81  }
   
   
   serverRuntimeSocketsOpenedTotalCount OBJECT-TYPE
      SYNTAX      Counter64
      MAX-ACCESS  read-only
      STATUS      current
      DESCRIPTION "Return the total number of registrations for socket muxing on this sever."
      ::= { serverRuntimeEntry 82  }
   
   
   serverRuntimeSSLListenPort OBJECT-TYPE
      SYNTAX      INTEGER
      MAX-ACCESS  read-only
      STATUS      current
      DESCRIPTION "Return the port on which this server is listening for SSL Connections"
      ::= { serverRuntimeEntry 83  }
   
   
   serverRuntimeAdministrationPortEnabled OBJECT-TYPE
      SYNTAX      INTEGER
      MAX-ACCESS  read-only
      STATUS      current
      DESCRIPTION "Return if the administrationPort is enabled on the  server"
      ::= { serverRuntimeEntry 84  }
   
   
   serverRuntimeAdminServer OBJECT-TYPE
      SYNTAX      INTEGER
      MAX-ACCESS  read-only
      STATUS      current
      DESCRIPTION "Returns true id its an admin server"
      ::= { serverRuntimeEntry 85  }
   
   
   serverRuntimeAdminServerListenPortSecure OBJECT-TYPE
      SYNTAX      INTEGER
      MAX-ACCESS  read-only
      STATUS      current
      DESCRIPTION "Return the secureType on which admin server is listening for connections."
      ::= { serverRuntimeEntry 86  }
   
   
   serverRuntimeListenPortEnabled OBJECT-TYPE
      SYNTAX      INTEGER
      MAX-ACCESS  read-only
      STATUS      current
      DESCRIPTION "Return if the default listenPort is enabled on the  server"
      ::= { serverRuntimeEntry 87  }
   
   
   serverRuntimeSSLListenPortEnabled OBJECT-TYPE
      SYNTAX      INTEGER
      MAX-ACCESS  read-only
      STATUS      current
      DESCRIPTION "Return if the default lSSListenPort is enabled on the  server"
      ::= { serverRuntimeEntry 88  }
   
   
   serverRuntimeRestartRequired OBJECT-TYPE
      SYNTAX      OCTET STRING
      MAX-ACCESS  read-only
      STATUS      current
      DESCRIPTION "Indicates whether the server must be restarted in order to activate configuration changes."
      ::= { serverRuntimeEntry 89  }
   
   
   serverRuntimeServerClasspath OBJECT-TYPE
      SYNTAX      OCTET STRING
      MAX-ACCESS  read-only
      STATUS      current
      DESCRIPTION "Get the classpath for this server including domain/lib contents that are automatically picked up and appended to the classpath."
      ::= { serverRuntimeEntry 90  }
   
   
   serverRuntimeCurrentMachine OBJECT-TYPE
      SYNTAX      OCTET STRING
      MAX-ACCESS  read-only
      STATUS      current
      DESCRIPTION "Return the machine on which the server is running. This will be different from the configuration if the server gets migrated automatically. * @return Machine on which server is running."
      ::= { serverRuntimeEntry 91  }
   
   
   serverRuntimeAdministrationURL OBJECT-TYPE
      SYNTAX      OCTET STRING
      MAX-ACCESS  read-only
      STATUS      current
      DESCRIPTION "The URL that the server and its clients use for administrative connections.  If no administration channel is enabled, then this method returns the URL for connections through the default channel. If the default channel is de-activated, this method returns the URL for a secure channel. If no secure channel is enabled, the method returns null.  The returned URL will be consistent with dynamic channel updates."
      ::= { serverRuntimeEntry 92  }
   
   
   serverRuntimeDefaultURL OBJECT-TYPE
      SYNTAX      OCTET STRING
      MAX-ACCESS  read-only
      STATUS      current
      DESCRIPTION "The URL that clients use to connect to this server's default network channel.  The returned value indicates the default protocol, listen address and listen port: protocol://listen-address:listen-port   Note:   The default protocol, listen address and listen port are persisted in the domain's config.xml file, however when a server instance is started, command-line options can override these persisted values. This getDefaultURL method returns the URL values that are currently being used, not necessarily the values that are specified in config.xml.    The returned URL will be consistent with dynamic channel updates."
      ::= { serverRuntimeEntry 93  }
   
   
   serverRuntimeStateVal OBJECT-TYPE
      SYNTAX      INTEGER
      MAX-ACCESS  read-only
      STATUS      current
      DESCRIPTION "Returns current state of the server as in integer.."
      ::= { serverRuntimeEntry 94  }
   
   
   serverRuntimeCurrentDirectory OBJECT-TYPE
      SYNTAX      OCTET STRING
      MAX-ACCESS  read-only
      STATUS      current
      DESCRIPTION "The absolute path of the directory from which the server was started.  This may be used in conjunction with other relative paths in ServerMBean to compute full paths."
      ::= { serverRuntimeEntry 95  }
   
   
   serverLifeCycleRuntimeTable OBJECT-TYPE
      SYNTAX      SEQUENCE OF ServerLifeCycleRuntimeEntry
      MAX-ACCESS  not-accessible
      STATUS      current
      DESCRIPTION "Provides values for Runtime server life cycle"
      ::= { wls 361  }
      
   
   serverLifeCycleRuntimeEntry OBJECT-TYPE
      SYNTAX      ServerLifeCycleRuntimeEntry
      MAX-ACCESS  not-accessible
      STATUS      current
      DESCRIPTION "Entry of serverLifeCycleRuntimeTable"
      INDEX { serverLifeCycleRuntimeIndex}
      ::= { serverLifeCycleRuntimeTable 1 }
      
   ServerLifeCycleRuntimeEntry ::=
      SEQUENCE
      {
         serverLifeCycleRuntimeIndex DisplayString (SIZE (1..16)),
         serverLifeCycleRuntimeObjectName DisplayString (SIZE (1..256)),
         serverLifeCycleRuntimeType DisplayString (SIZE (1..64)),
         serverLifeCycleRuntimeName DisplayString (SIZE (1..64)),
         serverLifeCycleRuntimeParent DisplayString (SIZE (1..256)),
         serverLifeCycleRuntimeState DisplayString,
         serverLifeCycleRuntimeStateVal INTEGER,
         serverLifeCycleRuntimeNodeManagerRestartCount INTEGER
      }
      
   
   serverLifeCycleRuntimeIndex OBJECT-TYPE
      SYNTAX      DisplayString (SIZE (1..16))
      MAX-ACCESS  read-only
      STATUS      current
      DESCRIPTION "Unique value directed from ObjectName which is used as table index"
      ::= { serverLifeCycleRuntimeEntry 1  }
   
   
   serverLifeCycleRuntimeObjectName OBJECT-TYPE
      SYNTAX      DisplayString (SIZE (1..256))
      MAX-ACCESS  read-only
      STATUS      current
      DESCRIPTION "JMX-standard MBean name"
      ::= { serverLifeCycleRuntimeEntry 5  }
   
   
   serverLifeCycleRuntimeType OBJECT-TYPE
      SYNTAX      DisplayString (SIZE (1..64))
      MAX-ACCESS  read-only
      STATUS      current
      DESCRIPTION "BEA-proprietary MBean type"
      ::= { serverLifeCycleRuntimeEntry 10  }
   
   
   serverLifeCycleRuntimeName OBJECT-TYPE
      SYNTAX      DisplayString (SIZE (1..64))
      MAX-ACCESS  read-only
      STATUS      current
      DESCRIPTION "BEA-proprietary MBean name"
      ::= { serverLifeCycleRuntimeEntry 15  }
   
   
   serverLifeCycleRuntimeParent OBJECT-TYPE
      SYNTAX      DisplayString (SIZE (1..256))
      MAX-ACCESS  read-only
      STATUS      current
      DESCRIPTION "BEA-proprietary Parent object's identification, with syntax
      <type>:<name>"
      ::= { serverLifeCycleRuntimeEntry 20  }
   
   
   serverLifeCycleRuntimeState OBJECT-TYPE
      SYNTAX      DisplayString
      MAX-ACCESS  read-only
      STATUS      current
      DESCRIPTION "gets the state."
      ::= { serverLifeCycleRuntimeEntry 25  }
   
   
   serverLifeCycleRuntimeStateVal OBJECT-TYPE
      SYNTAX      INTEGER
      MAX-ACCESS  read-only
      STATUS      current
      DESCRIPTION "state val."
      ::= { serverLifeCycleRuntimeEntry 30  }
   
   
   serverLifeCycleRuntimeNodeManagerRestartCount OBJECT-TYPE
      SYNTAX      INTEGER
      MAX-ACCESS  read-only
      STATUS      current
      DESCRIPTION "Number of times the server has been restarted using the NodeManager since creation. The first start does not count. The count is valid only if the NodeManager is used to start and restart the server everytime."
      ::= { serverLifeCycleRuntimeEntry 31  }
   
   
   manReplicationRuntimeTable OBJECT-TYPE
      SYNTAX      SEQUENCE OF ManReplicationRuntimeEntry
      MAX-ACCESS  not-accessible
      STATUS      current
      DESCRIPTION "MAN Replication details."
      ::= { wls 362  }
      
   
   manReplicationRuntimeEntry OBJECT-TYPE
      SYNTAX      ManReplicationRuntimeEntry
      MAX-ACCESS  not-accessible
      STATUS      current
      DESCRIPTION "Entry of MANReplicationRuntimeTable"
      INDEX { manReplicationRuntimeIndex}
      ::= { manReplicationRuntimeTable 1 }
      
   ManReplicationRuntimeEntry ::=
      SEQUENCE
      {
         manReplicationRuntimeIndex DisplayString (SIZE (1..16)),
         manReplicationRuntimeObjectName DisplayString (SIZE (1..256)),
         manReplicationRuntimeType DisplayString (SIZE (1..64)),
         manReplicationRuntimeName DisplayString (SIZE (1..64)),
         manReplicationRuntimeParent DisplayString (SIZE (1..256)),
         manReplicationRuntimeSecondaryServerName DisplayString (SIZE (1..128)),
         manReplicationRuntimeSecondaryServerDetails DisplayString (SIZE (1..256)),
         manReplicationRuntimePrimaryCount Counter64,
         manReplicationRuntimeSecondaryCount Counter64,
         manReplicationRuntimeRemoteClusterReachable INTEGER
                     {
                        true(1),
                        false(2)
                     }
      }
      
   
   manReplicationRuntimeIndex OBJECT-TYPE
      SYNTAX      DisplayString (SIZE (1..16))
      MAX-ACCESS  read-only
      STATUS      current
      DESCRIPTION "Unique value directed from ObjectName which is used as table index"
      ::= { manReplicationRuntimeEntry 1  }
   
   
   manReplicationRuntimeObjectName OBJECT-TYPE
      SYNTAX      DisplayString (SIZE (1..256))
      MAX-ACCESS  read-only
      STATUS      current
      DESCRIPTION "JMX-standard MBean name"
      ::= { manReplicationRuntimeEntry 5  }
   
   
   manReplicationRuntimeType OBJECT-TYPE
      SYNTAX      DisplayString (SIZE (1..64))
      MAX-ACCESS  read-only
      STATUS      current
      DESCRIPTION "BEA-proprietary MBean type"
      ::= { manReplicationRuntimeEntry 10  }
   
   
   manReplicationRuntimeName OBJECT-TYPE
      SYNTAX      DisplayString (SIZE (1..64))
      MAX-ACCESS  read-only
      STATUS      current
      DESCRIPTION "BEA-proprietary MBean name"
      ::= { manReplicationRuntimeEntry 15  }
   
   
   manReplicationRuntimeParent OBJECT-TYPE
      SYNTAX      DisplayString (SIZE (1..256))
      MAX-ACCESS  read-only
      STATUS      current
      DESCRIPTION "BEA-proprietary Parent object's identification, with syntax
      <type>:<name>"
      ::= { manReplicationRuntimeEntry 20  }
   
   
   manReplicationRuntimeSecondaryServerName OBJECT-TYPE
      SYNTAX      DisplayString (SIZE (1..128))
      MAX-ACCESS  read-only
      STATUS      current
      DESCRIPTION "Returns the name of the secondary server."
      ::= { manReplicationRuntimeEntry 25  }
   
   
   manReplicationRuntimeSecondaryServerDetails OBJECT-TYPE
      SYNTAX      DisplayString (SIZE (1..256))
      MAX-ACCESS  read-only
      STATUS      current
      DESCRIPTION "Returns the detailed information about the secondary server."
      ::= { manReplicationRuntimeEntry 30  }
   
   
   manReplicationRuntimePrimaryCount OBJECT-TYPE
      SYNTAX      Counter64
      MAX-ACCESS  read-only
      STATUS      current
      DESCRIPTION "Returns the number of object that the local server hosts as primaries."
      ::= { manReplicationRuntimeEntry 35  }
   
   
   manReplicationRuntimeSecondaryCount OBJECT-TYPE
      SYNTAX      Counter64
      MAX-ACCESS  read-only
      STATUS      current
      DESCRIPTION "Returns the number of object that the local server hosts as secondaries."
      ::= { manReplicationRuntimeEntry 40  }
   
   
   manReplicationRuntimeRemoteClusterReachable OBJECT-TYPE
      SYNTAX      INTEGER
                  {
                     true(1),
                     false(2)
                  }
      
      MAX-ACCESS  read-only
      STATUS      current
      DESCRIPTION "Returns true if the remote cluster is reachable."
      ::= { manReplicationRuntimeEntry 45  }
   
   
   maxThreadsConstraintRuntimeTable OBJECT-TYPE
      SYNTAX      SEQUENCE OF MaxThreadsConstraintRuntimeEntry
      MAX-ACCESS  not-accessible
      STATUS      current
      DESCRIPTION "Provides values for Max Threads Constraints for the server"
      ::= { wls 363  }
      
   
   maxThreadsConstraintRuntimeEntry OBJECT-TYPE
      SYNTAX      MaxThreadsConstraintRuntimeEntry
      MAX-ACCESS  not-accessible
      STATUS      current
      DESCRIPTION "Entry of maxThreadsConstraintRuntimeTable"
      INDEX { maxThreadsConstraintRuntimeIndex}
      ::= { maxThreadsConstraintRuntimeTable 1 }
      
   MaxThreadsConstraintRuntimeEntry ::=
      SEQUENCE
      {
         maxThreadsConstraintRuntimeIndex DisplayString (SIZE (1..16)),
         maxThreadsConstraintRuntimeObjectName DisplayString (SIZE (1..256)),
         maxThreadsConstraintRuntimeType DisplayString (SIZE (1..64)),
         maxThreadsConstraintRuntimeName DisplayString (SIZE (1..64)),
         maxThreadsConstraintRuntimeParent DisplayString (SIZE (1..256)),
         maxThreadsConstraintRuntimeExecutingRequests INTEGER,
         maxThreadsConstraintRuntimeDeferredRequests INTEGER
      }
      
   
   maxThreadsConstraintRuntimeIndex OBJECT-TYPE
      SYNTAX      DisplayString (SIZE (1..16))
      MAX-ACCESS  read-only
      STATUS      current
      DESCRIPTION "Unique value directed from ObjectName which is used as table index"
      ::= { maxThreadsConstraintRuntimeEntry 1  }
   
   
   maxThreadsConstraintRuntimeObjectName OBJECT-TYPE
      SYNTAX      DisplayString (SIZE (1..256))
      MAX-ACCESS  read-only
      STATUS      current
      DESCRIPTION "JMX-standard MBean name"
      ::= { maxThreadsConstraintRuntimeEntry 5  }
   
   
   maxThreadsConstraintRuntimeType OBJECT-TYPE
      SYNTAX      DisplayString (SIZE (1..64))
      MAX-ACCESS  read-only
      STATUS      current
      DESCRIPTION "BEA-proprietary MBean type"
      ::= { maxThreadsConstraintRuntimeEntry 10  }
   
   
   maxThreadsConstraintRuntimeName OBJECT-TYPE
      SYNTAX      DisplayString (SIZE (1..64))
      MAX-ACCESS  read-only
      STATUS      current
      DESCRIPTION "BEA-proprietary MBean name"
      ::= { maxThreadsConstraintRuntimeEntry 15  }
   
   
   maxThreadsConstraintRuntimeParent OBJECT-TYPE
      SYNTAX      DisplayString (SIZE (1..256))
      MAX-ACCESS  read-only
      STATUS      current
      DESCRIPTION "BEA-proprietary Parent object's identification, with syntax
      <type>:<name>"
      ::= { maxThreadsConstraintRuntimeEntry 20  }
   
   
   maxThreadsConstraintRuntimeExecutingRequests OBJECT-TYPE
      SYNTAX      INTEGER
      MAX-ACCESS  read-only
      STATUS      current
      DESCRIPTION "Returns the Number of requests that are currently executing."
      ::= { maxThreadsConstraintRuntimeEntry 25  }
   
   
   maxThreadsConstraintRuntimeDeferredRequests OBJECT-TYPE
      SYNTAX      INTEGER
      MAX-ACCESS  read-only
      STATUS      current
      DESCRIPTION "Returns the umber of requests that are denied a thread for execution because the constraint is exceeded."
      ::= { maxThreadsConstraintRuntimeEntry 30  }
   
   
   minThreadsConstraintRuntimeTable OBJECT-TYPE
      SYNTAX      SEQUENCE OF MinThreadsConstraintRuntimeEntry
      MAX-ACCESS  not-accessible
      STATUS      current
      DESCRIPTION "Provides values for Min Threads Constraints for the server"
      ::= { wls 364  }
      
   
   minThreadsConstraintRuntimeEntry OBJECT-TYPE
      SYNTAX      MinThreadsConstraintRuntimeEntry
      MAX-ACCESS  not-accessible
      STATUS      current
      DESCRIPTION "Entry of minThreadsConstraintRuntimeTable"
      INDEX { minThreadsConstraintRuntimeIndex}
      ::= { minThreadsConstraintRuntimeTable 1 }
      
   MinThreadsConstraintRuntimeEntry ::=
      SEQUENCE
      {
         minThreadsConstraintRuntimeIndex DisplayString (SIZE (1..16)),
         minThreadsConstraintRuntimeObjectName DisplayString (SIZE (1..256)),
         minThreadsConstraintRuntimeType DisplayString (SIZE (1..64)),
         minThreadsConstraintRuntimeName DisplayString (SIZE (1..64)),
         minThreadsConstraintRuntimeParent DisplayString (SIZE (1..256)),
         minThreadsConstraintRuntimeCompletedRequests Counter64,
         minThreadsConstraintRuntimePendingRequests INTEGER,
         minThreadsConstraintRuntimeExecutingRequests INTEGER,
         minThreadsConstraintRuntimeOutOfOrderExecutionCount Counter64,
         minThreadsConstraintRuntimeMustRunCount INTEGER,
         minThreadsConstraintRuntimeMaxWaitTime Counter64,
         minThreadsConstraintRuntimeCurrentWaitTime Counter64
      }
      
   
   minThreadsConstraintRuntimeIndex OBJECT-TYPE
      SYNTAX      DisplayString (SIZE (1..16))
      MAX-ACCESS  read-only
      STATUS      current
      DESCRIPTION "Unique value directed from ObjectName which is used as table index"
      ::= { minThreadsConstraintRuntimeEntry 1  }
   
   
   minThreadsConstraintRuntimeObjectName OBJECT-TYPE
      SYNTAX      DisplayString (SIZE (1..256))
      MAX-ACCESS  read-only
      STATUS      current
      DESCRIPTION "JMX-standard MBean name"
      ::= { minThreadsConstraintRuntimeEntry 5  }
   
   
   minThreadsConstraintRuntimeType OBJECT-TYPE
      SYNTAX      DisplayString (SIZE (1..64))
      MAX-ACCESS  read-only
      STATUS      current
      DESCRIPTION "BEA-proprietary MBean type"
      ::= { minThreadsConstraintRuntimeEntry 10  }
   
   
   minThreadsConstraintRuntimeName OBJECT-TYPE
      SYNTAX      DisplayString (SIZE (1..64))
      MAX-ACCESS  read-only
      STATUS      current
      DESCRIPTION "BEA-proprietary MBean name"
      ::= { minThreadsConstraintRuntimeEntry 15  }
   
   
   minThreadsConstraintRuntimeParent OBJECT-TYPE
      SYNTAX      DisplayString (SIZE (1..256))
      MAX-ACCESS  read-only
      STATUS      current
      DESCRIPTION "BEA-proprietary Parent object's identification, with syntax
      <type>:<name>"
      ::= { minThreadsConstraintRuntimeEntry 20  }
   
   
   minThreadsConstraintRuntimeCompletedRequests OBJECT-TYPE
      SYNTAX      Counter64
      MAX-ACCESS  read-only
      STATUS      current
      DESCRIPTION "Returns the Number of requests that have completed executing."
      ::= { minThreadsConstraintRuntimeEntry 25  }
   
   
   minThreadsConstraintRuntimePendingRequests OBJECT-TYPE
      SYNTAX      INTEGER
      MAX-ACCESS  read-only
      STATUS      current
      DESCRIPTION "Returns the Number of requests that are waiting for an available thread."
      ::= { minThreadsConstraintRuntimeEntry 30  }
   
   
   minThreadsConstraintRuntimeExecutingRequests OBJECT-TYPE
      SYNTAX      INTEGER
      MAX-ACCESS  read-only
      STATUS      current
      DESCRIPTION "Returns the Number of requests that are currently executing."
      ::= { minThreadsConstraintRuntimeEntry 35  }
   
   
   minThreadsConstraintRuntimeOutOfOrderExecutionCount OBJECT-TYPE
      SYNTAX      Counter64
      MAX-ACCESS  read-only
      STATUS      current
      DESCRIPTION "Returns the Number of requests executed out of turn to satisfy this constraint."
      ::= { minThreadsConstraintRuntimeEntry 40  }
   
   
   minThreadsConstraintRuntimeMustRunCount OBJECT-TYPE
      SYNTAX      INTEGER
      MAX-ACCESS  read-only
      STATUS      current
      DESCRIPTION "Returns the Number of requests that must be executed to satisfy the constraint."
      ::= { minThreadsConstraintRuntimeEntry 45  }
   
   
   minThreadsConstraintRuntimeMaxWaitTime OBJECT-TYPE
      SYNTAX      Counter64
      MAX-ACCESS  read-only
      STATUS      current
      DESCRIPTION "Returns the max time a request had to wait for a thread. Only requests whose execution is needed to satisfy
      the constraint are considered."
      ::= { minThreadsConstraintRuntimeEntry 50  }
   
   
   minThreadsConstraintRuntimeCurrentWaitTime OBJECT-TYPE
      SYNTAX      Counter64
      MAX-ACCESS  read-only
      STATUS      current
      DESCRIPTION "Returns the last measured time a request had to wait for a thread. Only requests whose execution is needed to
      satisfy the constraint are considered."
      ::= { minThreadsConstraintRuntimeEntry 55  }
   
   
   requestClassRuntimeTable OBJECT-TYPE
      SYNTAX      SEQUENCE OF RequestClassRuntimeEntry
      MAX-ACCESS  not-accessible
      STATUS      current
      DESCRIPTION "Presents runtime information about RequestClasses.  A request class represents a class of work. Work using the
      same request class shares the same priority"
      ::= { wls 365  }
      
   
   requestClassRuntimeEntry OBJECT-TYPE
      SYNTAX      RequestClassRuntimeEntry
      MAX-ACCESS  not-accessible
      STATUS      current
      DESCRIPTION "Entry of requestClassRuntimeTable"
      INDEX { requestClassRuntimeIndex}
      ::= { requestClassRuntimeTable 1 }
      
   RequestClassRuntimeEntry ::=
      SEQUENCE
      {
         requestClassRuntimeIndex DisplayString (SIZE (1..16)),
         requestClassRuntimeObjectName DisplayString (SIZE (1..256)),
         requestClassRuntimeType DisplayString (SIZE (1..64)),
         requestClassRuntimeName DisplayString (SIZE (1..64)),
         requestClassRuntimeParent DisplayString (SIZE (1..256)),
         requestClassRuntimeCompletedCount Counter64,
         requestClassRuntimeTotalThreadUse Counter64,
         requestClassRuntimePendingRequestCount INTEGER,
         requestClassRuntimeVirtualTimeIncrement Counter64,
         requestClassRuntimeRequestClassType DisplayString (SIZE (1..64)),
         requestClassRuntimeDeltaRepeat Counter64,
         requestClassRuntimeDeltaFirst Counter64,
         requestClassRuntimeThreadUseSquares Counter64,
         requestClassRuntimeMyLast Counter64,
         requestClassRuntimeInterval OCTET STRING
      }
      
   
   requestClassRuntimeIndex OBJECT-TYPE
      SYNTAX      DisplayString (SIZE (1..16))
      MAX-ACCESS  read-only
      STATUS      current
      DESCRIPTION "Unique value directed from ObjectName which is used as table index"
      ::= { requestClassRuntimeEntry 1  }
   
   
   requestClassRuntimeObjectName OBJECT-TYPE
      SYNTAX      DisplayString (SIZE (1..256))
      MAX-ACCESS  read-only
      STATUS      current
      DESCRIPTION "JMX-standard MBean name"
      ::= { requestClassRuntimeEntry 5  }
   
   
   requestClassRuntimeType OBJECT-TYPE
      SYNTAX      DisplayString (SIZE (1..64))
      MAX-ACCESS  read-only
      STATUS      current
      DESCRIPTION "BEA-proprietary MBean type"
      ::= { requestClassRuntimeEntry 10  }
   
   
   requestClassRuntimeName OBJECT-TYPE
      SYNTAX      DisplayString (SIZE (1..64))
      MAX-ACCESS  read-only
      STATUS      current
      DESCRIPTION "BEA-proprietary MBean name"
      ::= { requestClassRuntimeEntry 15  }
   
   
   requestClassRuntimeParent OBJECT-TYPE
      SYNTAX      DisplayString (SIZE (1..256))
      MAX-ACCESS  read-only
      STATUS      current
      DESCRIPTION "BEA-proprietary Parent object's identification, with syntax
      <type>:<name>"
      ::= { requestClassRuntimeEntry 20  }
   
   
   requestClassRuntimeCompletedCount OBJECT-TYPE
      SYNTAX      Counter64
      MAX-ACCESS  read-only
      STATUS      current
      DESCRIPTION "Returns the Total number of completions since server start."
      ::= { requestClassRuntimeEntry 25  }
   
   
   requestClassRuntimeTotalThreadUse OBJECT-TYPE
      SYNTAX      Counter64
      MAX-ACCESS  read-only
      STATUS      current
      DESCRIPTION "Returns the Total amount of thread use time in millisec's used by the request class since server start."
      ::= { requestClassRuntimeEntry 30  }
   
   
   requestClassRuntimePendingRequestCount OBJECT-TYPE
      SYNTAX      INTEGER
      MAX-ACCESS  read-only
      STATUS      current
      DESCRIPTION "Returns the Number of requests waiting for a thread to become available."
      ::= { requestClassRuntimeEntry 35  }
   
   
   requestClassRuntimeVirtualTimeIncrement OBJECT-TYPE
      SYNTAX      Counter64
      MAX-ACCESS  read-only
      STATUS      current
      DESCRIPTION "Returns the Current priority of the request class. The priority is relative to other request class priorities.
      The priority is calculated dynamically frequently and can change."
      ::= { requestClassRuntimeEntry 40  }
   
   
   requestClassRuntimeRequestClassType OBJECT-TYPE
      SYNTAX      DisplayString (SIZE (1..64))
      MAX-ACCESS  read-only
      STATUS      current
      DESCRIPTION "Returns the  type of RequestClass, either FIR_SHARE or RESPONSE_TIME."
      ::= { requestClassRuntimeEntry 45  }
   
   
   requestClassRuntimeDeltaRepeat OBJECT-TYPE
      SYNTAX      Counter64
      MAX-ACCESS  read-only
      STATUS      current
      DESCRIPTION "Undocumented attribute that exposes a value used in determining priority"
      ::= { requestClassRuntimeEntry 46  }
   
   
   requestClassRuntimeDeltaFirst OBJECT-TYPE
      SYNTAX      Counter64
      MAX-ACCESS  read-only
      STATUS      current
      DESCRIPTION "Undocumented attribute that exposes a value used in determining priority"
      ::= { requestClassRuntimeEntry 47  }
   
   
   requestClassRuntimeThreadUseSquares OBJECT-TYPE
      SYNTAX      Counter64
      MAX-ACCESS  read-only
      STATUS      current
      DESCRIPTION "Undocumented attribute that exposes a value used in determining priority"
      ::= { requestClassRuntimeEntry 48  }
   
   
   requestClassRuntimeMyLast OBJECT-TYPE
      SYNTAX      Counter64
      MAX-ACCESS  read-only
      STATUS      current
      DESCRIPTION "Undocumented attribute that exposes a value used in determining priority"
      ::= { requestClassRuntimeEntry 49  }
   
   
   requestClassRuntimeInterval OBJECT-TYPE
      SYNTAX      OCTET STRING
      MAX-ACCESS  read-only
      STATUS      current
      DESCRIPTION "Undocumented attribute that exposes a value used in determining priority. This attribute is applicable only for ResponseTimeRequestClass. -1 is returned for FairShareRequestClasses."
      ::= { requestClassRuntimeEntry 50  }
   
   
   serverChannelRuntimeTable OBJECT-TYPE
      SYNTAX      SEQUENCE OF ServerChannelRuntimeEntry
      MAX-ACCESS  not-accessible
      STATUS      current
      DESCRIPTION "Presents Runtime information for NetworkAccessPoints or Channels."
      ::= { wls 366  }
      
   
   serverChannelRuntimeEntry OBJECT-TYPE
      SYNTAX      ServerChannelRuntimeEntry
      MAX-ACCESS  not-accessible
      STATUS      current
      DESCRIPTION "Entry of serverChannelRuntimeTable"
      INDEX { serverChannelRuntimeIndex}
      ::= { serverChannelRuntimeTable 1 }
      
   ServerChannelRuntimeEntry ::=
      SEQUENCE
      {
         serverChannelRuntimeIndex DisplayString (SIZE (1..16)),
         serverChannelRuntimeObjectName DisplayString (SIZE (1..256)),
         serverChannelRuntimeType DisplayString (SIZE (1..64)),
         serverChannelRuntimeName DisplayString (SIZE (1..64)),
         serverChannelRuntimeParent DisplayString (SIZE (1..256)),
         serverChannelRuntimeBytesReceivedCount Counter64,
         serverChannelRuntimeBytesSentCount Counter64,
         serverChannelRuntimeChannelName DisplayString (SIZE (1..64)),
         serverChannelRuntimeConnectionsCount Counter64,
         serverChannelRuntimeAcceptCount Counter64,
         serverChannelRuntimeMessagesReceivedCount Counter64,
         serverChannelRuntimeMessagesSentCount Counter64,
         serverChannelRuntimePublicURL DisplayString (SIZE (1..128))
      }
      
   
   serverChannelRuntimeIndex OBJECT-TYPE
      SYNTAX      DisplayString (SIZE (1..16))
      MAX-ACCESS  read-only
      STATUS      current
      DESCRIPTION "Unique value directed from ObjectName which is used as table index"
      ::= { serverChannelRuntimeEntry 1  }
   
   
   serverChannelRuntimeObjectName OBJECT-TYPE
      SYNTAX      DisplayString (SIZE (1..256))
      MAX-ACCESS  read-only
      STATUS      current
      DESCRIPTION "JMX-standard MBean name"
      ::= { serverChannelRuntimeEntry 5  }
   
   
   serverChannelRuntimeType OBJECT-TYPE
      SYNTAX      DisplayString (SIZE (1..64))
      MAX-ACCESS  read-only
      STATUS      current
      DESCRIPTION "BEA-proprietary MBean type"
      ::= { serverChannelRuntimeEntry 10  }
   
   
   serverChannelRuntimeName OBJECT-TYPE
      SYNTAX      DisplayString (SIZE (1..64))
      MAX-ACCESS  read-only
      STATUS      current
      DESCRIPTION "BEA-proprietary MBean name"
      ::= { serverChannelRuntimeEntry 15  }
   
   
   serverChannelRuntimeParent OBJECT-TYPE
      SYNTAX      DisplayString (SIZE (1..256))
      MAX-ACCESS  read-only
      STATUS      current
      DESCRIPTION "BEA-proprietary Parent object's identification, with syntax
      <type>:<name>"
      ::= { serverChannelRuntimeEntry 20  }
   
   
   serverChannelRuntimeBytesReceivedCount OBJECT-TYPE
      SYNTAX      Counter64
      MAX-ACCESS  read-only
      STATUS      current
      DESCRIPTION "Returns the total number of bytes received on this channel."
      ::= { serverChannelRuntimeEntry 25  }
   
   
   serverChannelRuntimeBytesSentCount OBJECT-TYPE
      SYNTAX      Counter64
      MAX-ACCESS  read-only
      STATUS      current
      DESCRIPTION "Returns the total number of bytes sent on this channel."
      ::= { serverChannelRuntimeEntry 30  }
   
   
   serverChannelRuntimeChannelName OBJECT-TYPE
      SYNTAX      DisplayString (SIZE (1..64))
      MAX-ACCESS  read-only
      STATUS      current
      DESCRIPTION "Returns the channel name of this channel."
      ::= { serverChannelRuntimeEntry 35  }
   
   
   serverChannelRuntimeConnectionsCount OBJECT-TYPE
      SYNTAX      Counter64
      MAX-ACCESS  read-only
      STATUS      current
      DESCRIPTION "Returns the number of active connections and sockets associated with this channel."
      ::= { serverChannelRuntimeEntry 40  }
   
   
   serverChannelRuntimeAcceptCount OBJECT-TYPE
      SYNTAX      Counter64
      MAX-ACCESS  read-only
      STATUS      current
      DESCRIPTION "Returns the number of sockets that have been accepted on this channel. This includes sockets both
      past and present so gives a good idea of the connection rate to the server."
      ::= { serverChannelRuntimeEntry 45  }
   
   
   serverChannelRuntimeMessagesReceivedCount OBJECT-TYPE
      SYNTAX      Counter64
      MAX-ACCESS  read-only
      STATUS      current
      DESCRIPTION "Returns the number of messages received on this channel."
      ::= { serverChannelRuntimeEntry 50  }
   
   
   serverChannelRuntimeMessagesSentCount OBJECT-TYPE
      SYNTAX      Counter64
      MAX-ACCESS  read-only
      STATUS      current
      DESCRIPTION "Returns the number of messages sent on this channel."
      ::= { serverChannelRuntimeEntry 55  }
   
   
   serverChannelRuntimePublicURL OBJECT-TYPE
      SYNTAX      DisplayString (SIZE (1..128))
      MAX-ACCESS  read-only
      STATUS      current
      DESCRIPTION "Returns the physical URL that this channel is listening on."
      ::= { serverChannelRuntimeEntry 60  }
   
   
   threadPoolRuntimeTable OBJECT-TYPE
      SYNTAX      SEQUENCE OF ThreadPoolRuntimeEntry
      MAX-ACCESS  not-accessible
      STATUS      current
      DESCRIPTION "Presents Runtime information to monitor the self-tuning queue."
      ::= { wls 367  }
      
   
   threadPoolRuntimeEntry OBJECT-TYPE
      SYNTAX      ThreadPoolRuntimeEntry
      MAX-ACCESS  not-accessible
      STATUS      current
      DESCRIPTION "Entry of threadPoolRuntimeTable"
      INDEX { threadPoolRuntimeIndex}
      ::= { threadPoolRuntimeTable 1 }
      
   ThreadPoolRuntimeEntry ::=
      SEQUENCE
      {
         threadPoolRuntimeIndex DisplayString (SIZE (1..16)),
         threadPoolRuntimeObjectName DisplayString (SIZE (1..256)),
         threadPoolRuntimeType DisplayString (SIZE (1..64)),
         threadPoolRuntimeName DisplayString (SIZE (1..64)),
         threadPoolRuntimeParent DisplayString (SIZE (1..256)),
         threadPoolRuntimeExecuteThreadTotalCount INTEGER,
         threadPoolRuntimeExecuteThreadIdleCount INTEGER,
         threadPoolRuntimeQueueLength INTEGER,
         threadPoolRuntimePendingUserRequestCount INTEGER,
         threadPoolRuntimeSharedCapacityForWorkManagers INTEGER,
         threadPoolRuntimeCompletedRequestCount Counter64,
         threadPoolRuntimeHoggingThreadCount INTEGER,
         threadPoolRuntimeStandbyThreadCount INTEGER,
         threadPoolRuntimeThroughput INTEGER,
         threadPoolRuntimeMinThreadsConstraintsPending INTEGER,
         threadPoolRuntimeMinThreadsConstraintsCompleted Counter64,
         threadPoolRuntimeSuspended INTEGER
                     {
                        true(1),
                        false(2)
                     }
      }
      
   
   threadPoolRuntimeIndex OBJECT-TYPE
      SYNTAX      DisplayString (SIZE (1..16))
      MAX-ACCESS  read-only
      STATUS      current
      DESCRIPTION "Unique value directed from ObjectName which is used as table index"
      ::= { threadPoolRuntimeEntry 1  }
   
   
   threadPoolRuntimeObjectName OBJECT-TYPE
      SYNTAX      DisplayString (SIZE (1..256))
      MAX-ACCESS  read-only
      STATUS      current
      DESCRIPTION "JMX-standard MBean name"
      ::= { threadPoolRuntimeEntry 5  }
   
   
   threadPoolRuntimeType OBJECT-TYPE
      SYNTAX      DisplayString (SIZE (1..64))
      MAX-ACCESS  read-only
      STATUS      current
      DESCRIPTION "BEA-proprietary MBean type"
      ::= { threadPoolRuntimeEntry 10  }
   
   
   threadPoolRuntimeName OBJECT-TYPE
      SYNTAX      DisplayString (SIZE (1..64))
      MAX-ACCESS  read-only
      STATUS      current
      DESCRIPTION "BEA-proprietary MBean name"
      ::= { threadPoolRuntimeEntry 15  }
   
   
   threadPoolRuntimeParent OBJECT-TYPE
      SYNTAX      DisplayString (SIZE (1..256))
      MAX-ACCESS  read-only
      STATUS      current
      DESCRIPTION "BEA-proprietary Parent object's identification, with syntax
      <type>:<name>"
      ::= { threadPoolRuntimeEntry 20  }
   
   
   threadPoolRuntimeExecuteThreadTotalCount OBJECT-TYPE
      SYNTAX      INTEGER
      MAX-ACCESS  read-only
      STATUS      current
      DESCRIPTION "Returns the total number of threads in the pool."
      ::= { threadPoolRuntimeEntry 25  }
   
   
   threadPoolRuntimeExecuteThreadIdleCount OBJECT-TYPE
      SYNTAX      INTEGER
      MAX-ACCESS  read-only
      STATUS      current
      DESCRIPTION "Returns the number of idle threads in the pool."
      ::= { threadPoolRuntimeEntry 30  }
   
   
   threadPoolRuntimeQueueLength OBJECT-TYPE
      SYNTAX      INTEGER
      MAX-ACCESS  read-only
      STATUS      current
      DESCRIPTION "Returns the number of pending requests in the priority queue. This is the total of internal system requests
      and user requests."
      ::= { threadPoolRuntimeEntry 35  }
   
   
   threadPoolRuntimePendingUserRequestCount OBJECT-TYPE
      SYNTAX      INTEGER
      MAX-ACCESS  read-only
      STATUS      current
      DESCRIPTION "Returns the number of pending user requests in the priority queue. The priority queue contains requests from
      internal subsystems and users. This is just the count of all user requests."
      ::= { threadPoolRuntimeEntry 40  }
   
   
   threadPoolRuntimeSharedCapacityForWorkManagers OBJECT-TYPE
      SYNTAX      INTEGER
      MAX-ACCESS  read-only
      STATUS      current
      DESCRIPTION "Returns the maximum amount of requests that can be accepted in the priority qeueue."
      ::= { threadPoolRuntimeEntry 45  }
   
   
   threadPoolRuntimeCompletedRequestCount OBJECT-TYPE
      SYNTAX      Counter64
      MAX-ACCESS  read-only
      STATUS      current
      DESCRIPTION "Returns the number of completed requests in the priority queue."
      ::= { threadPoolRuntimeEntry 50  }
   
   
   threadPoolRuntimeHoggingThreadCount OBJECT-TYPE
      SYNTAX      INTEGER
      MAX-ACCESS  read-only
      STATUS      current
      DESCRIPTION "Returns the threads that are being hogged by a request right now. These threads will either be declared
      as stuck after the configured timeout or will return to the pool before that. The self-tuning mechanism will
      backfill if necessary."
      ::= { threadPoolRuntimeEntry 55  }
   
   
   threadPoolRuntimeStandbyThreadCount OBJECT-TYPE
      SYNTAX      INTEGER
      MAX-ACCESS  read-only
      STATUS      current
      DESCRIPTION "Returns the number of threads in the standby pool. Surplus threads that are not needed to handle the
      present work load are designated as standby and added to the standby pool. These threads are activated
      when more threads are needed."
      ::= { threadPoolRuntimeEntry 60  }
   
   
   threadPoolRuntimeThroughput OBJECT-TYPE
      SYNTAX      INTEGER
      MAX-ACCESS  read-only
      STATUS      current
      DESCRIPTION "Returns the mean number of requests completed per second."
      ::= { threadPoolRuntimeEntry 65  }
   
   
   threadPoolRuntimeMinThreadsConstraintsPending OBJECT-TYPE
      SYNTAX      INTEGER
      MAX-ACCESS  read-only
      STATUS      current
      DESCRIPTION "Returns the Number of requests that should be executed now to satisfy the min threads requirement."
      ::= { threadPoolRuntimeEntry 70  }
   
   
   threadPoolRuntimeMinThreadsConstraintsCompleted OBJECT-TYPE
      SYNTAX      Counter64
      MAX-ACCESS  read-only
      STATUS      current
      DESCRIPTION "Returns the Number of requests with min threads constraint picked up out of order for execution immediately
      since their min threads requirement was not met. This does not include the case where threads are idle during schedule."
      ::= { threadPoolRuntimeEntry 75  }
   
   
   threadPoolRuntimeSuspended OBJECT-TYPE
      SYNTAX      INTEGER
                  {
                     true(1),
                     false(2)
                  }
      
      MAX-ACCESS  read-only
      STATUS      current
      DESCRIPTION "Returns the Indicates if the RequestManager is suspended. A suspended manager will not dequeue work and
      dispatch threads till it is resumed"
      ::= { threadPoolRuntimeEntry 80  }
   
   
   workManagerRuntimeTable OBJECT-TYPE
      SYNTAX      SEQUENCE OF WorkManagerRuntimeEntry
      MAX-ACCESS  not-accessible
      STATUS      current
      DESCRIPTION "Presents Runtime information for the WorkManager Runtime."
      ::= { wls 368  }
      
   
   workManagerRuntimeEntry OBJECT-TYPE
      SYNTAX      WorkManagerRuntimeEntry
      MAX-ACCESS  not-accessible
      STATUS      current
      DESCRIPTION "Entry of workManagerRuntimeTable"
      INDEX { workManagerRuntimeIndex}
      ::= { workManagerRuntimeTable 1 }
      
   WorkManagerRuntimeEntry ::=
      SEQUENCE
      {
         workManagerRuntimeIndex DisplayString (SIZE (1..16)),
         workManagerRuntimeObjectName DisplayString (SIZE (1..256)),
         workManagerRuntimeType DisplayString (SIZE (1..64)),
         workManagerRuntimeName DisplayString (SIZE (1..64)),
         workManagerRuntimeParent DisplayString (SIZE (1..256)),
         workManagerRuntimeApplicationName DisplayString (SIZE (1..128)),
         workManagerRuntimeModuleName DisplayString (SIZE (1..128)),
         workManagerRuntimePendingRequests INTEGER,
         workManagerRuntimeCompletedRequests Counter64,
         workManagerRuntimeStuckThreadCount INTEGER
      }
      
   
   workManagerRuntimeIndex OBJECT-TYPE
      SYNTAX      DisplayString (SIZE (1..16))
      MAX-ACCESS  read-only
      STATUS      current
      DESCRIPTION "Unique value directed from ObjectName which is used as table index"
      ::= { workManagerRuntimeEntry 1  }
   
   
   workManagerRuntimeObjectName OBJECT-TYPE
      SYNTAX      DisplayString (SIZE (1..256))
      MAX-ACCESS  read-only
      STATUS      current
      DESCRIPTION "JMX-standard MBean name"
      ::= { workManagerRuntimeEntry 5  }
   
   
   workManagerRuntimeType OBJECT-TYPE
      SYNTAX      DisplayString (SIZE (1..64))
      MAX-ACCESS  read-only
      STATUS      current
      DESCRIPTION "BEA-proprietary MBean type"
      ::= { workManagerRuntimeEntry 10  }
   
   
   workManagerRuntimeName OBJECT-TYPE
      SYNTAX      DisplayString (SIZE (1..64))
      MAX-ACCESS  read-only
      STATUS      current
      DESCRIPTION "BEA-proprietary MBean name"
      ::= { workManagerRuntimeEntry 15  }
   
   
   workManagerRuntimeParent OBJECT-TYPE
      SYNTAX      DisplayString (SIZE (1..256))
      MAX-ACCESS  read-only
      STATUS      current
      DESCRIPTION "BEA-proprietary Parent object's identification, with syntax
      <type>:<name>"
      ::= { workManagerRuntimeEntry 20  }
   
   
   workManagerRuntimeApplicationName OBJECT-TYPE
      SYNTAX      DisplayString (SIZE (1..128))
      MAX-ACCESS  read-only
      STATUS      current
      DESCRIPTION "Returns the name of the application this WorkManager is associated with."
      ::= { workManagerRuntimeEntry 25  }
   
   
   workManagerRuntimeModuleName OBJECT-TYPE
      SYNTAX      DisplayString (SIZE (1..128))
      MAX-ACCESS  read-only
      STATUS      current
      DESCRIPTION "Returns the name of the module this WorkManager is associated with."
      ::= { workManagerRuntimeEntry 30  }
   
   
   workManagerRuntimePendingRequests OBJECT-TYPE
      SYNTAX      INTEGER
      MAX-ACCESS  read-only
      STATUS      current
      DESCRIPTION "Returns the number of waiting requests in the queue."
      ::= { workManagerRuntimeEntry 35  }
   
   
   workManagerRuntimeCompletedRequests OBJECT-TYPE
      SYNTAX      Counter64
      MAX-ACCESS  read-only
      STATUS      current
      DESCRIPTION "Returns the number of requests that have been processed."
      ::= { workManagerRuntimeEntry 40  }
   
   
   workManagerRuntimeStuckThreadCount OBJECT-TYPE
      SYNTAX      INTEGER
      MAX-ACCESS  read-only
      STATUS      current
      DESCRIPTION "The number of thread that are considers stuck on the basis of any stuck thread constraints."
      ::= { workManagerRuntimeEntry 41  }
   
   
   serverSecurityRuntimeTable OBJECT-TYPE
      SYNTAX      SEQUENCE OF ServerSecurityRuntimeEntry
      MAX-ACCESS  not-accessible
      STATUS      current
      DESCRIPTION "This table is used for monitoring a WebLogic Security Info."
      ::= { wls 370  }
      
   
   serverSecurityRuntimeEntry OBJECT-TYPE
      SYNTAX      ServerSecurityRuntimeEntry
      MAX-ACCESS  not-accessible
      STATUS      current
      DESCRIPTION "Entry of serverSecurityRuntimeTable"
      INDEX { serverSecurityRuntimeIndex}
      ::= { serverSecurityRuntimeTable 1 }
      
   ServerSecurityRuntimeEntry ::=
      SEQUENCE
      {
         serverSecurityRuntimeIndex DisplayString (SIZE (1..16)),
         serverSecurityRuntimeObjectName DisplayString (SIZE (1..256)),
         serverSecurityRuntimeType DisplayString (SIZE (1..64)),
         serverSecurityRuntimeName DisplayString (SIZE (1..64)),
         serverSecurityRuntimeParent DisplayString (SIZE (1..256)),
         serverSecurityRuntimeJACCEnabled INTEGER
                     {
                        true(1),
                        false(2)
                     }
      }
      
   
   serverSecurityRuntimeIndex OBJECT-TYPE
      SYNTAX      DisplayString (SIZE (1..16))
      MAX-ACCESS  read-only
      STATUS      current
      DESCRIPTION "Unique value directed from ObjectName which is used as table index"
      ::= { serverSecurityRuntimeEntry 1  }
   
   
   serverSecurityRuntimeObjectName OBJECT-TYPE
      SYNTAX      DisplayString (SIZE (1..256))
      MAX-ACCESS  read-only
      STATUS      current
      DESCRIPTION "JMX-standard MBean name"
      ::= { serverSecurityRuntimeEntry 5  }
   
   
   serverSecurityRuntimeType OBJECT-TYPE
      SYNTAX      DisplayString (SIZE (1..64))
      MAX-ACCESS  read-only
      STATUS      current
      DESCRIPTION "BEA-proprietary MBean type"
      ::= { serverSecurityRuntimeEntry 10  }
   
   
   serverSecurityRuntimeName OBJECT-TYPE
      SYNTAX      DisplayString (SIZE (1..64))
      MAX-ACCESS  read-only
      STATUS      current
      DESCRIPTION "BEA-proprietary MBean name"
      ::= { serverSecurityRuntimeEntry 15  }
   
   
   serverSecurityRuntimeParent OBJECT-TYPE
      SYNTAX      DisplayString (SIZE (1..256))
      MAX-ACCESS  read-only
      STATUS      current
      DESCRIPTION "BEA-proprietary Parent object's identification, with syntax
      <type>:<name>"
      ::= { serverSecurityRuntimeEntry 20  }
   
   
   serverSecurityRuntimeJACCEnabled OBJECT-TYPE
      SYNTAX      INTEGER
                  {
                     true(1),
                     false(2)
                  }
      
      MAX-ACCESS  read-only
      STATUS      current
      DESCRIPTION "Indicates whether JACC (Java Authorization Contract for Containers)
      was enabled on the commandline for the jvm hosting this server."
      ::= { serverSecurityRuntimeEntry 30  }
   
   
   userLockoutManagerRuntimeTable OBJECT-TYPE
      SYNTAX      SEQUENCE OF UserLockoutManagerRuntimeEntry
      MAX-ACCESS  not-accessible
      STATUS      current
      DESCRIPTION "This table is used for monitoring per-Security Realm user lockout information."
      ::= { wls 371  }
      
   
   userLockoutManagerRuntimeEntry OBJECT-TYPE
      SYNTAX      UserLockoutManagerRuntimeEntry
      MAX-ACCESS  not-accessible
      STATUS      current
      DESCRIPTION "Entry of userLockoutManagerRuntimeTable"
      INDEX { userLockoutManagerRuntimeIndex}
      ::= { userLockoutManagerRuntimeTable 1 }
      
   UserLockoutManagerRuntimeEntry ::=
      SEQUENCE
      {
         userLockoutManagerRuntimeIndex DisplayString (SIZE (1..16)),
         userLockoutManagerRuntimeObjectName DisplayString (SIZE (1..256)),
         userLockoutManagerRuntimeType DisplayString (SIZE (1..64)),
         userLockoutManagerRuntimeName DisplayString (SIZE (1..64)),
         userLockoutManagerRuntimeParent DisplayString (SIZE (1..256)),
         userLockoutManagerRuntimeUserLockoutTotalCount Counter64,
         userLockoutManagerRuntimeInvalidLoginAttemptsTotalCount Counter64,
         userLockoutManagerRuntimeLoginAttemptsWhileLockedTotalCount Counter64,
         userLockoutManagerRuntimeInvalidLoginUsersHighCount Counter64,
         userLockoutManagerRuntimeUnlockedUsersTotalCount Counter64,
         userLockoutManagerRuntimeLockedUsersCurrentCount Counter64
      }
      
   
   userLockoutManagerRuntimeIndex OBJECT-TYPE
      SYNTAX      DisplayString (SIZE (1..16))
      MAX-ACCESS  read-only
      STATUS      current
      DESCRIPTION "Unique value directed from ObjectName which is used as table index"
      ::= { userLockoutManagerRuntimeEntry 1  }
   
   
   userLockoutManagerRuntimeObjectName OBJECT-TYPE
      SYNTAX      DisplayString (SIZE (1..256))
      MAX-ACCESS  read-only
      STATUS      current
      DESCRIPTION "JMX-standard MBean name"
      ::= { userLockoutManagerRuntimeEntry 5  }
   
   
   userLockoutManagerRuntimeType OBJECT-TYPE
      SYNTAX      DisplayString (SIZE (1..64))
      MAX-ACCESS  read-only
      STATUS      current
      DESCRIPTION "BEA-proprietary MBean type"
      ::= { userLockoutManagerRuntimeEntry 10  }
   
   
   userLockoutManagerRuntimeName OBJECT-TYPE
      SYNTAX      DisplayString (SIZE (1..64))
      MAX-ACCESS  read-only
      STATUS      current
      DESCRIPTION "BEA-proprietary MBean name"
      ::= { userLockoutManagerRuntimeEntry 15  }
   
   
   userLockoutManagerRuntimeParent OBJECT-TYPE
      SYNTAX      DisplayString (SIZE (1..256))
      MAX-ACCESS  read-only
      STATUS      current
      DESCRIPTION "BEA-proprietary Parent object's identification, with syntax
      <type>:<name>"
      ::= { userLockoutManagerRuntimeEntry 20  }
   
   
   userLockoutManagerRuntimeUserLockoutTotalCount OBJECT-TYPE
      SYNTAX      Counter64
      MAX-ACCESS  read-only
      STATUS      current
      DESCRIPTION "Returns the number of user lockouts that have occured since this server has been started."
      ::= { userLockoutManagerRuntimeEntry 25  }
   
   
   userLockoutManagerRuntimeInvalidLoginAttemptsTotalCount OBJECT-TYPE
      SYNTAX      Counter64
      MAX-ACCESS  read-only
      STATUS      current
      DESCRIPTION "Returns the number of invalid logins attempted since this server has been started and lockouts have been enabled."
      ::= { userLockoutManagerRuntimeEntry 30  }
   
   
   userLockoutManagerRuntimeLoginAttemptsWhileLockedTotalCount OBJECT-TYPE
      SYNTAX      Counter64
      MAX-ACCESS  read-only
      STATUS      current
      DESCRIPTION "Returns the number of invalid logins attempted since this server has been started and lockouts have been enabled."
      ::= { userLockoutManagerRuntimeEntry 35  }
   
   
   userLockoutManagerRuntimeInvalidLoginUsersHighCount OBJECT-TYPE
      SYNTAX      Counter64
      MAX-ACCESS  read-only
      STATUS      current
      DESCRIPTION "Returns the highest number of users with concurrent unexpired or uncleared invalid login attempts."
      ::= { userLockoutManagerRuntimeEntry 40  }
   
   
   userLockoutManagerRuntimeUnlockedUsersTotalCount OBJECT-TYPE
      SYNTAX      Counter64
      MAX-ACCESS  read-only
      STATUS      current
      DESCRIPTION "Returns the number times users have been unlocked since this server has been started."
      ::= { userLockoutManagerRuntimeEntry 45  }
   
   
   userLockoutManagerRuntimeLockedUsersCurrentCount OBJECT-TYPE
      SYNTAX      Counter64
      MAX-ACCESS  read-only
      STATUS      current
      DESCRIPTION "Returns the number of users that are currently locked out of this server."
      ::= { userLockoutManagerRuntimeEntry 50  }
   
   
   servletRuntimeTable OBJECT-TYPE
      SYNTAX      SEQUENCE OF ServletRuntimeEntry
      MAX-ACCESS  not-accessible
      STATUS      current
      DESCRIPTION "This table Describes a servlet."
      ::= { wls 380  }
      
   
   servletRuntimeEntry OBJECT-TYPE
      SYNTAX      ServletRuntimeEntry
      MAX-ACCESS  not-accessible
      STATUS      current
      DESCRIPTION "Entry of servletRuntimeTable"
      INDEX { servletRuntimeIndex}
      ::= { servletRuntimeTable 1 }
      
   ServletRuntimeEntry ::=
      SEQUENCE
      {
         servletRuntimeIndex  DisplayString (SIZE (1..16)),
         servletRuntimeObjectName DisplayString (SIZE (1..256)),
         servletRuntimeType   DisplayString (SIZE (1..64)),
         servletRuntimeName   DisplayString (SIZE (1..64)),
         servletRuntimeParent DisplayString (SIZE (1..256)),
         servletRuntimeServletName DisplayString (SIZE (1..64)),
         servletRuntimeReloadTotalCount INTEGER,
         servletRuntimeInvocationTotalCount INTEGER,
         servletRuntimePoolMaxCapacity INTEGER,
         servletRuntimeExecutionTimeTotal INTEGER,
         servletRuntimeExecutionTimeHigh INTEGER,
         servletRuntimeExecutionTimeLow INTEGER,
         servletRuntimeExecutionTimeAverage INTEGER,
         servletRuntimeServletPath DisplayString (SIZE (1..256)),
         servletRuntimeContextPath DisplayString (SIZE (1..256)),
         servletRuntimeURL    DisplayString (SIZE (1..256)),
         servletRuntimeServletClassName OCTET STRING
      }
      
   
   servletRuntimeIndex OBJECT-TYPE
      SYNTAX      DisplayString (SIZE (1..16))
      MAX-ACCESS  read-only
      STATUS      current
      DESCRIPTION "Unique value directed from ObjectName which is used as table index"
      ::= { servletRuntimeEntry 1  }
   
   
   servletRuntimeObjectName OBJECT-TYPE
      SYNTAX      DisplayString (SIZE (1..256))
      MAX-ACCESS  read-only
      STATUS      current
      DESCRIPTION "JMX-standard MBean name"
      ::= { servletRuntimeEntry 5  }
   
   
   servletRuntimeType OBJECT-TYPE
      SYNTAX      DisplayString (SIZE (1..64))
      MAX-ACCESS  read-only
      STATUS      current
      DESCRIPTION "BEA-proprietary MBean type"
      ::= { servletRuntimeEntry 10  }
   
   
   servletRuntimeName OBJECT-TYPE
      SYNTAX      DisplayString (SIZE (1..64))
      MAX-ACCESS  read-only
      STATUS      current
      DESCRIPTION "BEA-proprietary MBean name"
      ::= { servletRuntimeEntry 15  }
   
   
   servletRuntimeParent OBJECT-TYPE
      SYNTAX      DisplayString (SIZE (1..256))
      MAX-ACCESS  read-only
      STATUS      current
      DESCRIPTION "BEA-proprietary Parent object's identification, with syntax
      <type>:<name>"
      ::= { servletRuntimeEntry 20  }
   
   
   servletRuntimeServletName OBJECT-TYPE
      SYNTAX      DisplayString (SIZE (1..64))
      MAX-ACCESS  read-only
      STATUS      current
      DESCRIPTION "Return the Servelet's name"
      ::= { servletRuntimeEntry 25  }
   
   
   servletRuntimeReloadTotalCount OBJECT-TYPE
      SYNTAX      INTEGER
      MAX-ACCESS  read-only
      STATUS      current
      DESCRIPTION "The total number of times the servelet has been reloaded."
      ::= { servletRuntimeEntry 30  }
   
   
   servletRuntimeInvocationTotalCount OBJECT-TYPE
      SYNTAX      INTEGER
      MAX-ACCESS  read-only
      STATUS      current
      DESCRIPTION "The total number of times the servelet has been invoked."
      ::= { servletRuntimeEntry 35  }
   
   
   servletRuntimePoolMaxCapacity OBJECT-TYPE
      SYNTAX      INTEGER
      MAX-ACCESS  read-only
      STATUS      current
      DESCRIPTION "The maximum capacity of this servlet for single thread model
      servlets."
      ::= { servletRuntimeEntry 40  }
   
   
   servletRuntimeExecutionTimeTotal OBJECT-TYPE
      SYNTAX      INTEGER
      MAX-ACCESS  read-only
      STATUS      current
      DESCRIPTION "The amount of time all invocations of the servlet has executed
      since created."
      ::= { servletRuntimeEntry 45  }
   
   
   servletRuntimeExecutionTimeHigh OBJECT-TYPE
      SYNTAX      INTEGER
      MAX-ACCESS  read-only
      STATUS      current
      DESCRIPTION "The amount of time the single longest invocation of the 
      servlet has executed since created."
      ::= { servletRuntimeEntry 50  }
   
   
   servletRuntimeExecutionTimeLow OBJECT-TYPE
      SYNTAX      INTEGER
      MAX-ACCESS  read-only
      STATUS      current
      DESCRIPTION "The amount of time the single shortest invocation of the 
      servlet has executed since created."
      ::= { servletRuntimeEntry 55  }
   
   
   servletRuntimeExecutionTimeAverage OBJECT-TYPE
      SYNTAX      INTEGER
      MAX-ACCESS  read-only
      STATUS      current
      DESCRIPTION "The average amount of time all invocations of the servlet have
      executed since created."
      ::= { servletRuntimeEntry 60  }
   
   
   servletRuntimeServletPath OBJECT-TYPE
      SYNTAX      DisplayString (SIZE (1..256))
      MAX-ACCESS  read-only
      STATUS      current
      DESCRIPTION "The servlet path."
      ::= { servletRuntimeEntry 65  }
   
   
   servletRuntimeContextPath OBJECT-TYPE
      SYNTAX      DisplayString (SIZE (1..256))
      MAX-ACCESS  read-only
      STATUS      current
      DESCRIPTION "context path."
      ::= { servletRuntimeEntry 70  }
   
   
   servletRuntimeURL OBJECT-TYPE
      SYNTAX      DisplayString (SIZE (1..256))
      MAX-ACCESS  read-only
      STATUS      current
      DESCRIPTION "http://<host>:port/<context path>/<servlet path>."
      ::= { servletRuntimeEntry 75  }
   
   
   servletRuntimeServletClassName OBJECT-TYPE
      SYNTAX      OCTET STRING
      MAX-ACCESS  read-only
      STATUS      current
      DESCRIPTION "Provides the servlet class name"
      ::= { servletRuntimeEntry 76  }
   
   
   servletSessionRuntimeTable OBJECT-TYPE
      SYNTAX      SEQUENCE OF ServletSessionRuntimeEntry
      MAX-ACCESS  not-accessible
      STATUS      current
      DESCRIPTION "This table is used for monitoring a WebLogic servlet session
      within a WebLogic server."
      ::= { wls 390  }
      
   
   servletSessionRuntimeEntry OBJECT-TYPE
      SYNTAX      ServletSessionRuntimeEntry
      MAX-ACCESS  not-accessible
      STATUS      current
      DESCRIPTION "Entry of servletSessionRuntimeTable"
      INDEX { servletSessionRuntimeIndex}
      ::= { servletSessionRuntimeTable 1 }
      
   ServletSessionRuntimeEntry ::=
      SEQUENCE
      {
         servletSessionRuntimeIndex DisplayString (SIZE (1..16)),
         servletSessionRuntimeObjectName DisplayString (SIZE (1..256)),
         servletSessionRuntimeType DisplayString (SIZE (1..64)),
         servletSessionRuntimeName DisplayString (SIZE (1..64)),
         servletSessionRuntimeParent DisplayString (SIZE (1..256)),
         servletSessionRuntimeTimeLastAccessed Counter64,
         servletSessionRuntimeMainAttribute DisplayString (SIZE (1..64))
      }
      
   
   servletSessionRuntimeIndex OBJECT-TYPE
      SYNTAX      DisplayString (SIZE (1..16))
      MAX-ACCESS  read-only
      STATUS      current
      DESCRIPTION "Unique value directed from ObjectName which is used as table index"
      ::= { servletSessionRuntimeEntry 1  }
   
   
   servletSessionRuntimeObjectName OBJECT-TYPE
      SYNTAX      DisplayString (SIZE (1..256))
      MAX-ACCESS  read-only
      STATUS      current
      DESCRIPTION "JMX-standard MBean name"
      ::= { servletSessionRuntimeEntry 5  }
   
   
   servletSessionRuntimeType OBJECT-TYPE
      SYNTAX      DisplayString (SIZE (1..64))
      MAX-ACCESS  read-only
      STATUS      current
      DESCRIPTION "BEA-proprietary MBean type"
      ::= { servletSessionRuntimeEntry 10  }
   
   
   servletSessionRuntimeName OBJECT-TYPE
      SYNTAX      DisplayString (SIZE (1..64))
      MAX-ACCESS  read-only
      STATUS      current
      DESCRIPTION "BEA-proprietary MBean name"
      ::= { servletSessionRuntimeEntry 15  }
   
   
   servletSessionRuntimeParent OBJECT-TYPE
      SYNTAX      DisplayString (SIZE (1..256))
      MAX-ACCESS  read-only
      STATUS      current
      DESCRIPTION "BEA-proprietary Parent object's identification, with syntax
      <type>:<name>"
      ::= { servletSessionRuntimeEntry 20  }
   
   
   servletSessionRuntimeTimeLastAccessed OBJECT-TYPE
      SYNTAX      Counter64
      MAX-ACCESS  read-only
      STATUS      current
      DESCRIPTION "Last time accessed."
      ::= { servletSessionRuntimeEntry 25  }
   
   
   servletSessionRuntimeMainAttribute OBJECT-TYPE
      SYNTAX      DisplayString (SIZE (1..64))
      MAX-ACCESS  read-only
      STATUS      current
      DESCRIPTION "Gets a Stringified copy of an attribute specified by the user (like user-name)
      associated with this session."
      ::= { servletSessionRuntimeEntry 30  }
   
   
   taskRuntimeTable OBJECT-TYPE
      SYNTAX      SEQUENCE OF TaskRuntimeEntry
      MAX-ACCESS  not-accessible
      STATUS      current
      DESCRIPTION "Exposes monitoring information about an ongoing and potentially
      long-running administrative process."
      ::= { wls 391  }
      
   
   taskRuntimeEntry OBJECT-TYPE
      SYNTAX      TaskRuntimeEntry
      MAX-ACCESS  not-accessible
      STATUS      current
      DESCRIPTION "Entry of taskRuntimeTable"
      INDEX { taskRuntimeIndex}
      ::= { taskRuntimeTable 1 }
      
   TaskRuntimeEntry ::=
      SEQUENCE
      {
         taskRuntimeIndex     DisplayString (SIZE (1..16)),
         taskRuntimeObjectName DisplayString (SIZE (1..256)),
         taskRuntimeType      DisplayString (SIZE (1..64)),
         taskRuntimeName      DisplayString (SIZE (1..64)),
         taskRuntimeParent    DisplayString (SIZE (1..256)),
         taskRuntimeBeginTime Counter64,
         taskRuntimeDescription DisplayString (SIZE (1..64)),
         taskRuntimeEndTime   Counter64,
         taskRuntimeStatus    DisplayString (SIZE (1..64)),
         taskRuntimeRunning   INTEGER,
         taskRuntimeSystemTask INTEGER
      }
      
   
   taskRuntimeIndex OBJECT-TYPE
      SYNTAX      DisplayString (SIZE (1..16))
      MAX-ACCESS  read-only
      STATUS      current
      DESCRIPTION "Unique value directed from ObjectName which is used as table index"
      ::= { taskRuntimeEntry 1  }
   
   
   taskRuntimeObjectName OBJECT-TYPE
      SYNTAX      DisplayString (SIZE (1..256))
      MAX-ACCESS  read-only
      STATUS      current
      DESCRIPTION "JMX-standard MBean name"
      ::= { taskRuntimeEntry 5  }
   
   
   taskRuntimeType OBJECT-TYPE
      SYNTAX      DisplayString (SIZE (1..64))
      MAX-ACCESS  read-only
      STATUS      current
      DESCRIPTION "BEA-proprietary MBean type"
      ::= { taskRuntimeEntry 10  }
   
   
   taskRuntimeName OBJECT-TYPE
      SYNTAX      DisplayString (SIZE (1..64))
      MAX-ACCESS  read-only
      STATUS      current
      DESCRIPTION "BEA-proprietary MBean name"
      ::= { taskRuntimeEntry 15  }
   
   
   taskRuntimeParent OBJECT-TYPE
      SYNTAX      DisplayString (SIZE (1..256))
      MAX-ACCESS  read-only
      STATUS      current
      DESCRIPTION "BEA-proprietary Parent object's identification, with syntax
      <type>:<name>"
      ::= { taskRuntimeEntry 20  }
   
   
   taskRuntimeBeginTime OBJECT-TYPE
      SYNTAX      Counter64
      MAX-ACCESS  read-only
      STATUS      current
      DESCRIPTION "Returns the time at which this task was started."
      ::= { taskRuntimeEntry 25  }
   
   
   taskRuntimeDescription OBJECT-TYPE
      SYNTAX      DisplayString (SIZE (1..64))
      MAX-ACCESS  read-only
      STATUS      current
      DESCRIPTION "Returns a short, arbitrary String describing the nature of
      this task, e.g. 'Starting MyServer.."
      ::= { taskRuntimeEntry 30  }
   
   
   taskRuntimeEndTime OBJECT-TYPE
      SYNTAX      Counter64
      MAX-ACCESS  read-only
      STATUS      current
      DESCRIPTION "Returns the time at which this task was completed.  Returns -1                           
      if the task is currently running."
      ::= { taskRuntimeEntry 35  }
   
   
   taskRuntimeStatus OBJECT-TYPE
      SYNTAX      DisplayString (SIZE (1..64))
      MAX-ACCESS  read-only
      STATUS      current
      DESCRIPTION "eturns a short, arbitrary String describing the status of
      this Task, e.g. 'Starting Server', 'Completed', 'Failed'."
      ::= { taskRuntimeEntry 40  }
   
   
   taskRuntimeRunning OBJECT-TYPE
      SYNTAX      INTEGER
      MAX-ACCESS  read-only
      STATUS      current
      DESCRIPTION "Returns true if the Task is still running."
      ::= { taskRuntimeEntry 45  }
   
   
   taskRuntimeSystemTask OBJECT-TYPE
      SYNTAX      INTEGER
      MAX-ACCESS  read-only
      STATUS      current
      DESCRIPTION "Indicates this task was initiated by the server."
      ::= { taskRuntimeEntry 50  }
   
   
   transactionNameRuntimeTable OBJECT-TYPE
      SYNTAX      SEQUENCE OF TransactionNameRuntimeEntry
      MAX-ACCESS  not-accessible
      STATUS      current
      DESCRIPTION "This table represents runtime statistics for a transaction name
      category."
      ::= { wls 410  }
      
   
   transactionNameRuntimeEntry OBJECT-TYPE
      SYNTAX      TransactionNameRuntimeEntry
      MAX-ACCESS  not-accessible
      STATUS      current
      DESCRIPTION "Entry of transactionNameRuntimeTable"
      INDEX { transactionNameRuntimeIndex}
      ::= { transactionNameRuntimeTable 1 }
      
   TransactionNameRuntimeEntry ::=
      SEQUENCE
      {
         transactionNameRuntimeIndex DisplayString (SIZE (1..16)),
         transactionNameRuntimeObjectName DisplayString (SIZE (1..256)),
         transactionNameRuntimeType DisplayString (SIZE (1..64)),
         transactionNameRuntimeName DisplayString (SIZE (1..64)),
         transactionNameRuntimeParent DisplayString (SIZE (1..256)),
         transactionNameRuntimeTransactionTotalCount INTEGER,
         transactionNameRuntimeTransactionCommittedTotalCount INTEGER,
         transactionNameRuntimeTransactionRolledBackTotalCount INTEGER,
         transactionNameRuntimeTransactionHeuristicsTotalCount INTEGER,
         transactionNameRuntimeTransactionRolledBackResourceTotalCount INTEGER,
         transactionNameRuntimeTransactionRolledBackAppTotalCount INTEGER,
         transactionNameRuntimeTransactionRolledBackSystemTotalCount INTEGER,
         transactionNameRuntimeSecondsActiveTotalCount INTEGER,
         transactionNameRuntimeTransactionRolledBackTimeoutTotalCount INTEGER,
         transactionNameRuntimeTransactionName DisplayString (SIZE (1..64)),
         transactionNameRuntimeTransactionAbandonedTotalCount Counter64
      }
      
   
   transactionNameRuntimeIndex OBJECT-TYPE
      SYNTAX      DisplayString (SIZE (1..16))
      MAX-ACCESS  read-only
      STATUS      current
      DESCRIPTION "Unique value directed from ObjectName which is used as table index"
      ::= { transactionNameRuntimeEntry 1  }
   
   
   transactionNameRuntimeObjectName OBJECT-TYPE
      SYNTAX      DisplayString (SIZE (1..256))
      MAX-ACCESS  read-only
      STATUS      current
      DESCRIPTION "JMX-standard MBean name"
      ::= { transactionNameRuntimeEntry 5  }
   
   
   transactionNameRuntimeType OBJECT-TYPE
      SYNTAX      DisplayString (SIZE (1..64))
      MAX-ACCESS  read-only
      STATUS      current
      DESCRIPTION "BEA-proprietary MBean type"
      ::= { transactionNameRuntimeEntry 10  }
   
   
   transactionNameRuntimeName OBJECT-TYPE
      SYNTAX      DisplayString (SIZE (1..64))
      MAX-ACCESS  read-only
      STATUS      current
      DESCRIPTION "BEA-proprietary MBean name"
      ::= { transactionNameRuntimeEntry 15  }
   
   
   transactionNameRuntimeParent OBJECT-TYPE
      SYNTAX      DisplayString (SIZE (1..256))
      MAX-ACCESS  read-only
      STATUS      current
      DESCRIPTION "BEA-proprietary Parent object's identification, with syntax
      <type>:<name>"
      ::= { transactionNameRuntimeEntry 20  }
   
   
   transactionNameRuntimeTransactionTotalCount OBJECT-TYPE
      SYNTAX      INTEGER
      MAX-ACCESS  read-only
      STATUS      current
      DESCRIPTION "The total number of transactions processed.
      This total includes all committed, rolled back
      and heuristic transaction completions."
      ::= { transactionNameRuntimeEntry 25  }
   
   
   transactionNameRuntimeTransactionCommittedTotalCount OBJECT-TYPE
      SYNTAX      INTEGER
      MAX-ACCESS  read-only
      STATUS      current
      DESCRIPTION "The number of committed transactions."
      ::= { transactionNameRuntimeEntry 30  }
   
   
   transactionNameRuntimeTransactionRolledBackTotalCount OBJECT-TYPE
      SYNTAX      INTEGER
      MAX-ACCESS  read-only
      STATUS      current
      DESCRIPTION "The number of transactions that were rolled back."
      ::= { transactionNameRuntimeEntry 35  }
   
   
   transactionNameRuntimeTransactionHeuristicsTotalCount OBJECT-TYPE
      SYNTAX      INTEGER
      MAX-ACCESS  read-only
      STATUS      current
      DESCRIPTION "The number of transactions that completed with a
      heuristic status."
      ::= { transactionNameRuntimeEntry 40  }
   
   
   transactionNameRuntimeTransactionRolledBackResourceTotalCount OBJECT-TYPE
      SYNTAX      INTEGER
      MAX-ACCESS  read-only
      STATUS      current
      DESCRIPTION "The number of transactions that were rolled back
      due to a resource error."
      ::= { transactionNameRuntimeEntry 45  }
   
   
   transactionNameRuntimeTransactionRolledBackAppTotalCount OBJECT-TYPE
      SYNTAX      INTEGER
      MAX-ACCESS  read-only
      STATUS      current
      DESCRIPTION "The number of transactions that were rolled back
      due to an application error."
      ::= { transactionNameRuntimeEntry 50  }
   
   
   transactionNameRuntimeTransactionRolledBackSystemTotalCount OBJECT-TYPE
      SYNTAX      INTEGER
      MAX-ACCESS  read-only
      STATUS      current
      DESCRIPTION "The number of transactions that were rolled back
      due to an internal system error."
      ::= { transactionNameRuntimeEntry 55  }
   
   
   transactionNameRuntimeSecondsActiveTotalCount OBJECT-TYPE
      SYNTAX      INTEGER
      MAX-ACCESS  read-only
      STATUS      current
      DESCRIPTION "The total number of seconds for all committed
      transactions."
      ::= { transactionNameRuntimeEntry 60  }
   
   
   transactionNameRuntimeTransactionRolledBackTimeoutTotalCount OBJECT-TYPE
      SYNTAX      INTEGER
      MAX-ACCESS  read-only
      STATUS      current
      DESCRIPTION "The total number of seconds for all committed
      transactions."
      ::= { transactionNameRuntimeEntry 65  }
   
   
   transactionNameRuntimeTransactionName OBJECT-TYPE
      SYNTAX      DisplayString (SIZE (1..64))
      MAX-ACCESS  read-only
      STATUS      current
      DESCRIPTION "The transaction name."
      ::= { transactionNameRuntimeEntry 70  }
   
   
   transactionNameRuntimeTransactionAbandonedTotalCount OBJECT-TYPE
      SYNTAX      Counter64
      MAX-ACCESS  read-only
      STATUS      current
      DESCRIPTION "The total number of transactions that were abandoned since the server was started."
      ::= { transactionNameRuntimeEntry 71  }
   
   
   transactionResourceRuntimeTable OBJECT-TYPE
      SYNTAX      SEQUENCE OF TransactionResourceRuntimeEntry
      MAX-ACCESS  not-accessible
      STATUS      current
      DESCRIPTION "This table represents runtime statistics for a transactional
      resource."
      ::= { wls 420  }
      
   
   transactionResourceRuntimeEntry OBJECT-TYPE
      SYNTAX      TransactionResourceRuntimeEntry
      MAX-ACCESS  not-accessible
      STATUS      current
      DESCRIPTION "Entry of transactionResourceRuntimeTable"
      INDEX { transactionResourceRuntimeIndex}
      ::= { transactionResourceRuntimeTable 1 }
      
   TransactionResourceRuntimeEntry ::=
      SEQUENCE
      {
         transactionResourceRuntimeIndex DisplayString (SIZE (1..16)),
         transactionResourceRuntimeObjectName DisplayString (SIZE (1..256)),
         transactionResourceRuntimeType DisplayString (SIZE (1..64)),
         transactionResourceRuntimeName DisplayString (SIZE (1..64)),
         transactionResourceRuntimeParent DisplayString (SIZE (1..256)),
         transactionResourceRuntimeTransactionTotalCount Counter64,
         transactionResourceRuntimeTransactionCommittedTotalCount Counter64,
         transactionResourceRuntimeTransactionRolledBackTotalCount Counter64,
         transactionResourceRuntimeTransactionHeuristicsTotalCount Counter64,
         transactionResourceRuntimeResourceName DisplayString (SIZE (1..64)),
         transactionResourceRuntimeTransactionHeuristicCommitTotalCount Counter64,
         transactionResourceRuntimeTransactionHeuristicRollbackTotalCount Counter64,
         transactionResourceRuntimeTransactionHeuristicMixedTotalCount Counter64,
         transactionResourceRuntimeTransactionHeuristicHazardTotalCount Counter64
      }
      
   
   transactionResourceRuntimeIndex OBJECT-TYPE
      SYNTAX      DisplayString (SIZE (1..16))
      MAX-ACCESS  read-only
      STATUS      current
      DESCRIPTION "Unique value directed from ObjectName which is used as table index"
      ::= { transactionResourceRuntimeEntry 1  }
   
   
   transactionResourceRuntimeObjectName OBJECT-TYPE
      SYNTAX      DisplayString (SIZE (1..256))
      MAX-ACCESS  read-only
      STATUS      current
      DESCRIPTION "JMX-standard MBean name"
      ::= { transactionResourceRuntimeEntry 5  }
   
   
   transactionResourceRuntimeType OBJECT-TYPE
      SYNTAX      DisplayString (SIZE (1..64))
      MAX-ACCESS  read-only
      STATUS      current
      DESCRIPTION "BEA-proprietary MBean type"
      ::= { transactionResourceRuntimeEntry 10  }
   
   
   transactionResourceRuntimeName OBJECT-TYPE
      SYNTAX      DisplayString (SIZE (1..64))
      MAX-ACCESS  read-only
      STATUS      current
      DESCRIPTION "BEA-proprietary MBean name"
      ::= { transactionResourceRuntimeEntry 15  }
   
   
   transactionResourceRuntimeParent OBJECT-TYPE
      SYNTAX      DisplayString (SIZE (1..256))
      MAX-ACCESS  read-only
      STATUS      current
      DESCRIPTION "BEA-proprietary Parent object's identification, with syntax
      <type>:<name>"
      ::= { transactionResourceRuntimeEntry 20  }
   
   
   transactionResourceRuntimeTransactionTotalCount OBJECT-TYPE
      SYNTAX      Counter64
      MAX-ACCESS  read-only
      STATUS      current
      DESCRIPTION "The total number of transactions processed.
      This total includes all committed, rolled back
      and heuristic transaction completions."
      ::= { transactionResourceRuntimeEntry 25  }
   
   
   transactionResourceRuntimeTransactionCommittedTotalCount OBJECT-TYPE
      SYNTAX      Counter64
      MAX-ACCESS  read-only
      STATUS      current
      DESCRIPTION "The number of committed transactions."
      ::= { transactionResourceRuntimeEntry 30  }
   
   
   transactionResourceRuntimeTransactionRolledBackTotalCount OBJECT-TYPE
      SYNTAX      Counter64
      MAX-ACCESS  read-only
      STATUS      current
      DESCRIPTION "The number of transactions that were rolled back."
      ::= { transactionResourceRuntimeEntry 35  }
   
   
   transactionResourceRuntimeTransactionHeuristicsTotalCount OBJECT-TYPE
      SYNTAX      Counter64
      MAX-ACCESS  read-only
      STATUS      current
      DESCRIPTION "The number of transactions that completed with a
      heuristic status."
      ::= { transactionResourceRuntimeEntry 40  }
   
   
   transactionResourceRuntimeResourceName OBJECT-TYPE
      SYNTAX      DisplayString (SIZE (1..64))
      MAX-ACCESS  read-only
      STATUS      current
      DESCRIPTION "The resource name."
      ::= { transactionResourceRuntimeEntry 45  }
   
   
   transactionResourceRuntimeTransactionHeuristicCommitTotalCount OBJECT-TYPE
      SYNTAX      Counter64
      MAX-ACCESS  read-only
      STATUS      current
      DESCRIPTION "The number of transactions for which this resource has
      returned a heuristic commit decision."
      ::= { transactionResourceRuntimeEntry 50  }
   
   
   transactionResourceRuntimeTransactionHeuristicRollbackTotalCount OBJECT-TYPE
      SYNTAX      Counter64
      MAX-ACCESS  read-only
      STATUS      current
      DESCRIPTION "The number of transactions for which this resource has
      returned a heuristic rollback decision."
      ::= { transactionResourceRuntimeEntry 55  }
   
   
   transactionResourceRuntimeTransactionHeuristicMixedTotalCount OBJECT-TYPE
      SYNTAX      Counter64
      MAX-ACCESS  read-only
      STATUS      current
      DESCRIPTION "The number of transactions for which this resource has
      reported a heuristic mixed decision."
      ::= { transactionResourceRuntimeEntry 60  }
   
   
   transactionResourceRuntimeTransactionHeuristicHazardTotalCount OBJECT-TYPE
      SYNTAX      Counter64
      MAX-ACCESS  read-only
      STATUS      current
      DESCRIPTION "The number of transactions for which this resource has
      reported a heuristic hazard decision."
      ::= { transactionResourceRuntimeEntry 65  }
   
   
   webAppComponentRuntimeTable OBJECT-TYPE
      SYNTAX      SEQUENCE OF WebAppComponentRuntimeEntry
      MAX-ACCESS  not-accessible
      STATUS      current
      DESCRIPTION "This table describes a servlet component (servlet context)."
      ::= { wls 430  }
      
   
   webAppComponentRuntimeEntry OBJECT-TYPE
      SYNTAX      WebAppComponentRuntimeEntry
      MAX-ACCESS  not-accessible
      STATUS      current
      DESCRIPTION "Entry of webAppComponentRuntimeTable"
      INDEX { webAppComponentRuntimeIndex}
      ::= { webAppComponentRuntimeTable 1 }
      
   WebAppComponentRuntimeEntry ::=
      SEQUENCE
      {
         webAppComponentRuntimeIndex DisplayString (SIZE (1..16)),
         webAppComponentRuntimeObjectName DisplayString (SIZE (1..256)),
         webAppComponentRuntimeType DisplayString (SIZE (1..64)),
         webAppComponentRuntimeName DisplayString (SIZE (1..64)),
         webAppComponentRuntimeParent DisplayString (SIZE (1..256)),
         webAppComponentRuntimeComponentName DisplayString (SIZE (1..64)),
         webAppComponentRuntimeStatus DisplayString (SIZE (1..64)),
         webAppComponentRuntimeSourceInfo DisplayString (SIZE (1..256)),
         webAppComponentRuntimeServletSessions DisplayString (SIZE (1..2048)),
         webAppComponentRuntimeServlets DisplayString (SIZE (1..2048)),
         webAppComponentRuntimeOpenSessionsCurrentCount INTEGER,
         webAppComponentRuntimeOpenSessionsHighCount INTEGER,
         webAppComponentRuntimeSessionsOpenedTotalCount INTEGER,
         webAppComponentRuntimeSingleThreadedServletPoolSize INTEGER,
         webAppComponentRuntimeJSPVerbose OCTET STRING,
         webAppComponentRuntimeIndexDirectoryEnabled OCTET STRING,
         webAppComponentRuntimeModuleId OCTET STRING,
         webAppComponentRuntimeJSPDebug OCTET STRING,
         webAppComponentRuntimeSessionCookieName OCTET STRING,
         webAppComponentRuntimeSessionCookieDomain OCTET STRING,
         webAppComponentRuntimeFilterDispatchedRequestsEnabled OCTET STRING,
         webAppComponentRuntimeLogFilename OCTET STRING,
         webAppComponentRuntimeSessionCookiePath OCTET STRING,
         webAppComponentRuntimeJSPKeepGenerated OCTET STRING,
         webAppComponentRuntimeSessionCookieComment OCTET STRING,
         webAppComponentRuntimeJSPCompileCommand OCTET STRING,
         webAppComponentRuntimeJSPPageCheckSecs Counter64,
         webAppComponentRuntimeContextRoot OCTET STRING,
         webAppComponentRuntimeModuleURI OCTET STRING,
         webAppComponentRuntimeSessionInvalidationIntervalSecs INTEGER,
         webAppComponentRuntimeServletReloadCheckSecs INTEGER,
         webAppComponentRuntimeSessionCookieMaxAgeSecs INTEGER,
         webAppComponentRuntimeSessionTimeoutSecs INTEGER,
         webAppComponentRuntimeSessionIDLength INTEGER,
         webAppComponentRuntimeDeploymentState INTEGER,
         webAppComponentRuntimeSessionMonitoringEnabled OCTET STRING
      }
      
   
   webAppComponentRuntimeIndex OBJECT-TYPE
      SYNTAX      DisplayString (SIZE (1..16))
      MAX-ACCESS  read-only
      STATUS      current
      DESCRIPTION "Unique value directed from ObjectName which is used as table index"
      ::= { webAppComponentRuntimeEntry 1  }
   
   
   webAppComponentRuntimeObjectName OBJECT-TYPE
      SYNTAX      DisplayString (SIZE (1..256))
      MAX-ACCESS  read-only
      STATUS      current
      DESCRIPTION "JMX-standard MBean name"
      ::= { webAppComponentRuntimeEntry 5  }
   
   
   webAppComponentRuntimeType OBJECT-TYPE
      SYNTAX      DisplayString (SIZE (1..64))
      MAX-ACCESS  read-only
      STATUS      current
      DESCRIPTION "BEA-proprietary MBean type"
      ::= { webAppComponentRuntimeEntry 10  }
   
   
   webAppComponentRuntimeName OBJECT-TYPE
      SYNTAX      DisplayString (SIZE (1..64))
      MAX-ACCESS  read-only
      STATUS      current
      DESCRIPTION "BEA-proprietary MBean name"
      ::= { webAppComponentRuntimeEntry 15  }
   
   
   webAppComponentRuntimeParent OBJECT-TYPE
      SYNTAX      DisplayString (SIZE (1..256))
      MAX-ACCESS  read-only
      STATUS      current
      DESCRIPTION "BEA-proprietary Parent object's identification, with syntax
      <type>:<name>"
      ::= { webAppComponentRuntimeEntry 20  }
   
   
   webAppComponentRuntimeComponentName OBJECT-TYPE
      SYNTAX      DisplayString (SIZE (1..64))
      MAX-ACCESS  read-only
      STATUS      current
      DESCRIPTION "Return the component's name."
      ::= { webAppComponentRuntimeEntry 25  }
   
   
   webAppComponentRuntimeStatus OBJECT-TYPE
      SYNTAX      DisplayString (SIZE (1..64))
      MAX-ACCESS  read-only
      STATUS      current
      DESCRIPTION "Return the component's status."
      ::= { webAppComponentRuntimeEntry 30  }
   
   
   webAppComponentRuntimeSourceInfo OBJECT-TYPE
      SYNTAX      DisplayString (SIZE (1..256))
      MAX-ACCESS  read-only
      STATUS      current
      DESCRIPTION "Return an informative string about the component's source."
      ::= { webAppComponentRuntimeEntry 35  }
   
   
   webAppComponentRuntimeServletSessions OBJECT-TYPE
      SYNTAX      DisplayString (SIZE (1..2048))
      MAX-ACCESS  read-only
      STATUS      current
      DESCRIPTION "Return the number of elements of the array of ServletRuntimeMBeans associated with this component"
      ::= { webAppComponentRuntimeEntry 40  }
   
   
   webAppComponentRuntimeServlets OBJECT-TYPE
      SYNTAX      DisplayString (SIZE (1..2048))
      MAX-ACCESS  read-only
      STATUS      current
      DESCRIPTION "Return an array of ServletRuntimeMBeans associated with this component"
      ::= { webAppComponentRuntimeEntry 45  }
   
   
   webAppComponentRuntimeOpenSessionsCurrentCount OBJECT-TYPE
      SYNTAX      INTEGER
      MAX-ACCESS  read-only
      STATUS      current
      DESCRIPTION "The current total number of open sessions in this component."
      ::= { webAppComponentRuntimeEntry 50  }
   
   
   webAppComponentRuntimeOpenSessionsHighCount OBJECT-TYPE
      SYNTAX      INTEGER
      MAX-ACCESS  read-only
      STATUS      current
      DESCRIPTION "The high water mark of the total number of open sessions
      in this server. The count starts at zero each time
      the server is activated."
      ::= { webAppComponentRuntimeEntry 55  }
   
   
   webAppComponentRuntimeSessionsOpenedTotalCount OBJECT-TYPE
      SYNTAX      INTEGER
      MAX-ACCESS  read-only
      STATUS      current
      DESCRIPTION "The total number of sessions opened in this server."
      ::= { webAppComponentRuntimeEntry 60  }
   
   
   webAppComponentRuntimeSingleThreadedServletPoolSize OBJECT-TYPE
      SYNTAX      INTEGER
      MAX-ACCESS  read-only
      STATUS      current
      DESCRIPTION "Provides the single threaded servlet pool size as it is configured in weblogic.xml."
      ::= { webAppComponentRuntimeEntry 61  }
   
   
   webAppComponentRuntimeJSPVerbose OBJECT-TYPE
      SYNTAX      OCTET STRING
      MAX-ACCESS  read-only
      STATUS      current
      DESCRIPTION "Provides the jsp's verbose parameter value as it is configured in weblogic.xml."
      ::= { webAppComponentRuntimeEntry 62  }
   
   
   webAppComponentRuntimeIndexDirectoryEnabled OBJECT-TYPE
      SYNTAX      OCTET STRING
      MAX-ACCESS  read-only
      STATUS      current
      DESCRIPTION "Provides the directory indexing indicator as it is configured in weblogic.xml."
      ::= { webAppComponentRuntimeEntry 63  }
   
   
   webAppComponentRuntimeModuleId OBJECT-TYPE
      SYNTAX      OCTET STRING
      MAX-ACCESS  read-only
      STATUS      current
      DESCRIPTION "Returns the identifier for this Component.  The identifier is unique within the application.  Typical modules will use the URI for their id.  Web Modules will return their context-root since the web-uri may not be unique within an EAR."
      ::= { webAppComponentRuntimeEntry 64  }
   
   
   webAppComponentRuntimeJSPDebug OBJECT-TYPE
      SYNTAX      OCTET STRING
      MAX-ACCESS  read-only
      STATUS      current
      DESCRIPTION "Provides the jsp's debug/linenumbers parameter value as it is configured in weblogic.xml."
      ::= { webAppComponentRuntimeEntry 65  }
   
   
   webAppComponentRuntimeSessionCookieName OBJECT-TYPE
      SYNTAX      OCTET STRING
      MAX-ACCESS  read-only
      STATUS      current
      DESCRIPTION "By default, all applications on WebLogic Server specify 'JSESSIONID' as the cookie name. To provide a more specific name, edit your application's weblogic.xml deployment descriptor."
      ::= { webAppComponentRuntimeEntry 66  }
   
   
   webAppComponentRuntimeSessionCookieDomain OBJECT-TYPE
      SYNTAX      OCTET STRING
      MAX-ACCESS  read-only
      STATUS      current
      DESCRIPTION "By default, clients can return cookies only to the server that issued the cookie. You can change this default behavior by editing your application's weblogic.xml deployment descriptor.  For more information, see Cookie.setDomain() in the Servlet specification from Sun Microsystems."
      ::= { webAppComponentRuntimeEntry 67  }
   
   
   webAppComponentRuntimeFilterDispatchedRequestsEnabled OBJECT-TYPE
      SYNTAX      OCTET STRING
      MAX-ACCESS  read-only
      STATUS      current
      DESCRIPTION "Indicates whether the dispatched requests are filtered as configured in weblogic.xml."
      ::= { webAppComponentRuntimeEntry 68  }
   
   
   webAppComponentRuntimeLogFilename OBJECT-TYPE
      SYNTAX      OCTET STRING
      MAX-ACCESS  read-only
      STATUS      current
      DESCRIPTION "Returns the log filename as configured in the 'logging/log-filename' element in weblogic.xml"
      ::= { webAppComponentRuntimeEntry 69  }
   
   
   webAppComponentRuntimeSessionCookiePath OBJECT-TYPE
      SYNTAX      OCTET STRING
      MAX-ACCESS  read-only
      STATUS      current
      DESCRIPTION "Provides the path name to which clients send cookies."
      ::= { webAppComponentRuntimeEntry 70  }
   
   
   webAppComponentRuntimeJSPKeepGenerated OBJECT-TYPE
      SYNTAX      OCTET STRING
      MAX-ACCESS  read-only
      STATUS      current
      DESCRIPTION "Provides the jsp's KeepGenerated parameter value as it is configured in weblogic.xml."
      ::= { webAppComponentRuntimeEntry 71  }
   
   
   webAppComponentRuntimeSessionCookieComment OBJECT-TYPE
      SYNTAX      OCTET STRING
      MAX-ACCESS  read-only
      STATUS      current
      DESCRIPTION "By default, all applications on WebLogic Server specify 'WebLogic Session Tracking Cookie' as the cookie comment. To provide a more specific comment, edit your application's weblogic.xml deployment descriptor."
      ::= { webAppComponentRuntimeEntry 72  }
   
   
   webAppComponentRuntimeJSPCompileCommand OBJECT-TYPE
      SYNTAX      OCTET STRING
      MAX-ACCESS  read-only
      STATUS      current
      DESCRIPTION "Provides the jsp's compileCommand as it is configured in weblogic.xml."
      ::= { webAppComponentRuntimeEntry 73  }
   
   
   webAppComponentRuntimeJSPPageCheckSecs OBJECT-TYPE
      SYNTAX      Counter64
      MAX-ACCESS  read-only
      STATUS      current
      DESCRIPTION "Provides the jsp's PageCheckSecs as it is configured in weblogic.xml."
      ::= { webAppComponentRuntimeEntry 74  }
   
   
   webAppComponentRuntimeContextRoot OBJECT-TYPE
      SYNTAX      OCTET STRING
      MAX-ACCESS  read-only
      STATUS      current
      DESCRIPTION "Returns the context root (context path) for the webapp"
      ::= { webAppComponentRuntimeEntry 75  }
   
   
   webAppComponentRuntimeModuleURI OBJECT-TYPE
      SYNTAX      OCTET STRING
      MAX-ACCESS  read-only
      STATUS      current
      DESCRIPTION "Returns the web-uri as configured in application.xml for the webapp. For a standalone war it will return the docroot (if exploded) or name of the war file (if archived)."
      ::= { webAppComponentRuntimeEntry 76  }
   
   
   webAppComponentRuntimeSessionInvalidationIntervalSecs OBJECT-TYPE
      SYNTAX      INTEGER
      MAX-ACCESS  read-only
      STATUS      current
      DESCRIPTION "Provides the invalidation check timer interval configured for http sessions."
      ::= { webAppComponentRuntimeEntry 77  }
   
   
   webAppComponentRuntimeServletReloadCheckSecs OBJECT-TYPE
      SYNTAX      INTEGER
      MAX-ACCESS  read-only
      STATUS      current
      DESCRIPTION "Provides the servlet reload check seconds as it is configured in weblogic.xml."
      ::= { webAppComponentRuntimeEntry 78  }
   
   
   webAppComponentRuntimeSessionCookieMaxAgeSecs OBJECT-TYPE
      SYNTAX      INTEGER
      MAX-ACCESS  read-only
      STATUS      current
      DESCRIPTION "Provides the life span of the session cookie, in seconds, after which it expires on the client. If the value is 0, the cookie expires immediately. If set to -1, the cookie expires when the user exits the browser."
      ::= { webAppComponentRuntimeEntry 79  }
   
   
   webAppComponentRuntimeSessionTimeoutSecs OBJECT-TYPE
      SYNTAX      INTEGER
      MAX-ACCESS  read-only
      STATUS      current
      DESCRIPTION "Provides the timeout configured for http sessions."
      ::= { webAppComponentRuntimeEntry 80  }
   
   
   webAppComponentRuntimeSessionIDLength OBJECT-TYPE
      SYNTAX      INTEGER
      MAX-ACCESS  read-only
      STATUS      current
      DESCRIPTION "Provides the session ID length configured for http sessions."
      ::= { webAppComponentRuntimeEntry 81  }
   
   
   webAppComponentRuntimeDeploymentState OBJECT-TYPE
      SYNTAX      INTEGER
      MAX-ACCESS  read-only
      STATUS      current
      DESCRIPTION "The current deployment state of the module."
      ::= { webAppComponentRuntimeEntry 82  }
   
   
   webAppComponentRuntimeSessionMonitoringEnabled OBJECT-TYPE
      SYNTAX      OCTET STRING
      MAX-ACCESS  read-only
      STATUS      current
      DESCRIPTION "Provides the session monitoring indicator as it is configured in weblogic.xml."
      ::= { webAppComponentRuntimeEntry 83  }
   
   
   webServerRuntimeTable OBJECT-TYPE
      SYNTAX      SEQUENCE OF WebServerRuntimeEntry
      MAX-ACCESS  not-accessible
      STATUS      current
      DESCRIPTION "This table describes the web server."
      ::= { wls 431  }
      
   
   webServerRuntimeEntry OBJECT-TYPE
      SYNTAX      WebServerRuntimeEntry
      MAX-ACCESS  not-accessible
      STATUS      current
      DESCRIPTION "Entry of webServerRuntimeTable"
      INDEX { webServerRuntimeIndex}
      ::= { webServerRuntimeTable 1 }
      
   WebServerRuntimeEntry ::=
      SEQUENCE
      {
         webServerRuntimeIndex DisplayString (SIZE (1..16)),
         webServerRuntimeObjectName DisplayString (SIZE (1..256)),
         webServerRuntimeType DisplayString (SIZE (1..64)),
         webServerRuntimeName DisplayString (SIZE (1..64)),
         webServerRuntimeParent DisplayString (SIZE (1..256)),
         webServerRuntimeWebServerName DisplayString (SIZE (1..64)),
         webServerRuntimeDefaultWebServer OCTET STRING
      }
      
   
   webServerRuntimeIndex OBJECT-TYPE
      SYNTAX      DisplayString (SIZE (1..16))
      MAX-ACCESS  read-only
      STATUS      current
      DESCRIPTION "Unique value directed from ObjectName which is used as table index"
      ::= { webServerRuntimeEntry 1  }
   
   
   webServerRuntimeObjectName OBJECT-TYPE
      SYNTAX      DisplayString (SIZE (1..256))
      MAX-ACCESS  read-only
      STATUS      current
      DESCRIPTION "JMX-standard MBean name"
      ::= { webServerRuntimeEntry 5  }
   
   
   webServerRuntimeType OBJECT-TYPE
      SYNTAX      DisplayString (SIZE (1..64))
      MAX-ACCESS  read-only
      STATUS      current
      DESCRIPTION "BEA-proprietary MBean type"
      ::= { webServerRuntimeEntry 10  }
   
   
   webServerRuntimeName OBJECT-TYPE
      SYNTAX      DisplayString (SIZE (1..64))
      MAX-ACCESS  read-only
      STATUS      current
      DESCRIPTION "BEA-proprietary MBean name"
      ::= { webServerRuntimeEntry 15  }
   
   
   webServerRuntimeParent OBJECT-TYPE
      SYNTAX      DisplayString (SIZE (1..256))
      MAX-ACCESS  read-only
      STATUS      current
      DESCRIPTION "BEA-proprietary Parent object's identification, with syntax
      <type>:<name>"
      ::= { webServerRuntimeEntry 20  }
   
   
   webServerRuntimeWebServerName OBJECT-TYPE
      SYNTAX      DisplayString (SIZE (1..64))
      MAX-ACCESS  read-only
      STATUS      current
      DESCRIPTION "Return the web server's name."
      ::= { webServerRuntimeEntry 25  }
   
   
   webServerRuntimeDefaultWebServer OBJECT-TYPE
      SYNTAX      OCTET STRING
      MAX-ACCESS  read-only
      STATUS      current
      DESCRIPTION "Indicates whether it is the default WebServer or a VirtualHost"
      ::= { webServerRuntimeEntry 26  }
   
   
   wlecConnectionPoolRuntimeTable OBJECT-TYPE
      SYNTAX      SEQUENCE OF WlecConnectionPoolRuntimeEntry
      MAX-ACCESS  not-accessible
      STATUS      current
      DESCRIPTION "This table is used for monitoring a WebLogic WLEC Connection Pool"
      ::= { wls 440  }
      
   
   wlecConnectionPoolRuntimeEntry OBJECT-TYPE
      SYNTAX      WlecConnectionPoolRuntimeEntry
      MAX-ACCESS  not-accessible
      STATUS      current
      DESCRIPTION "Entry of wlecConnectionPoolRuntimeTable"
      INDEX { wlecConnectionPoolRuntimeIndex}
      ::= { wlecConnectionPoolRuntimeTable 1 }
      
   WlecConnectionPoolRuntimeEntry ::=
      SEQUENCE
      {
         wlecConnectionPoolRuntimeIndex DisplayString (SIZE (1..16)),
         wlecConnectionPoolRuntimeObjectName DisplayString (SIZE (1..256)),
         wlecConnectionPoolRuntimeType DisplayString (SIZE (1..64)),
         wlecConnectionPoolRuntimeName DisplayString (SIZE (1..64)),
         wlecConnectionPoolRuntimeParent DisplayString (SIZE (1..256)),
         wlecConnectionPoolRuntimePoolName DisplayString (SIZE (1..64)),
         wlecConnectionPoolRuntimeWLEDomainName DisplayString (SIZE (1..64)),
         wlecConnectionPoolRuntimeMaxCapacity INTEGER,
         wlecConnectionPoolRuntimePoolState DisplayString (SIZE (1..16)),
         wlecConnectionPoolRuntimeSecurityContextPropagation INTEGER
                     {
                        true(1),
                        false(2)
                     }
         ,
         wlecConnectionPoolRuntimeCertificateBasedAuthentication INTEGER
                     {
                        true(1),
                        false(2)
                     }
         ,
         wlecConnectionPoolRuntimeConnections DisplayString (SIZE (1..2048))
      }
      
   
   wlecConnectionPoolRuntimeIndex OBJECT-TYPE
      SYNTAX      DisplayString (SIZE (1..16))
      MAX-ACCESS  read-only
      STATUS      current
      DESCRIPTION "Unique value directed from ObjectName which is used as table index"
      ::= { wlecConnectionPoolRuntimeEntry 1  }
   
   
   wlecConnectionPoolRuntimeObjectName OBJECT-TYPE
      SYNTAX      DisplayString (SIZE (1..256))
      MAX-ACCESS  read-only
      STATUS      current
      DESCRIPTION "JMX-standard MBean name"
      ::= { wlecConnectionPoolRuntimeEntry 5  }
   
   
   wlecConnectionPoolRuntimeType OBJECT-TYPE
      SYNTAX      DisplayString (SIZE (1..64))
      MAX-ACCESS  read-only
      STATUS      current
      DESCRIPTION "BEA-proprietary MBean type"
      ::= { wlecConnectionPoolRuntimeEntry 10  }
   
   
   wlecConnectionPoolRuntimeName OBJECT-TYPE
      SYNTAX      DisplayString (SIZE (1..64))
      MAX-ACCESS  read-only
      STATUS      current
      DESCRIPTION "BEA-proprietary MBean name"
      ::= { wlecConnectionPoolRuntimeEntry 15  }
   
   
   wlecConnectionPoolRuntimeParent OBJECT-TYPE
      SYNTAX      DisplayString (SIZE (1..256))
      MAX-ACCESS  read-only
      STATUS      current
      DESCRIPTION "BEA-proprietary Parent object's identification, with syntax
      <type>:<name>"
      ::= { wlecConnectionPoolRuntimeEntry 20  }
   
   
   wlecConnectionPoolRuntimePoolName OBJECT-TYPE
      SYNTAX      DisplayString (SIZE (1..64))
      MAX-ACCESS  read-only
      STATUS      current
      DESCRIPTION "The configured name of this WLEC pool."
      ::= { wlecConnectionPoolRuntimeEntry 25  }
   
   
   wlecConnectionPoolRuntimeWLEDomainName OBJECT-TYPE
      SYNTAX      DisplayString (SIZE (1..64))
      MAX-ACCESS  read-only
      STATUS      current
      DESCRIPTION "The WLE DomainName this WLEC pool is connected to."
      ::= { wlecConnectionPoolRuntimeEntry 30  }
   
   
   wlecConnectionPoolRuntimeMaxCapacity OBJECT-TYPE
      SYNTAX      INTEGER
      MAX-ACCESS  read-only
      STATUS      current
      DESCRIPTION "The maximum capacity configured for this WLEC pool."
      ::= { wlecConnectionPoolRuntimeEntry 35  }
   
   
   wlecConnectionPoolRuntimePoolState OBJECT-TYPE
      SYNTAX      DisplayString (SIZE (1..16))
      MAX-ACCESS  read-only
      STATUS      current
      DESCRIPTION "The pool state as one of 'Active' OR 'Suspended'"
      ::= { wlecConnectionPoolRuntimeEntry 40  }
   
   
   wlecConnectionPoolRuntimeSecurityContextPropagation OBJECT-TYPE
      SYNTAX      INTEGER
                  {
                     true(1),
                     false(2)
                  }
      
      MAX-ACCESS  read-only
      STATUS      current
      DESCRIPTION "A boolean value (true Or false). Is the security context propagated"
      ::= { wlecConnectionPoolRuntimeEntry 45  }
   
   
   wlecConnectionPoolRuntimeCertificateBasedAuthentication OBJECT-TYPE
      SYNTAX      INTEGER
                  {
                     true(1),
                     false(2)
                  }
      
      MAX-ACCESS  read-only
      STATUS      current
      DESCRIPTION "A boolean value (true Or false). Is certificate-based authentication enabled"
      ::= { wlecConnectionPoolRuntimeEntry 50  }
   
   
   wlecConnectionPoolRuntimeConnections OBJECT-TYPE
      SYNTAX      DisplayString (SIZE (1..2048))
      MAX-ACCESS  read-only
      STATUS      current
      DESCRIPTION "An array of WLECConnectionRuntimeMBeans that each
      represents the statistics for a WLEC Connection."
      ::= { wlecConnectionPoolRuntimeEntry 55  }
   
   
   wlecConnectionRuntimeTable OBJECT-TYPE
      SYNTAX      SEQUENCE OF WlecConnectionRuntimeEntry
      MAX-ACCESS  not-accessible
      STATUS      current
      DESCRIPTION "This table is used for monitoring individual WebLogic WLEC connections"
      ::= { wls 450  }
      
   
   wlecConnectionRuntimeEntry OBJECT-TYPE
      SYNTAX      WlecConnectionRuntimeEntry
      MAX-ACCESS  not-accessible
      STATUS      current
      DESCRIPTION "Entry of wlecConnectionRuntimeTable"
      INDEX { wlecConnectionRuntimeIndex}
      ::= { wlecConnectionRuntimeTable 1 }
      
   WlecConnectionRuntimeEntry ::=
      SEQUENCE
      {
         wlecConnectionRuntimeIndex DisplayString (SIZE (1..16)),
         wlecConnectionRuntimeObjectName DisplayString (SIZE (1..256)),
         wlecConnectionRuntimeType DisplayString (SIZE (1..64)),
         wlecConnectionRuntimeName DisplayString (SIZE (1..64)),
         wlecConnectionRuntimeParent DisplayString (SIZE (1..256)),
         wlecConnectionRuntimeAddress DisplayString (SIZE (1..256)),
         wlecConnectionRuntimeLastAccessTime DisplayString (SIZE (1..32)),
         wlecConnectionRuntimeAlive INTEGER
                     {
                        true(1),
                        false(2)
                     }
         ,
         wlecConnectionRuntimeRequestCount INTEGER,
         wlecConnectionRuntimePendingRequestCount INTEGER,
         wlecConnectionRuntimeErrorCount INTEGER,
         wlecConnectionRuntimeInTransaction INTEGER
                     {
                        true(1),
                        false(2)
                     }
      }
      
   
   wlecConnectionRuntimeIndex OBJECT-TYPE
      SYNTAX      DisplayString (SIZE (1..16))
      MAX-ACCESS  read-only
      STATUS      current
      DESCRIPTION "Unique value directed from ObjectName which is used as table index"
      ::= { wlecConnectionRuntimeEntry 1  }
   
   
   wlecConnectionRuntimeObjectName OBJECT-TYPE
      SYNTAX      DisplayString (SIZE (1..256))
      MAX-ACCESS  read-only
      STATUS      current
      DESCRIPTION "JMX-standard MBean name"
      ::= { wlecConnectionRuntimeEntry 5  }
   
   
   wlecConnectionRuntimeType OBJECT-TYPE
      SYNTAX      DisplayString (SIZE (1..64))
      MAX-ACCESS  read-only
      STATUS      current
      DESCRIPTION "BEA-proprietary MBean type"
      ::= { wlecConnectionRuntimeEntry 10  }
   
   
   wlecConnectionRuntimeName OBJECT-TYPE
      SYNTAX      DisplayString (SIZE (1..64))
      MAX-ACCESS  read-only
      STATUS      current
      DESCRIPTION "BEA-proprietary MBean name"
      ::= { wlecConnectionRuntimeEntry 15  }
   
   
   wlecConnectionRuntimeParent OBJECT-TYPE
      SYNTAX      DisplayString (SIZE (1..256))
      MAX-ACCESS  read-only
      STATUS      current
      DESCRIPTION "BEA-proprietary Parent object's identification, with syntax
      <type>:<name>"
      ::= { wlecConnectionRuntimeEntry 20  }
   
   
   wlecConnectionRuntimeAddress OBJECT-TYPE
      SYNTAX      DisplayString (SIZE (1..256))
      MAX-ACCESS  read-only
      STATUS      current
      DESCRIPTION "The connection Address"
      ::= { wlecConnectionRuntimeEntry 25  }
   
   
   wlecConnectionRuntimeLastAccessTime OBJECT-TYPE
      SYNTAX      DisplayString (SIZE (1..32))
      MAX-ACCESS  read-only
      STATUS      current
      DESCRIPTION "The Last Access Date and Time"
      ::= { wlecConnectionRuntimeEntry 30  }
   
   
   wlecConnectionRuntimeAlive OBJECT-TYPE
      SYNTAX      INTEGER
                  {
                     true(1),
                     false(2)
                  }
      
      MAX-ACCESS  read-only
      STATUS      current
      DESCRIPTION "A boolean value (true Or false). Returns the connection Alive indicator"
      ::= { wlecConnectionRuntimeEntry 35  }
   
   
   wlecConnectionRuntimeRequestCount OBJECT-TYPE
      SYNTAX      INTEGER
      MAX-ACCESS  read-only
      STATUS      current
      DESCRIPTION "The Request Count"
      ::= { wlecConnectionRuntimeEntry 40  }
   
   
   wlecConnectionRuntimePendingRequestCount OBJECT-TYPE
      SYNTAX      INTEGER
      MAX-ACCESS  read-only
      STATUS      current
      DESCRIPTION "The Pending Request Count"
      ::= { wlecConnectionRuntimeEntry 45  }
   
   
   wlecConnectionRuntimeErrorCount OBJECT-TYPE
      SYNTAX      INTEGER
      MAX-ACCESS  read-only
      STATUS      current
      DESCRIPTION "The Request Error Count"
      ::= { wlecConnectionRuntimeEntry 50  }
   
   
   wlecConnectionRuntimeInTransaction OBJECT-TYPE
      SYNTAX      INTEGER
                  {
                     true(1),
                     false(2)
                  }
      
      MAX-ACCESS  read-only
      STATUS      current
      DESCRIPTION "A boolean value (true Or false). Returns the Connection in Transaction indicator"
      ::= { wlecConnectionRuntimeEntry 55  }
   
   
   wlecConnectionServiceRuntimeTable OBJECT-TYPE
      SYNTAX      SEQUENCE OF WlecConnectionServiceRuntimeEntry
      MAX-ACCESS  not-accessible
      STATUS      current
      DESCRIPTION "This table describes the web server."
      ::= { wls 451  }
      
   
   wlecConnectionServiceRuntimeEntry OBJECT-TYPE
      SYNTAX      WlecConnectionServiceRuntimeEntry
      MAX-ACCESS  not-accessible
      STATUS      current
      DESCRIPTION "Entry of wlecConnectionServiceRuntimeTable"
      INDEX { wlecConnectionServiceRuntimeIndex}
      ::= { wlecConnectionServiceRuntimeTable 1 }
      
   WlecConnectionServiceRuntimeEntry ::=
      SEQUENCE
      {
         wlecConnectionServiceRuntimeIndex DisplayString (SIZE (1..16)),
         wlecConnectionServiceRuntimeObjectName DisplayString (SIZE (1..256)),
         wlecConnectionServiceRuntimeType DisplayString (SIZE (1..64)),
         wlecConnectionServiceRuntimeName DisplayString (SIZE (1..64)),
         wlecConnectionServiceRuntimeParent DisplayString (SIZE (1..256)),
         wlecConnectionServiceRuntimeConnectionPoolCount INTEGER
      }
      
   
   wlecConnectionServiceRuntimeIndex OBJECT-TYPE
      SYNTAX      DisplayString (SIZE (1..16))
      MAX-ACCESS  read-only
      STATUS      current
      DESCRIPTION "Unique value directed from ObjectName which is used as table index"
      ::= { wlecConnectionServiceRuntimeEntry 1  }
   
   
   wlecConnectionServiceRuntimeObjectName OBJECT-TYPE
      SYNTAX      DisplayString (SIZE (1..256))
      MAX-ACCESS  read-only
      STATUS      current
      DESCRIPTION "JMX-standard MBean name"
      ::= { wlecConnectionServiceRuntimeEntry 5  }
   
   
   wlecConnectionServiceRuntimeType OBJECT-TYPE
      SYNTAX      DisplayString (SIZE (1..64))
      MAX-ACCESS  read-only
      STATUS      current
      DESCRIPTION "BEA-proprietary MBean type"
      ::= { wlecConnectionServiceRuntimeEntry 10  }
   
   
   wlecConnectionServiceRuntimeName OBJECT-TYPE
      SYNTAX      DisplayString (SIZE (1..64))
      MAX-ACCESS  read-only
      STATUS      current
      DESCRIPTION "BEA-proprietary MBean name"
      ::= { wlecConnectionServiceRuntimeEntry 15  }
   
   
   wlecConnectionServiceRuntimeParent OBJECT-TYPE
      SYNTAX      DisplayString (SIZE (1..256))
      MAX-ACCESS  read-only
      STATUS      current
      DESCRIPTION "BEA-proprietary Parent object's identification, with syntax
      <type>:<name>"
      ::= { wlecConnectionServiceRuntimeEntry 20  }
   
   
   wlecConnectionServiceRuntimeConnectionPoolCount OBJECT-TYPE
      SYNTAX      INTEGER
      MAX-ACCESS  read-only
      STATUS      current
      DESCRIPTION "Return the pool count."
      ::= { wlecConnectionServiceRuntimeEntry 25  }
   
   
   connectorConnectionRuntimeTable OBJECT-TYPE
      SYNTAX      SEQUENCE OF ConnectorConnectionRuntimeEntry
      MAX-ACCESS  not-accessible
      STATUS      current
      DESCRIPTION "This table is used for monitoring individual WebLogic Connector connections."
      ::= { wls 454  }
      
   
   connectorConnectionRuntimeEntry OBJECT-TYPE
      SYNTAX      ConnectorConnectionRuntimeEntry
      MAX-ACCESS  not-accessible
      STATUS      current
      DESCRIPTION "Entry of connectorConnectionRuntimeTable"
      INDEX { connectorConnectionRuntimeIndex}
      ::= { connectorConnectionRuntimeTable 1 }
      
   ConnectorConnectionRuntimeEntry ::=
      SEQUENCE
      {
         connectorConnectionRuntimeIndex DisplayString (SIZE (1..16)),
         connectorConnectionRuntimeObjectName DisplayString (SIZE (1..256)),
         connectorConnectionRuntimeType DisplayString (SIZE (1..64)),
         connectorConnectionRuntimeName DisplayString (SIZE (1..64)),
         connectorConnectionRuntimeParent DisplayString (SIZE (1..256)),
         connectorConnectionRuntimeActiveHandlesCurrentCount INTEGER,
         connectorConnectionRuntimeActiveHandlesHighCount INTEGER,
         connectorConnectionRuntimeHandlesCreatedTotalCount INTEGER,
         connectorConnectionRuntimeCurrentlyInUse INTEGER
                     {
                        true(1),
                        false(2)
                     }
         ,
         connectorConnectionRuntimeInTransaction INTEGER
                     {
                        true(1),
                        false(2)
                     }
         ,
         connectorConnectionRuntimeShared INTEGER,
         connectorConnectionRuntimeEISProductVersion OCTET STRING,
         connectorConnectionRuntimeDeletable OCTET STRING,
         connectorConnectionRuntimeReserveDurationTime Counter64,
         connectorConnectionRuntimeTransactionId OCTET STRING,
         connectorConnectionRuntimeConnectionFactoryClassName OCTET STRING,
         connectorConnectionRuntimeEISProductName OCTET STRING,
         connectorConnectionRuntimeUserName OCTET STRING,
         connectorConnectionRuntimeReserveTime Counter64,
         connectorConnectionRuntimeCreationDurationTime Counter64,
         connectorConnectionRuntimeManagedConnectionFactoryClassName OCTET STRING,
         connectorConnectionRuntimeMaxConnections OCTET STRING
      }
      
   
   connectorConnectionRuntimeIndex OBJECT-TYPE
      SYNTAX      DisplayString (SIZE (1..16))
      MAX-ACCESS  read-only
      STATUS      current
      DESCRIPTION "Unique value directed from ObjectName which is used as table index"
      ::= { connectorConnectionRuntimeEntry 1  }
   
   
   connectorConnectionRuntimeObjectName OBJECT-TYPE
      SYNTAX      DisplayString (SIZE (1..256))
      MAX-ACCESS  read-only
      STATUS      current
      DESCRIPTION "JMX-standard MBean name"
      ::= { connectorConnectionRuntimeEntry 5  }
   
   
   connectorConnectionRuntimeType OBJECT-TYPE
      SYNTAX      DisplayString (SIZE (1..64))
      MAX-ACCESS  read-only
      STATUS      current
      DESCRIPTION "BEA-proprietary MBean type"
      ::= { connectorConnectionRuntimeEntry 10  }
   
   
   connectorConnectionRuntimeName OBJECT-TYPE
      SYNTAX      DisplayString (SIZE (1..64))
      MAX-ACCESS  read-only
      STATUS      current
      DESCRIPTION "BEA-proprietary MBean name"
      ::= { connectorConnectionRuntimeEntry 15  }
   
   
   connectorConnectionRuntimeParent OBJECT-TYPE
      SYNTAX      DisplayString (SIZE (1..256))
      MAX-ACCESS  read-only
      STATUS      current
      DESCRIPTION "BEA-proprietary Parent object's identification, with syntax
      <type>:<name>"
      ::= { connectorConnectionRuntimeEntry 20  }
   
   
   connectorConnectionRuntimeActiveHandlesCurrentCount OBJECT-TYPE
      SYNTAX      INTEGER
      MAX-ACCESS  read-only
      STATUS      current
      DESCRIPTION "The current total active connection handles for this connection."
      ::= { connectorConnectionRuntimeEntry 25  }
   
   
   connectorConnectionRuntimeActiveHandlesHighCount OBJECT-TYPE
      SYNTAX      INTEGER
      MAX-ACCESS  read-only
      STATUS      current
      DESCRIPTION "The high water mark of active connection handles for 
      this connection since the connection was created."
      ::= { connectorConnectionRuntimeEntry 30  }
   
   
   connectorConnectionRuntimeHandlesCreatedTotalCount OBJECT-TYPE
      SYNTAX      INTEGER
      MAX-ACCESS  read-only
      STATUS      current
      DESCRIPTION "The total number of connection handles created for this 
      connection since the connection was created."
      ::= { connectorConnectionRuntimeEntry 35  }
   
   
   connectorConnectionRuntimeCurrentlyInUse OBJECT-TYPE
      SYNTAX      INTEGER
                  {
                     true(1),
                     false(2)
                  }
      
      MAX-ACCESS  read-only
      STATUS      current
      DESCRIPTION "An indicator of whether or not the connection is currently in use."
      ::= { connectorConnectionRuntimeEntry 40  }
   
   
   connectorConnectionRuntimeInTransaction OBJECT-TYPE
      SYNTAX      INTEGER
                  {
                     true(1),
                     false(2)
                  }
      
      MAX-ACCESS  read-only
      STATUS      current
      DESCRIPTION "An indicator of whether or not the connection is currently in use in a transaction"
      ::= { connectorConnectionRuntimeEntry 45  }
   
   
   connectorConnectionRuntimeShared OBJECT-TYPE
      SYNTAX      INTEGER
      MAX-ACCESS  read-only
      STATUS      current
      DESCRIPTION "An indicator of whether or not the connection is 
      currently being shared by more than one invoker."
      ::= { connectorConnectionRuntimeEntry 50  }
   
   
   connectorConnectionRuntimeEISProductVersion OBJECT-TYPE
      SYNTAX      OCTET STRING
      MAX-ACCESS  read-only
      STATUS      current
      DESCRIPTION "Returns the EISProductVersion associated with the ManagedConnection's MetaData."
      ::= { connectorConnectionRuntimeEntry 51  }
   
   
   connectorConnectionRuntimeDeletable OBJECT-TYPE
      SYNTAX      OCTET STRING
      MAX-ACCESS  read-only
      STATUS      current
      DESCRIPTION "Indicates whether the connection can be closed manually through the console."
      ::= { connectorConnectionRuntimeEntry 52  }
   
   
   connectorConnectionRuntimeReserveDurationTime OBJECT-TYPE
      SYNTAX      Counter64
      MAX-ACCESS  read-only
      STATUS      current
      DESCRIPTION "Get the time taken to reserve this connection."
      ::= { connectorConnectionRuntimeEntry 53  }
   
   
   connectorConnectionRuntimeTransactionId OBJECT-TYPE
      SYNTAX      OCTET STRING
      MAX-ACCESS  read-only
      STATUS      current
      DESCRIPTION "Get the Transaction ID of the transaction that this connection is being used with."
      ::= { connectorConnectionRuntimeEntry 54  }
   
   
   connectorConnectionRuntimeConnectionFactoryClassName OBJECT-TYPE
      SYNTAX      OCTET STRING
      MAX-ACCESS  read-only
      STATUS      current
      DESCRIPTION "Returns the connection factory class name."
      ::= { connectorConnectionRuntimeEntry 55  }
   
   
   connectorConnectionRuntimeEISProductName OBJECT-TYPE
      SYNTAX      OCTET STRING
      MAX-ACCESS  read-only
      STATUS      current
      DESCRIPTION "Returns the EISProductName associated with the ManagedConnection's MetaData"
      ::= { connectorConnectionRuntimeEntry 56  }
   
   
   connectorConnectionRuntimeUserName OBJECT-TYPE
      SYNTAX      OCTET STRING
      MAX-ACCESS  read-only
      STATUS      current
      DESCRIPTION "Returns the UserName associated with the ManagedConnection's MetaData"
      ::= { connectorConnectionRuntimeEntry 57  }
   
   
   connectorConnectionRuntimeReserveTime OBJECT-TYPE
      SYNTAX      Counter64
      MAX-ACCESS  read-only
      STATUS      current
      DESCRIPTION "Return the last time the connection was reserved."
      ::= { connectorConnectionRuntimeEntry 58  }
   
   
   connectorConnectionRuntimeCreationDurationTime OBJECT-TYPE
      SYNTAX      Counter64
      MAX-ACCESS  read-only
      STATUS      current
      DESCRIPTION "Return the time taken to create the connection."
      ::= { connectorConnectionRuntimeEntry 59  }
   
   
   connectorConnectionRuntimeManagedConnectionFactoryClassName OBJECT-TYPE
      SYNTAX      OCTET STRING
      MAX-ACCESS  read-only
      STATUS      current
      DESCRIPTION "Returns the managed connection factory class name."
      ::= { connectorConnectionRuntimeEntry 60  }
   
   
   connectorConnectionRuntimeMaxConnections OBJECT-TYPE
      SYNTAX      OCTET STRING
      MAX-ACCESS  read-only
      STATUS      current
      DESCRIPTION "Returns the MaxConnections associated with the ManagedConnection's MetaData"
      ::= { connectorConnectionRuntimeEntry 61  }
   
   
   connectorConnectionPoolRuntimeTable OBJECT-TYPE
      SYNTAX      SEQUENCE OF ConnectorConnectionPoolRuntimeEntry
      MAX-ACCESS  not-accessible
      STATUS      current
      DESCRIPTION "This table is used for monitoring a WebLogic Connector Connection Pool"
      ::= { wls 455  }
      
   
   connectorConnectionPoolRuntimeEntry OBJECT-TYPE
      SYNTAX      ConnectorConnectionPoolRuntimeEntry
      MAX-ACCESS  not-accessible
      STATUS      current
      DESCRIPTION "Entry of connectorConnectionRuntimeTable"
      INDEX { connectorConnectionPoolRuntimeIndex}
      ::= { connectorConnectionPoolRuntimeTable 1 }
      
   ConnectorConnectionPoolRuntimeEntry ::=
      SEQUENCE
      {
         connectorConnectionPoolRuntimeIndex DisplayString (SIZE (1..16)),
         connectorConnectionPoolRuntimeObjectName DisplayString (SIZE (1..256)),
         connectorConnectionPoolRuntimeType DisplayString (SIZE (1..64)),
         connectorConnectionPoolRuntimeName DisplayString (SIZE (1..64)),
         connectorConnectionPoolRuntimeParent DisplayString (SIZE (1..256)),
         connectorConnectionPoolRuntimePoolName DisplayString (SIZE (1..256)),
         connectorConnectionPoolRuntimeJNDIName DisplayString (SIZE (1..64)),
         connectorConnectionPoolRuntimeConnectionFactoryName DisplayString (SIZE (1..256)),
         connectorConnectionPoolRuntimeResourceAdapterLinkRefName DisplayString (SIZE (1..256)),
         connectorConnectionPoolRuntimeLogFileName DisplayString (SIZE (1..256)),
         connectorConnectionPoolRuntimeTransactionSupport DisplayString (SIZE (1..256)),
         connectorConnectionPoolRuntimeConnections DisplayString (SIZE (1..256)),
         connectorConnectionPoolRuntimeLoggingEnabled INTEGER
                     {
                        true(1),
                        false(2)
                     }
         ,
         connectorConnectionPoolRuntimeMaxCapacity INTEGER,
         connectorConnectionPoolRuntimeInitialCapacity INTEGER,
         connectorConnectionPoolRuntimeCapacityIncrement INTEGER,
         connectorConnectionPoolRuntimeShrinkingEnabled INTEGER
                     {
                        true(1),
                        false(2)
                     }
         ,
         connectorConnectionPoolRuntimeShrinkPeriodMinutes INTEGER,
         connectorConnectionPoolRuntimeActiveConnectionsCurrentCount INTEGER,
         connectorConnectionPoolRuntimeActiveConnectionsHighCount INTEGER,
         connectorConnectionPoolRuntimeFreeConnectionsCurrentCount INTEGER,
         connectorConnectionPoolRuntimeFreeConnectionsHighCount INTEGER,
         connectorConnectionPoolRuntimeAverageActiveUsage INTEGER,
         connectorConnectionPoolRuntimeShrinkCountDownTime INTEGER,
         connectorConnectionPoolRuntimeRecycledTotal INTEGER,
         connectorConnectionPoolRuntimeConnectionsCreatedTotalCount INTEGER,
         connectorConnectionPoolRuntimeConnectionsMatchedTotalCount INTEGER,
         connectorConnectionPoolRuntimeConnectionsDestroyedTotalCount INTEGER,
         connectorConnectionPoolRuntimeConnectionsRejectedTotalCount INTEGER,
         connectorConnectionPoolRuntimeConnectionLeakProfileCount INTEGER,
         connectorConnectionPoolRuntimeNumberDetectedIdle INTEGER,
         connectorConnectionPoolRuntimeNumberDetectedLeaks INTEGER,
         connectorConnectionPoolRuntimeFreePoolSizeHighWaterMark Counter64,
         connectorConnectionPoolRuntimeKey OCTET STRING,
         connectorConnectionPoolRuntimeCurrentCapacity Counter64,
         connectorConnectionPoolRuntimeMCFClassName OCTET STRING,
         connectorConnectionPoolRuntimeTestable OCTET STRING,
         connectorConnectionPoolRuntimeNumUnavailableHighCount INTEGER,
         connectorConnectionPoolRuntimeConnectionsDestroyedByErrorTotalCount INTEGER,
         connectorConnectionPoolRuntimeNumWaiters Counter64,
         connectorConnectionPoolRuntimeConnectorEisType OCTET STRING,
         connectorConnectionPoolRuntimeNumWaitersCurrentCount INTEGER,
         connectorConnectionPoolRuntimeMaxIdleTime INTEGER,
         connectorConnectionPoolRuntimeLastShrinkTime Counter64,
         connectorConnectionPoolRuntimeState OCTET STRING,
         connectorConnectionPoolRuntimeResourceLink OCTET STRING,
         connectorConnectionPoolRuntimeCloseCount Counter64,
         connectorConnectionPoolRuntimeManagedConnectionFactoryClassName OCTET STRING,
         connectorConnectionPoolRuntimeHighestNumWaiters Counter64,
         connectorConnectionPoolRuntimePoolSizeHighWaterMark Counter64,
         connectorConnectionPoolRuntimeConnectionFactoryClassName OCTET STRING,
         connectorConnectionPoolRuntimeEISResourceId OCTET STRING,
         connectorConnectionPoolRuntimeFreePoolSizeLowWaterMark Counter64,
         connectorConnectionPoolRuntimePoolSizeLowWaterMark Counter64,
         connectorConnectionPoolRuntimeConnectionsDestroyedByShrinkingTotalCount INTEGER,
         connectorConnectionPoolRuntimeNumUnavailableCurrentCount INTEGER,
         connectorConnectionPoolRuntimeProxyOn OCTET STRING
      }
      
   
   connectorConnectionPoolRuntimeIndex OBJECT-TYPE
      SYNTAX      DisplayString (SIZE (1..16))
      MAX-ACCESS  read-only
      STATUS      current
      DESCRIPTION "Unique value directed from ObjectName which is used as table index"
      ::= { connectorConnectionPoolRuntimeEntry 1  }
   
   
   connectorConnectionPoolRuntimeObjectName OBJECT-TYPE
      SYNTAX      DisplayString (SIZE (1..256))
      MAX-ACCESS  read-only
      STATUS      current
      DESCRIPTION "JMX-standard MBean name"
      ::= { connectorConnectionPoolRuntimeEntry 5  }
   
   
   connectorConnectionPoolRuntimeType OBJECT-TYPE
      SYNTAX      DisplayString (SIZE (1..64))
      MAX-ACCESS  read-only
      STATUS      current
      DESCRIPTION "BEA-proprietary MBean type"
      ::= { connectorConnectionPoolRuntimeEntry 10  }
   
   
   connectorConnectionPoolRuntimeName OBJECT-TYPE
      SYNTAX      DisplayString (SIZE (1..64))
      MAX-ACCESS  read-only
      STATUS      current
      DESCRIPTION "BEA-proprietary MBean name"
      ::= { connectorConnectionPoolRuntimeEntry 15  }
   
   
   connectorConnectionPoolRuntimeParent OBJECT-TYPE
      SYNTAX      DisplayString (SIZE (1..256))
      MAX-ACCESS  read-only
      STATUS      current
      DESCRIPTION "BEA-proprietary Parent object's identification, with syntax
      <type>:<name>"
      ::= { connectorConnectionPoolRuntimeEntry 20  }
   
   
   connectorConnectionPoolRuntimePoolName OBJECT-TYPE
      SYNTAX      DisplayString (SIZE (1..256))
      MAX-ACCESS  read-only
      STATUS      current
      DESCRIPTION "The configured Logical Name for the Connection 
      Factory using this Connector connection pool."
      ::= { connectorConnectionPoolRuntimeEntry 25  }
   
   
   connectorConnectionPoolRuntimeJNDIName OBJECT-TYPE
      SYNTAX      DisplayString (SIZE (1..64))
      MAX-ACCESS  read-only
      STATUS      current
      DESCRIPTION "The configured JNDI Name for the Connection Factory using this Connector connection pool."
      ::= { connectorConnectionPoolRuntimeEntry 30  }
   
   
   connectorConnectionPoolRuntimeConnectionFactoryName OBJECT-TYPE
      SYNTAX      DisplayString (SIZE (1..256))
      MAX-ACCESS  read-only
      STATUS      current
      DESCRIPTION "The Resource Adapter Link Reference for cases where this Connection 
      Factory refers to an existing Resource Adapter deployment."
      ::= { connectorConnectionPoolRuntimeEntry 35  }
   
   
   connectorConnectionPoolRuntimeResourceAdapterLinkRefName OBJECT-TYPE
      SYNTAX      DisplayString (SIZE (1..256))
      MAX-ACCESS  read-only
      STATUS      current
      DESCRIPTION "The Resource Adapter Link Reference for cases where this Connection 
      Factory refers to an existing Resource Adapter deployment."
      ::= { connectorConnectionPoolRuntimeEntry 40  }
   
   
   connectorConnectionPoolRuntimeLogFileName OBJECT-TYPE
      SYNTAX      DisplayString (SIZE (1..256))
      MAX-ACCESS  read-only
      STATUS      current
      DESCRIPTION "The Log File used by the Resource Adapter for this Connector connection pool."
      ::= { connectorConnectionPoolRuntimeEntry 45  }
   
   
   connectorConnectionPoolRuntimeTransactionSupport OBJECT-TYPE
      SYNTAX      DisplayString (SIZE (1..256))
      MAX-ACCESS  read-only
      STATUS      current
      DESCRIPTION "The transaction support level for the Resource Adapter for this Connector connection pool."
      ::= { connectorConnectionPoolRuntimeEntry 50  }
   
   
   connectorConnectionPoolRuntimeConnections OBJECT-TYPE
      SYNTAX      DisplayString (SIZE (1..256))
      MAX-ACCESS  read-only
      STATUS      current
      DESCRIPTION "An array of ConnectorConnectionRuntimeMBeans that each 
      represents the statistics for a Connector Connection."
      ::= { connectorConnectionPoolRuntimeEntry 55  }
   
   
   connectorConnectionPoolRuntimeLoggingEnabled OBJECT-TYPE
      SYNTAX      INTEGER
                  {
                     true(1),
                     false(2)
                  }
      
      MAX-ACCESS  read-only
      STATUS      current
      DESCRIPTION "A boolean whether logging is enabled."
      ::= { connectorConnectionPoolRuntimeEntry 60  }
   
   
   connectorConnectionPoolRuntimeMaxCapacity OBJECT-TYPE
      SYNTAX      INTEGER
      MAX-ACCESS  read-only
      STATUS      current
      DESCRIPTION "The maximum capacity configured for this Connector connection pool."
      ::= { connectorConnectionPoolRuntimeEntry 65  }
   
   
   connectorConnectionPoolRuntimeInitialCapacity OBJECT-TYPE
      SYNTAX      INTEGER
      MAX-ACCESS  read-only
      STATUS      current
      DESCRIPTION "The initial capacity configured for this Connector connection pool."
      ::= { connectorConnectionPoolRuntimeEntry 70  }
   
   
   connectorConnectionPoolRuntimeCapacityIncrement OBJECT-TYPE
      SYNTAX      INTEGER
      MAX-ACCESS  read-only
      STATUS      current
      DESCRIPTION "The capacity increment."
      ::= { connectorConnectionPoolRuntimeEntry 75  }
   
   
   connectorConnectionPoolRuntimeShrinkingEnabled OBJECT-TYPE
      SYNTAX      INTEGER
                  {
                     true(1),
                     false(2)
                  }
      
      MAX-ACCESS  read-only
      STATUS      current
      DESCRIPTION "Is shrinking of this Connector connection pool enabled."
      ::= { connectorConnectionPoolRuntimeEntry 80  }
   
   
   connectorConnectionPoolRuntimeShrinkPeriodMinutes OBJECT-TYPE
      SYNTAX      INTEGER
      MAX-ACCESS  read-only
      STATUS      current
      DESCRIPTION "The Shrink Period (in minutes) of this Connector connection pool."
      ::= { connectorConnectionPoolRuntimeEntry 85  }
   
   
   connectorConnectionPoolRuntimeActiveConnectionsCurrentCount OBJECT-TYPE
      SYNTAX      INTEGER
      MAX-ACCESS  read-only
      STATUS      current
      DESCRIPTION "The current total active connections."
      ::= { connectorConnectionPoolRuntimeEntry 90  }
   
   
   connectorConnectionPoolRuntimeActiveConnectionsHighCount OBJECT-TYPE
      SYNTAX      INTEGER
      MAX-ACCESS  read-only
      STATUS      current
      DESCRIPTION "The high water mark of active connections in this 
      Connector Pool since the pool was instantiated."
      ::= { connectorConnectionPoolRuntimeEntry 95  }
   
   
   connectorConnectionPoolRuntimeFreeConnectionsCurrentCount OBJECT-TYPE
      SYNTAX      INTEGER
      MAX-ACCESS  read-only
      STATUS      current
      DESCRIPTION "The current total free connections."
      ::= { connectorConnectionPoolRuntimeEntry 100  }
   
   
   connectorConnectionPoolRuntimeFreeConnectionsHighCount OBJECT-TYPE
      SYNTAX      INTEGER
      MAX-ACCESS  read-only
      STATUS      current
      DESCRIPTION "The high water mark of free connections in this 
      Connector Pool since the pool was instantiated."
      ::= { connectorConnectionPoolRuntimeEntry 105  }
   
   
   connectorConnectionPoolRuntimeAverageActiveUsage OBJECT-TYPE
      SYNTAX      INTEGER
      MAX-ACCESS  read-only
      STATUS      current
      DESCRIPTION "The running average usage of created connections 
      that are active in the Connector Pool since the pool was last shrunk."
      ::= { connectorConnectionPoolRuntimeEntry 110  }
   
   
   connectorConnectionPoolRuntimeShrinkCountDownTime OBJECT-TYPE
      SYNTAX      INTEGER
      MAX-ACCESS  read-only
      STATUS      current
      DESCRIPTION "The amount of time left (in minutes) until an attempt to shrink the pool will be made."
      ::= { connectorConnectionPoolRuntimeEntry 115  }
   
   
   connectorConnectionPoolRuntimeRecycledTotal OBJECT-TYPE
      SYNTAX      INTEGER
      MAX-ACCESS  read-only
      STATUS      current
      DESCRIPTION "The total number of Connector connections created in this 
      Connector Pool since the pool is instantiated."
      ::= { connectorConnectionPoolRuntimeEntry 120  }
   
   
   connectorConnectionPoolRuntimeConnectionsCreatedTotalCount OBJECT-TYPE
      SYNTAX      INTEGER
      MAX-ACCESS  read-only
      STATUS      current
      DESCRIPTION "The total number of Connector connections created in this 
      Connector Pool since the pool is instantiated."
      ::= { connectorConnectionPoolRuntimeEntry 125  }
   
   
   connectorConnectionPoolRuntimeConnectionsMatchedTotalCount OBJECT-TYPE
      SYNTAX      INTEGER
      MAX-ACCESS  read-only
      STATUS      current
      DESCRIPTION "The total number of times a request for a Connector connections 
      was satisfied via the use of an existing created connection since the 
      pool is instantiated."
      ::= { connectorConnectionPoolRuntimeEntry 130  }
   
   
   connectorConnectionPoolRuntimeConnectionsDestroyedTotalCount OBJECT-TYPE
      SYNTAX      INTEGER
      MAX-ACCESS  read-only
      STATUS      current
      DESCRIPTION "The total number of Connector connections destroyed in this 
      Connector Pool since the pool is instantiated."
      ::= { connectorConnectionPoolRuntimeEntry 135  }
   
   
   connectorConnectionPoolRuntimeConnectionsRejectedTotalCount OBJECT-TYPE
      SYNTAX      INTEGER
      MAX-ACCESS  read-only
      STATUS      current
      DESCRIPTION "An array of ConnectorConnectionRuntimeMBeans that each 
      represents the statistics for a Connector Connection."
      ::= { connectorConnectionPoolRuntimeEntry 140  }
   
   
   connectorConnectionPoolRuntimeConnectionLeakProfileCount OBJECT-TYPE
      SYNTAX      INTEGER
      MAX-ACCESS  read-only
      STATUS      current
      DESCRIPTION "Returns the number of Leak connection profiles stored for this pool."
      ::= { connectorConnectionPoolRuntimeEntry 141  }
   
   
   connectorConnectionPoolRuntimeNumberDetectedIdle OBJECT-TYPE
      SYNTAX      INTEGER
      MAX-ACCESS  read-only
      STATUS      current
      DESCRIPTION "Returns the total number of idle connections detected in the lifetime of this Pool."
      ::= { connectorConnectionPoolRuntimeEntry 143  }
   
   
   connectorConnectionPoolRuntimeNumberDetectedLeaks OBJECT-TYPE
      SYNTAX      INTEGER
      MAX-ACCESS  read-only
      STATUS      current
      DESCRIPTION "Returns the total number of leaked connections detected in the lifetime of this Pool."
      ::= { connectorConnectionPoolRuntimeEntry 144  }
   
   
   connectorConnectionPoolRuntimeFreePoolSizeHighWaterMark OBJECT-TYPE
      SYNTAX      Counter64
      MAX-ACCESS  read-only
      STATUS      current
      DESCRIPTION "The FreePoolSizeHighWaterMark of this Connector connection pool."
      ::= { connectorConnectionPoolRuntimeEntry 145  }
   
   
   connectorConnectionPoolRuntimeKey OBJECT-TYPE
      SYNTAX      OCTET STRING
      MAX-ACCESS  read-only
      STATUS      current
      DESCRIPTION "The configured Key for the Connection Factory using this Connector connection pool."
      ::= { connectorConnectionPoolRuntimeEntry 146  }
   
   
   connectorConnectionPoolRuntimeCurrentCapacity OBJECT-TYPE
      SYNTAX      Counter64
      MAX-ACCESS  read-only
      STATUS      current
      DESCRIPTION "The PoolSize of this Connector connection pool."
      ::= { connectorConnectionPoolRuntimeEntry 147  }
   
   
   connectorConnectionPoolRuntimeMCFClassName OBJECT-TYPE
      SYNTAX      OCTET STRING
      MAX-ACCESS  read-only
      STATUS      current
      DESCRIPTION "Get the MCF class name."
      ::= { connectorConnectionPoolRuntimeEntry 148  }
   
   
   connectorConnectionPoolRuntimeTestable OBJECT-TYPE
      SYNTAX      OCTET STRING
      MAX-ACCESS  read-only
      STATUS      current
      DESCRIPTION "This indicates whether the connection pool is testable or not."
      ::= { connectorConnectionPoolRuntimeEntry 149  }
   
   
   connectorConnectionPoolRuntimeNumUnavailableHighCount OBJECT-TYPE
      SYNTAX      INTEGER
      MAX-ACCESS  read-only
      STATUS      current
      DESCRIPTION "Return the highest unavailable number of connections at any given time."
      ::= { connectorConnectionPoolRuntimeEntry 150  }
   
   
   connectorConnectionPoolRuntimeConnectionsDestroyedByErrorTotalCount OBJECT-TYPE
      SYNTAX      INTEGER
      MAX-ACCESS  read-only
      STATUS      current
      DESCRIPTION "Return the number of connections that were destroyed because an error event was recieved."
      ::= { connectorConnectionPoolRuntimeEntry 151  }
   
   
   connectorConnectionPoolRuntimeNumWaiters OBJECT-TYPE
      SYNTAX      Counter64
      MAX-ACCESS  read-only
      STATUS      current
      DESCRIPTION "Gets the current number of waiters."
      ::= { connectorConnectionPoolRuntimeEntry 152  }
   
   
   connectorConnectionPoolRuntimeConnectorEisType OBJECT-TYPE
      SYNTAX      OCTET STRING
      MAX-ACCESS  read-only
      STATUS      current
      DESCRIPTION "The EIS type of this Connector connection pool."
      ::= { connectorConnectionPoolRuntimeEntry 153  }
   
   
   connectorConnectionPoolRuntimeNumWaitersCurrentCount OBJECT-TYPE
      SYNTAX      INTEGER
      MAX-ACCESS  read-only
      STATUS      current
      DESCRIPTION "Return the number of waiters."
      ::= { connectorConnectionPoolRuntimeEntry 154  }
   
   
   connectorConnectionPoolRuntimeMaxIdleTime OBJECT-TYPE
      SYNTAX      INTEGER
      MAX-ACCESS  read-only
      STATUS      current
      DESCRIPTION "The configured MaxIdle time for this pool"
      ::= { connectorConnectionPoolRuntimeEntry 155  }
   
   
   connectorConnectionPoolRuntimeLastShrinkTime OBJECT-TYPE
      SYNTAX      Counter64
      MAX-ACCESS  read-only
      STATUS      current
      DESCRIPTION "Return the last time that the pool was shrunk."
      ::= { connectorConnectionPoolRuntimeEntry 156  }
   
   
   connectorConnectionPoolRuntimeState OBJECT-TYPE
      SYNTAX      OCTET STRING
      MAX-ACCESS  read-only
      STATUS      current
      DESCRIPTION "Get the state of the pool."
      ::= { connectorConnectionPoolRuntimeEntry 157  }
   
   
   connectorConnectionPoolRuntimeResourceLink OBJECT-TYPE
      SYNTAX      OCTET STRING
      MAX-ACCESS  read-only
      STATUS      current
      DESCRIPTION "Get the resource link."
      ::= { connectorConnectionPoolRuntimeEntry 158  }
   
   
   connectorConnectionPoolRuntimeCloseCount OBJECT-TYPE
      SYNTAX      Counter64
      MAX-ACCESS  read-only
      STATUS      current
      DESCRIPTION "The number of connections that were closed for the connection pool."
      ::= { connectorConnectionPoolRuntimeEntry 159  }
   
   
   connectorConnectionPoolRuntimeManagedConnectionFactoryClassName OBJECT-TYPE
      SYNTAX      OCTET STRING
      MAX-ACCESS  read-only
      STATUS      current
      DESCRIPTION "The ManagedConnectionFactoryName of this Connector connection pool."
      ::= { connectorConnectionPoolRuntimeEntry 160  }
   
   
   connectorConnectionPoolRuntimeHighestNumWaiters OBJECT-TYPE
      SYNTAX      Counter64
      MAX-ACCESS  read-only
      STATUS      current
      DESCRIPTION "Gets the highest number of waiters."
      ::= { connectorConnectionPoolRuntimeEntry 161  }
   
   
   connectorConnectionPoolRuntimePoolSizeHighWaterMark OBJECT-TYPE
      SYNTAX      Counter64
      MAX-ACCESS  read-only
      STATUS      current
      DESCRIPTION "The PoolSizeHighWaterMark of this Connector connection pool."
      ::= { connectorConnectionPoolRuntimeEntry 162  }
   
   
   connectorConnectionPoolRuntimeConnectionFactoryClassName OBJECT-TYPE
      SYNTAX      OCTET STRING
      MAX-ACCESS  read-only
      STATUS      current
      DESCRIPTION "The ConnectionFactoryName of this Connector connection pool."
      ::= { connectorConnectionPoolRuntimeEntry 163  }
   
   
   connectorConnectionPoolRuntimeEISResourceId OBJECT-TYPE
      SYNTAX      OCTET STRING
      MAX-ACCESS  read-only
      STATUS      current
      DESCRIPTION "The EISResourceId of this Connector connection pool."
      ::= { connectorConnectionPoolRuntimeEntry 164  }
   
   
   connectorConnectionPoolRuntimeFreePoolSizeLowWaterMark OBJECT-TYPE
      SYNTAX      Counter64
      MAX-ACCESS  read-only
      STATUS      current
      DESCRIPTION "The FreePoolSizeLowWaterMark of this Connector connection pool."
      ::= { connectorConnectionPoolRuntimeEntry 165  }
   
   
   connectorConnectionPoolRuntimePoolSizeLowWaterMark OBJECT-TYPE
      SYNTAX      Counter64
      MAX-ACCESS  read-only
      STATUS      current
      DESCRIPTION "The PoolSizeLowWaterMark of this Connector connection pool."
      ::= { connectorConnectionPoolRuntimeEntry 166  }
   
   
   connectorConnectionPoolRuntimeConnectionsDestroyedByShrinkingTotalCount OBJECT-TYPE
      SYNTAX      INTEGER
      MAX-ACCESS  read-only
      STATUS      current
      DESCRIPTION "Return the number of connections that were destroyed as a result of shrinking."
      ::= { connectorConnectionPoolRuntimeEntry 167  }
   
   
   connectorConnectionPoolRuntimeNumUnavailableCurrentCount OBJECT-TYPE
      SYNTAX      INTEGER
      MAX-ACCESS  read-only
      STATUS      current
      DESCRIPTION "Return the number of unavailable connections."
      ::= { connectorConnectionPoolRuntimeEntry 168  }
   
   
   connectorConnectionPoolRuntimeProxyOn OBJECT-TYPE
      SYNTAX      OCTET STRING
      MAX-ACCESS  read-only
      STATUS      current
      DESCRIPTION "Return a flag indicating if the proxy is on. Returns true if it is."
      ::= { connectorConnectionPoolRuntimeEntry 169  }
   
   
   connectorServiceRuntimeTable OBJECT-TYPE
      SYNTAX      SEQUENCE OF ConnectorServiceRuntimeEntry
      MAX-ACCESS  not-accessible
      STATUS      current
      DESCRIPTION "This table is used for monitoring the WebLogic Connector Service."
      ::= { wls 456  }
      
   
   connectorServiceRuntimeEntry OBJECT-TYPE
      SYNTAX      ConnectorServiceRuntimeEntry
      MAX-ACCESS  not-accessible
      STATUS      current
      DESCRIPTION "Entry of connectorServiceRuntimeTable"
      INDEX { connectorServiceRuntimeIndex}
      ::= { connectorServiceRuntimeTable 1 }
      
   ConnectorServiceRuntimeEntry ::=
      SEQUENCE
      {
         connectorServiceRuntimeIndex DisplayString (SIZE (1..16)),
         connectorServiceRuntimeObjectName DisplayString (SIZE (1..256)),
         connectorServiceRuntimeType DisplayString (SIZE (1..64)),
         connectorServiceRuntimeName DisplayString (SIZE (1..64)),
         connectorServiceRuntimeParent DisplayString (SIZE (1..256)),
         connectorServiceRuntimeConnectionPoolCurrentCount INTEGER,
         connectorServiceRuntimeConnectionPoolsTotalCount INTEGER,
         connectorServiceRuntimeRACount INTEGER,
         connectorServiceRuntimeActiveRACount INTEGER
      }
      
   
   connectorServiceRuntimeIndex OBJECT-TYPE
      SYNTAX      DisplayString (SIZE (1..16))
      MAX-ACCESS  read-only
      STATUS      current
      DESCRIPTION "Unique value directed from ObjectName which is used as table index"
      ::= { connectorServiceRuntimeEntry 1  }
   
   
   connectorServiceRuntimeObjectName OBJECT-TYPE
      SYNTAX      DisplayString (SIZE (1..256))
      MAX-ACCESS  read-only
      STATUS      current
      DESCRIPTION "JMX-standard MBean name"
      ::= { connectorServiceRuntimeEntry 5  }
   
   
   connectorServiceRuntimeType OBJECT-TYPE
      SYNTAX      DisplayString (SIZE (1..64))
      MAX-ACCESS  read-only
      STATUS      current
      DESCRIPTION "BEA-proprietary MBean type"
      ::= { connectorServiceRuntimeEntry 10  }
   
   
   connectorServiceRuntimeName OBJECT-TYPE
      SYNTAX      DisplayString (SIZE (1..64))
      MAX-ACCESS  read-only
      STATUS      current
      DESCRIPTION "BEA-proprietary MBean name"
      ::= { connectorServiceRuntimeEntry 15  }
   
   
   connectorServiceRuntimeParent OBJECT-TYPE
      SYNTAX      DisplayString (SIZE (1..256))
      MAX-ACCESS  read-only
      STATUS      current
      DESCRIPTION "BEA-proprietary Parent object's identification, with syntax
      <type>:<name>"
      ::= { connectorServiceRuntimeEntry 20  }
   
   
   connectorServiceRuntimeConnectionPoolCurrentCount OBJECT-TYPE
      SYNTAX      INTEGER
      MAX-ACCESS  read-only
      STATUS      current
      DESCRIPTION "The number of currently deployed connection pools."
      ::= { connectorServiceRuntimeEntry 25  }
   
   
   connectorServiceRuntimeConnectionPoolsTotalCount OBJECT-TYPE
      SYNTAX      INTEGER
      MAX-ACCESS  read-only
      STATUS      current
      DESCRIPTION "The total number of deployed connection pools instantiated since the Server startup."
      ::= { connectorServiceRuntimeEntry 30  }
   
   
   connectorServiceRuntimeRACount OBJECT-TYPE
      SYNTAX      INTEGER
      MAX-ACCESS  read-only
      STATUS      current
      DESCRIPTION "Returns the number of resource adapters that have been deployed in the server. This count includes active RAs and Non-active RAs ( in the case of versioned RAs that are being replced by a new version )"
      ::= { connectorServiceRuntimeEntry 31  }
   
   
   connectorServiceRuntimeActiveRACount OBJECT-TYPE
      SYNTAX      INTEGER
      MAX-ACCESS  read-only
      STATUS      current
      DESCRIPTION "Returns the number of resource adapters that are active."
      ::= { connectorServiceRuntimeEntry 32  }
   
   
   connectorComponentRuntimeTable OBJECT-TYPE
      SYNTAX      SEQUENCE OF ConnectorComponentRuntimeEntry
      MAX-ACCESS  not-accessible
      STATUS      current
      DESCRIPTION "This table is used for monitoring the WebLogic Connector Component."
      ::= { wls 457  }
      
   
   connectorComponentRuntimeEntry OBJECT-TYPE
      SYNTAX      ConnectorComponentRuntimeEntry
      MAX-ACCESS  not-accessible
      STATUS      current
      DESCRIPTION "Entry of connectorComponentRuntimeTable"
      INDEX { connectorComponentRuntimeIndex}
      ::= { connectorComponentRuntimeTable 1 }
      
   ConnectorComponentRuntimeEntry ::=
      SEQUENCE
      {
         connectorComponentRuntimeIndex DisplayString (SIZE (1..16)),
         connectorComponentRuntimeObjectName DisplayString (SIZE (1..256)),
         connectorComponentRuntimeType DisplayString (SIZE (1..64)),
         connectorComponentRuntimeName DisplayString (SIZE (1..64)),
         connectorComponentRuntimeParent DisplayString (SIZE (1..256)),
         connectorComponentRuntimeConnectionPoolCount INTEGER,
         connectorComponentRuntimeInboundConnectionsCount INTEGER,
         connectorComponentRuntimeEISResourceId DisplayString (SIZE (1..64)),
         connectorComponentRuntimeVersionId DisplayString (SIZE (1..64)),
         connectorComponentRuntimeActiveVersionId DisplayString (SIZE (1..64)),
         connectorComponentRuntimeVersioned INTEGER
                     {
                        true(1),
                        false(2)
                     }
         ,
         connectorComponentRuntimeActiveVersion INTEGER,
         connectorComponentRuntimeJndiName DisplayString (SIZE (1..64)),
         connectorComponentRuntimeState DisplayString (SIZE (1..64)),
         connectorComponentRuntimeSuspendedState INTEGER,
         connectorComponentRuntimeDescription DisplayString (SIZE (1..64)),
         connectorComponentRuntimeEISType DisplayString (SIZE (1..64)),
         connectorComponentRuntimeSpecVersion DisplayString (SIZE (1..64)),
         connectorComponentRuntimeVendorName DisplayString (SIZE (1..64)),
         connectorComponentRuntimeVersion DisplayString (SIZE (1..32)),
         connectorComponentRuntimeComponentName OCTET STRING,
         connectorComponentRuntimeModuleId OCTET STRING,
         connectorComponentRuntimeConfiguration OCTET STRING,
         connectorComponentRuntimeSchema OCTET STRING,
         connectorComponentRuntimeLinkref OCTET STRING,
         connectorComponentRuntimeDeploymentState INTEGER,
         connectorComponentRuntimeConfigurationVersion OCTET STRING
      }
      
   
   connectorComponentRuntimeIndex OBJECT-TYPE
      SYNTAX      DisplayString (SIZE (1..16))
      MAX-ACCESS  read-only
      STATUS      current
      DESCRIPTION "Unique value directed from ObjectName which is used as table index"
      ::= { connectorComponentRuntimeEntry 1  }
   
   
   connectorComponentRuntimeObjectName OBJECT-TYPE
      SYNTAX      DisplayString (SIZE (1..256))
      MAX-ACCESS  read-only
      STATUS      current
      DESCRIPTION "JMX-standard MBean name"
      ::= { connectorComponentRuntimeEntry 5  }
   
   
   connectorComponentRuntimeType OBJECT-TYPE
      SYNTAX      DisplayString (SIZE (1..64))
      MAX-ACCESS  read-only
      STATUS      current
      DESCRIPTION "BEA-proprietary MBean type"
      ::= { connectorComponentRuntimeEntry 10  }
   
   
   connectorComponentRuntimeName OBJECT-TYPE
      SYNTAX      DisplayString (SIZE (1..64))
      MAX-ACCESS  read-only
      STATUS      current
      DESCRIPTION "BEA-proprietary MBean name"
      ::= { connectorComponentRuntimeEntry 15  }
   
   
   connectorComponentRuntimeParent OBJECT-TYPE
      SYNTAX      DisplayString (SIZE (1..256))
      MAX-ACCESS  read-only
      STATUS      current
      DESCRIPTION "BEA-proprietary Parent object's identification, with syntax
      <type>:<name>"
      ::= { connectorComponentRuntimeEntry 20  }
   
   
   connectorComponentRuntimeConnectionPoolCount OBJECT-TYPE
      SYNTAX      INTEGER
      MAX-ACCESS  read-only
      STATUS      current
      DESCRIPTION "The number of connection pools."
      ::= { connectorComponentRuntimeEntry 25  }
   
   
   connectorComponentRuntimeInboundConnectionsCount OBJECT-TYPE
      SYNTAX      INTEGER
      MAX-ACCESS  read-only
      STATUS      current
      DESCRIPTION "The number of inbound connections for the resource adapter."
      ::= { connectorComponentRuntimeEntry 30  }
   
   
   connectorComponentRuntimeEISResourceId OBJECT-TYPE
      SYNTAX      DisplayString (SIZE (1..64))
      MAX-ACCESS  read-only
      STATUS      current
      DESCRIPTION "EISResourceId for the component."
      ::= { connectorComponentRuntimeEntry 35  }
   
   
   connectorComponentRuntimeVersionId OBJECT-TYPE
      SYNTAX      DisplayString (SIZE (1..64))
      MAX-ACCESS  read-only
      STATUS      current
      DESCRIPTION "Deployment Version ID."
      ::= { connectorComponentRuntimeEntry 40  }
   
   
   connectorComponentRuntimeActiveVersionId OBJECT-TYPE
      SYNTAX      DisplayString (SIZE (1..64))
      MAX-ACCESS  read-only
      STATUS      current
      DESCRIPTION "Deployment Active Version ID."
      ::= { connectorComponentRuntimeEntry 45  }
   
   
   connectorComponentRuntimeVersioned OBJECT-TYPE
      SYNTAX      INTEGER
                  {
                     true(1),
                     false(2)
                  }
      
      MAX-ACCESS  read-only
      STATUS      current
      DESCRIPTION "Returns true if this Resource Adapter is versioned."
      ::= { connectorComponentRuntimeEntry 50  }
   
   
   connectorComponentRuntimeActiveVersion OBJECT-TYPE
      SYNTAX      INTEGER
      MAX-ACCESS  read-only
      STATUS      current
      DESCRIPTION "Returns true if this is the active version."
      ::= { connectorComponentRuntimeEntry 55  }
   
   
   connectorComponentRuntimeJndiName OBJECT-TYPE
      SYNTAX      DisplayString (SIZE (1..64))
      MAX-ACCESS  read-only
      STATUS      current
      DESCRIPTION "Jndi name of the resource adapter."
      ::= { connectorComponentRuntimeEntry 60  }
   
   
   connectorComponentRuntimeState OBJECT-TYPE
      SYNTAX      DisplayString (SIZE (1..64))
      MAX-ACCESS  read-only
      STATUS      current
      DESCRIPTION "Deployment state of the resource adapter."
      ::= { connectorComponentRuntimeEntry 65  }
   
   
   connectorComponentRuntimeSuspendedState OBJECT-TYPE
      SYNTAX      INTEGER
      MAX-ACCESS  read-only
      STATUS      current
      DESCRIPTION "suspended state information of the resource adapter.."
      ::= { connectorComponentRuntimeEntry 70  }
   
   
   connectorComponentRuntimeDescription OBJECT-TYPE
      SYNTAX      DisplayString (SIZE (1..64))
      MAX-ACCESS  read-only
      STATUS      current
      DESCRIPTION "Description for the resource adapter"
      ::= { connectorComponentRuntimeEntry 75  }
   
   
   connectorComponentRuntimeEISType OBJECT-TYPE
      SYNTAX      DisplayString (SIZE (1..64))
      MAX-ACCESS  read-only
      STATUS      current
      DESCRIPTION "EIS type"
      ::= { connectorComponentRuntimeEntry 80  }
   
   
   connectorComponentRuntimeSpecVersion OBJECT-TYPE
      SYNTAX      DisplayString (SIZE (1..64))
      MAX-ACCESS  read-only
      STATUS      current
      DESCRIPTION "Supported specification version."
      ::= { connectorComponentRuntimeEntry 85  }
   
   
   connectorComponentRuntimeVendorName OBJECT-TYPE
      SYNTAX      DisplayString (SIZE (1..64))
      MAX-ACCESS  read-only
      STATUS      current
      DESCRIPTION "Resource Adapter Vendor Name."
      ::= { connectorComponentRuntimeEntry 90  }
   
   
   connectorComponentRuntimeVersion OBJECT-TYPE
      SYNTAX      DisplayString (SIZE (1..32))
      MAX-ACCESS  read-only
      STATUS      current
      DESCRIPTION "Resource Adapter Version."
      ::= { connectorComponentRuntimeEntry 95  }
   
   
   connectorComponentRuntimeComponentName OBJECT-TYPE
      SYNTAX      OCTET STRING
      MAX-ACCESS  read-only
      STATUS      current
      DESCRIPTION "Get the name of the connector component."
      ::= { connectorComponentRuntimeEntry 96  }
   
   
   connectorComponentRuntimeModuleId OBJECT-TYPE
      SYNTAX      OCTET STRING
      MAX-ACCESS  read-only
      STATUS      current
      DESCRIPTION "Returns the identifier for this Component.  The identifier is unique within the application.  Typical modules will use the URI for their id.  Web Modules will return their context-root since the web-uri may not be unique within an EAR."
      ::= { connectorComponentRuntimeEntry 97  }
   
   
   connectorComponentRuntimeConfiguration OBJECT-TYPE
      SYNTAX      OCTET STRING
      MAX-ACCESS  read-only
      STATUS      current
      DESCRIPTION "Return the xml string representing the RA configuration. The xml corresponding to the latest schema is returned. The current supported version is '1.0'"
      ::= { connectorComponentRuntimeEntry 98  }
   
   
   connectorComponentRuntimeSchema OBJECT-TYPE
      SYNTAX      OCTET STRING
      MAX-ACCESS  read-only
      STATUS      current
      DESCRIPTION "Get the latest schema for RA configuration."
      ::= { connectorComponentRuntimeEntry 99  }
   
   
   connectorComponentRuntimeLinkref OBJECT-TYPE
      SYNTAX      OCTET STRING
      MAX-ACCESS  read-only
      STATUS      current
      DESCRIPTION "Get the linkref."
      ::= { connectorComponentRuntimeEntry 100  }
   
   
   connectorComponentRuntimeDeploymentState OBJECT-TYPE
      SYNTAX      INTEGER
      MAX-ACCESS  read-only
      STATUS      current
      DESCRIPTION "The current deployment state of the module."
      ::= { connectorComponentRuntimeEntry 101  }
   
   
   connectorComponentRuntimeConfigurationVersion OBJECT-TYPE
      SYNTAX      OCTET STRING
      MAX-ACCESS  read-only
      STATUS      current
      DESCRIPTION "Return the latest configuration version."
      ::= { connectorComponentRuntimeEntry 102  }
   
   
   connectorInboundRuntimeTable OBJECT-TYPE
      SYNTAX      SEQUENCE OF ConnectorInboundRuntimeEntry
      MAX-ACCESS  not-accessible
      STATUS      current
      DESCRIPTION "This table is used for monitoring the WebLogic Connector Component Inbound Connections."
      ::= { wls 459  }
      
   
   connectorInboundRuntimeEntry OBJECT-TYPE
      SYNTAX      ConnectorInboundRuntimeEntry
      MAX-ACCESS  not-accessible
      STATUS      current
      DESCRIPTION "Entry of connectorInboundRuntimeTable"
      INDEX { connectorInboundRuntimeIndex}
      ::= { connectorInboundRuntimeTable 1 }
      
   ConnectorInboundRuntimeEntry ::=
      SEQUENCE
      {
         connectorInboundRuntimeIndex DisplayString (SIZE (1..16)),
         connectorInboundRuntimeObjectName DisplayString (SIZE (1..256)),
         connectorInboundRuntimeType DisplayString (SIZE (1..64)),
         connectorInboundRuntimeName DisplayString (SIZE (1..64)),
         connectorInboundRuntimeParent DisplayString (SIZE (1..256)),
         connectorInboundRuntimeMsgListenerType DisplayString (SIZE (1..64)),
         connectorInboundRuntimeActivationSpecClass DisplayString (SIZE (1..64)),
         connectorInboundRuntimeState DisplayString (SIZE (1..64))
      }
      
   
   connectorInboundRuntimeIndex OBJECT-TYPE
      SYNTAX      DisplayString (SIZE (1..16))
      MAX-ACCESS  read-only
      STATUS      current
      DESCRIPTION "Unique value directed from ObjectName which is used as table index"
      ::= { connectorInboundRuntimeEntry 1  }
   
   
   connectorInboundRuntimeObjectName OBJECT-TYPE
      SYNTAX      DisplayString (SIZE (1..256))
      MAX-ACCESS  read-only
      STATUS      current
      DESCRIPTION "JMX-standard MBean name"
      ::= { connectorInboundRuntimeEntry 5  }
   
   
   connectorInboundRuntimeType OBJECT-TYPE
      SYNTAX      DisplayString (SIZE (1..64))
      MAX-ACCESS  read-only
      STATUS      current
      DESCRIPTION "BEA-proprietary MBean type"
      ::= { connectorInboundRuntimeEntry 10  }
   
   
   connectorInboundRuntimeName OBJECT-TYPE
      SYNTAX      DisplayString (SIZE (1..64))
      MAX-ACCESS  read-only
      STATUS      current
      DESCRIPTION "BEA-proprietary MBean name"
      ::= { connectorInboundRuntimeEntry 15  }
   
   
   connectorInboundRuntimeParent OBJECT-TYPE
      SYNTAX      DisplayString (SIZE (1..256))
      MAX-ACCESS  read-only
      STATUS      current
      DESCRIPTION "BEA-proprietary Parent object's identification, with syntax
      <type>:<name>"
      ::= { connectorInboundRuntimeEntry 20  }
   
   
   connectorInboundRuntimeMsgListenerType OBJECT-TYPE
      SYNTAX      DisplayString (SIZE (1..64))
      MAX-ACCESS  read-only
      STATUS      current
      DESCRIPTION "Message Listener type."
      ::= { connectorInboundRuntimeEntry 25  }
   
   
   connectorInboundRuntimeActivationSpecClass OBJECT-TYPE
      SYNTAX      DisplayString (SIZE (1..64))
      MAX-ACCESS  read-only
      STATUS      current
      DESCRIPTION "Activation specification class."
      ::= { connectorInboundRuntimeEntry 30  }
   
   
   connectorInboundRuntimeState OBJECT-TYPE
      SYNTAX      DisplayString (SIZE (1..64))
      MAX-ACCESS  read-only
      STATUS      current
      DESCRIPTION "Current state of this inbound connector, either running or suspended."
      ::= { connectorInboundRuntimeEntry 35  }
   
   
   jMSDurableSubscriberRuntimeTable OBJECT-TYPE
      SYNTAX      SEQUENCE OF JMSDurableSubscriberRuntimeEntry
      MAX-ACCESS  not-accessible
      STATUS      current
      DESCRIPTION "This table is used for monitoring a WebLogic JMS Durable Subscriber."
      ::= { wls 460  }
      
   
   jMSDurableSubscriberRuntimeEntry OBJECT-TYPE
      SYNTAX      JMSDurableSubscriberRuntimeEntry
      MAX-ACCESS  not-accessible
      STATUS      current
      DESCRIPTION "Entry of jMSDurableSubscriberRuntimeTable"
      INDEX { jMSDurableSubscriberRuntimeIndex}
      ::= { jMSDurableSubscriberRuntimeTable 1 }
      
   JMSDurableSubscriberRuntimeEntry ::=
      SEQUENCE
      {
         jMSDurableSubscriberRuntimeIndex DisplayString (SIZE (1..16)),
         jMSDurableSubscriberRuntimeObjectName DisplayString (SIZE (1..256)),
         jMSDurableSubscriberRuntimeType DisplayString (SIZE (1..64)),
         jMSDurableSubscriberRuntimeName DisplayString (SIZE (1..64)),
         jMSDurableSubscriberRuntimeParent DisplayString (SIZE (1..256)),
         jMSDurableSubscriberRuntimeClientID DisplayString (SIZE (1..256)),
         jMSDurableSubscriberRuntimeSubscriptionName DisplayString (SIZE (1..256)),
         jMSDurableSubscriberRuntimeSelector DisplayString (SIZE (1..256)),
         jMSDurableSubscriberRuntimeNoLocal INTEGER
                     {
                        true(1),
                        false(2)
                     }
         ,
         jMSDurableSubscriberRuntimeActive INTEGER
                     {
                        true(1),
                        false(2)
                     }
         ,
         jMSDurableSubscriberRuntimeMessagesPendingCount Counter64,
         jMSDurableSubscriberRuntimeMessagesCurrentCount Counter64,
         jMSDurableSubscriberRuntimeBytesPendingCount Counter64,
         jMSDurableSubscriberRuntimeBytesCurrentCount Counter64,
         jMSDurableSubscriberRuntimeMessagesReceivedCount Counter64,
         jMSDurableSubscriberRuntimeMessagesHighCount Counter64
      }
      
   
   jMSDurableSubscriberRuntimeIndex OBJECT-TYPE
      SYNTAX      DisplayString (SIZE (1..16))
      MAX-ACCESS  read-only
      STATUS      current
      DESCRIPTION "Unique value directed from ObjectName which is used as table index"
      ::= { jMSDurableSubscriberRuntimeEntry 1  }
   
   
   jMSDurableSubscriberRuntimeObjectName OBJECT-TYPE
      SYNTAX      DisplayString (SIZE (1..256))
      MAX-ACCESS  read-only
      STATUS      current
      DESCRIPTION "JMX-standard MBean name"
      ::= { jMSDurableSubscriberRuntimeEntry 5  }
   
   
   jMSDurableSubscriberRuntimeType OBJECT-TYPE
      SYNTAX      DisplayString (SIZE (1..64))
      MAX-ACCESS  read-only
      STATUS      current
      DESCRIPTION "BEA-proprietary MBean type"
      ::= { jMSDurableSubscriberRuntimeEntry 10  }
   
   
   jMSDurableSubscriberRuntimeName OBJECT-TYPE
      SYNTAX      DisplayString (SIZE (1..64))
      MAX-ACCESS  read-only
      STATUS      current
      DESCRIPTION "BEA-proprietary MBean name"
      ::= { jMSDurableSubscriberRuntimeEntry 15  }
   
   
   jMSDurableSubscriberRuntimeParent OBJECT-TYPE
      SYNTAX      DisplayString (SIZE (1..256))
      MAX-ACCESS  read-only
      STATUS      current
      DESCRIPTION "BEA-proprietary Parent object's identification, with syntax
      <type>:<name>"
      ::= { jMSDurableSubscriberRuntimeEntry 20  }
   
   
   jMSDurableSubscriberRuntimeClientID OBJECT-TYPE
      SYNTAX      DisplayString (SIZE (1..256))
      MAX-ACCESS  read-only
      STATUS      current
      DESCRIPTION "The client Id for this durable subscriber."
      ::= { jMSDurableSubscriberRuntimeEntry 25  }
   
   
   jMSDurableSubscriberRuntimeSubscriptionName OBJECT-TYPE
      SYNTAX      DisplayString (SIZE (1..256))
      MAX-ACCESS  read-only
      STATUS      current
      DESCRIPTION "The subscription name for this durable subscriber."
      ::= { jMSDurableSubscriberRuntimeEntry 30  }
   
   
   jMSDurableSubscriberRuntimeSelector OBJECT-TYPE
      SYNTAX      DisplayString (SIZE (1..256))
      MAX-ACCESS  read-only
      STATUS      current
      DESCRIPTION "durable subscriber selector."
      ::= { jMSDurableSubscriberRuntimeEntry 35  }
   
   
   jMSDurableSubscriberRuntimeNoLocal OBJECT-TYPE
      SYNTAX      INTEGER
                  {
                     true(1),
                     false(2)
                  }
      
      MAX-ACCESS  read-only
      STATUS      current
      DESCRIPTION "The noLocal boolean for this durable subscriber."
      ::= { jMSDurableSubscriberRuntimeEntry 40  }
   
   
   jMSDurableSubscriberRuntimeActive OBJECT-TYPE
      SYNTAX      INTEGER
                  {
                     true(1),
                     false(2)
                  }
      
      MAX-ACCESS  read-only
      STATUS      current
      DESCRIPTION "Is this subscription being used by a durable subscriber."
      ::= { jMSDurableSubscriberRuntimeEntry 45  }
   
   
   jMSDurableSubscriberRuntimeMessagesPendingCount OBJECT-TYPE
      SYNTAX      Counter64
      MAX-ACCESS  read-only
      STATUS      current
      DESCRIPTION "The number of messages pending (uncommitted and 
      unacknowledged) by this durable subscriber"
      ::= { jMSDurableSubscriberRuntimeEntry 50  }
   
   
   jMSDurableSubscriberRuntimeMessagesCurrentCount OBJECT-TYPE
      SYNTAX      Counter64
      MAX-ACCESS  read-only
      STATUS      current
      DESCRIPTION "The number of messages still available by this durable subscriber."
      ::= { jMSDurableSubscriberRuntimeEntry 55  }
   
   
   jMSDurableSubscriberRuntimeBytesPendingCount OBJECT-TYPE
      SYNTAX      Counter64
      MAX-ACCESS  read-only
      STATUS      current
      DESCRIPTION "The number of bytes pending by this durable subscriber."
      ::= { jMSDurableSubscriberRuntimeEntry 60  }
   
   
   jMSDurableSubscriberRuntimeBytesCurrentCount OBJECT-TYPE
      SYNTAX      Counter64
      MAX-ACCESS  read-only
      STATUS      current
      DESCRIPTION "The number of bytes received by this durable subscriber."
      ::= { jMSDurableSubscriberRuntimeEntry 65  }
   
   
   jMSDurableSubscriberRuntimeMessagesReceivedCount OBJECT-TYPE
      SYNTAX      Counter64
      MAX-ACCESS  read-only
      STATUS      current
      DESCRIPTION "Returns the number of messages received by the durable subscriber since that reset."
      ::= { jMSDurableSubscriberRuntimeEntry 66  }
   
   
   jMSDurableSubscriberRuntimeMessagesHighCount OBJECT-TYPE
      SYNTAX      Counter64
      MAX-ACCESS  read-only
      STATUS      current
      DESCRIPTION "Returns the peak number of messages for the durable subscriber since the last reset."
      ::= { jMSDurableSubscriberRuntimeEntry 67  }
   
   
   safAgentRuntimeTable OBJECT-TYPE
      SYNTAX      SEQUENCE OF SafAgentRuntimeEntry
      MAX-ACCESS  not-accessible
      STATUS      current
      DESCRIPTION "This table is used for monitoring a WebLogic Store And Forward Agent."
      ::= { wls 470  }
      
   
   safAgentRuntimeEntry OBJECT-TYPE
      SYNTAX      SafAgentRuntimeEntry
      MAX-ACCESS  not-accessible
      STATUS      current
      DESCRIPTION "Entry of SafAgentRuntimeTable"
      INDEX { safAgentRuntimeIndex}
      ::= { safAgentRuntimeTable 1 }
      
   SafAgentRuntimeEntry ::=
      SEQUENCE
      {
         safAgentRuntimeIndex DisplayString (SIZE (1..16)),
         safAgentRuntimeObjectName DisplayString (SIZE (1..256)),
         safAgentRuntimeType  DisplayString (SIZE (1..64)),
         safAgentRuntimeName  DisplayString (SIZE (1..64)),
         safAgentRuntimeParent DisplayString (SIZE (1..256)),
         safAgentRuntimeRemoteEndpointsCurrentCount Counter64,
         safAgentRuntimeRemoteEndpointsHighCount Counter64,
         safAgentRuntimeRemoteEndpointsTotalCount Counter64,
         safAgentRuntimePausedForIncoming INTEGER
                     {
                        true(1),
                        false(2)
                     }
         ,
         safAgentRuntimePausedForForwarding INTEGER
                     {
                        true(1),
                        false(2)
                     }
         ,
         safAgentRuntimeConversationsCurrentCount Counter64,
         safAgentRuntimeConversationsHighCount Counter64,
         safAgentRuntimeConversationsTotalCount Counter64,
         safAgentRuntimeMessagesCurrentCount Counter64,
         safAgentRuntimeMessagesPendingCount Counter64,
         safAgentRuntimeMessagesHighCount Counter64,
         safAgentRuntimeMessagesReceivedCount Counter64,
         safAgentRuntimeMessagesThresholdTime Counter64,
         safAgentRuntimeBytesPendingCount Counter64,
         safAgentRuntimeBytesCurrentCount Counter64,
         safAgentRuntimeBytesHighCount Counter64,
         safAgentRuntimeBytesReceivedCount Counter64,
         safAgentRuntimeBytesThresholdTime Counter64,
         safAgentRuntimeFailedMessagesTotal Counter64,
         safAgentRuntimePausedForReceiving OCTET STRING
      }
      
   
   safAgentRuntimeIndex OBJECT-TYPE
      SYNTAX      DisplayString (SIZE (1..16))
      MAX-ACCESS  read-only
      STATUS      current
      DESCRIPTION "Unique value directed from ObjectName which is used as table index"
      ::= { safAgentRuntimeEntry 1  }
   
   
   safAgentRuntimeObjectName OBJECT-TYPE
      SYNTAX      DisplayString (SIZE (1..256))
      MAX-ACCESS  read-only
      STATUS      current
      DESCRIPTION "JMX-standard MBean name"
      ::= { safAgentRuntimeEntry 5  }
   
   
   safAgentRuntimeType OBJECT-TYPE
      SYNTAX      DisplayString (SIZE (1..64))
      MAX-ACCESS  read-only
      STATUS      current
      DESCRIPTION "BEA-proprietary MBean type"
      ::= { safAgentRuntimeEntry 10  }
   
   
   safAgentRuntimeName OBJECT-TYPE
      SYNTAX      DisplayString (SIZE (1..64))
      MAX-ACCESS  read-only
      STATUS      current
      DESCRIPTION "BEA-proprietary MBean name"
      ::= { safAgentRuntimeEntry 15  }
   
   
   safAgentRuntimeParent OBJECT-TYPE
      SYNTAX      DisplayString (SIZE (1..256))
      MAX-ACCESS  read-only
      STATUS      current
      DESCRIPTION "BEA-proprietary Parent object's identification, with syntax
      <type>:<name>"
      ::= { safAgentRuntimeEntry 20  }
   
   
   safAgentRuntimeRemoteEndpointsCurrentCount OBJECT-TYPE
      SYNTAX      Counter64
      MAX-ACCESS  read-only
      STATUS      current
      DESCRIPTION "Returns the current number of remote endpoints to which this saf agent has been storing and forwarding messages."
      ::= { safAgentRuntimeEntry 25  }
   
   
   safAgentRuntimeRemoteEndpointsHighCount OBJECT-TYPE
      SYNTAX      Counter64
      MAX-ACCESS  read-only
      STATUS      current
      DESCRIPTION "Returns the peak number of remote endpoints to which this saf agent has been storing and forwarding messages
      since last reset."
      ::= { safAgentRuntimeEntry 30  }
   
   
   safAgentRuntimeRemoteEndpointsTotalCount OBJECT-TYPE
      SYNTAX      Counter64
      MAX-ACCESS  read-only
      STATUS      current
      DESCRIPTION "Returns the number of remote endpoints to which this saf agent has been storing and forwarding messages since last reset."
      ::= { safAgentRuntimeEntry 35  }
   
   
   safAgentRuntimePausedForIncoming OBJECT-TYPE
      SYNTAX      INTEGER
                  {
                     true(1),
                     false(2)
                  }
      
      MAX-ACCESS  read-only
      STATUS      current
      DESCRIPTION "Indicates whether or not the sending agent is paused for incoming messages at the current time."
      ::= { safAgentRuntimeEntry 40  }
   
   
   safAgentRuntimePausedForForwarding OBJECT-TYPE
      SYNTAX      INTEGER
                  {
                     true(1),
                     false(2)
                  }
      
      MAX-ACCESS  read-only
      STATUS      current
      DESCRIPTION "Indicates whether or not the sending agent is paused for forwarding at the current time."
      ::= { safAgentRuntimeEntry 45  }
   
   
   safAgentRuntimeConversationsCurrentCount OBJECT-TYPE
      SYNTAX      Counter64
      MAX-ACCESS  read-only
      STATUS      current
      DESCRIPTION "Returns the current number of conversations."
      ::= { safAgentRuntimeEntry 55  }
   
   
   safAgentRuntimeConversationsHighCount OBJECT-TYPE
      SYNTAX      Counter64
      MAX-ACCESS  read-only
      STATUS      current
      DESCRIPTION "Returns the peak number of conversations since the last reset."
      ::= { safAgentRuntimeEntry 60  }
   
   
   safAgentRuntimeConversationsTotalCount OBJECT-TYPE
      SYNTAX      Counter64
      MAX-ACCESS  read-only
      STATUS      current
      DESCRIPTION "Returns the total number of conversations since the last reset."
      ::= { safAgentRuntimeEntry 65  }
   
   
   safAgentRuntimeMessagesCurrentCount OBJECT-TYPE
      SYNTAX      Counter64
      MAX-ACCESS  read-only
      STATUS      current
      DESCRIPTION "Returns the current number of messages. This number includes the pending messages."
      ::= { safAgentRuntimeEntry 70  }
   
   
   safAgentRuntimeMessagesPendingCount OBJECT-TYPE
      SYNTAX      Counter64
      MAX-ACCESS  read-only
      STATUS      current
      DESCRIPTION "Returns the number of pending messages. Pending messages are over and above the current number of messages.
      A pending message is one that has either been sent in a transaction and not committed, or been forwarded
      but has not been acknowledged."
      ::= { safAgentRuntimeEntry 75  }
   
   
   safAgentRuntimeMessagesHighCount OBJECT-TYPE
      SYNTAX      Counter64
      MAX-ACCESS  read-only
      STATUS      current
      DESCRIPTION "Returns the peak number of messages since the last reset."
      ::= { safAgentRuntimeEntry 80  }
   
   
   safAgentRuntimeMessagesReceivedCount OBJECT-TYPE
      SYNTAX      Counter64
      MAX-ACCESS  read-only
      STATUS      current
      DESCRIPTION "The number of messages received since the last reset."
      ::= { safAgentRuntimeEntry 85  }
   
   
   safAgentRuntimeMessagesThresholdTime OBJECT-TYPE
      SYNTAX      Counter64
      MAX-ACCESS  read-only
      STATUS      current
      DESCRIPTION "Returns the amount of time in the threshold condition since the last reset."
      ::= { safAgentRuntimeEntry 90  }
   
   
   safAgentRuntimeBytesPendingCount OBJECT-TYPE
      SYNTAX      Counter64
      MAX-ACCESS  read-only
      STATUS      current
      DESCRIPTION "Returns the number of pending bytes. Pending bytes are over and above the current number of bytes."
      ::= { safAgentRuntimeEntry 95  }
   
   
   safAgentRuntimeBytesCurrentCount OBJECT-TYPE
      SYNTAX      Counter64
      MAX-ACCESS  read-only
      STATUS      current
      DESCRIPTION "Returns the current number of bytes. This number does not include the pending bytes."
      ::= { safAgentRuntimeEntry 100  }
   
   
   safAgentRuntimeBytesHighCount OBJECT-TYPE
      SYNTAX      Counter64
      MAX-ACCESS  read-only
      STATUS      current
      DESCRIPTION "Returns the peak number of bytes since the last reset."
      ::= { safAgentRuntimeEntry 105  }
   
   
   safAgentRuntimeBytesReceivedCount OBJECT-TYPE
      SYNTAX      Counter64
      MAX-ACCESS  read-only
      STATUS      current
      DESCRIPTION "The number of bytes received since the last reset."
      ::= { safAgentRuntimeEntry 110  }
   
   
   safAgentRuntimeBytesThresholdTime OBJECT-TYPE
      SYNTAX      Counter64
      MAX-ACCESS  read-only
      STATUS      current
      DESCRIPTION "Returns the amount of time in the threshold condition since the last reset."
      ::= { safAgentRuntimeEntry 115  }
   
   
   safAgentRuntimeFailedMessagesTotal OBJECT-TYPE
      SYNTAX      Counter64
      MAX-ACCESS  read-only
      STATUS      current
      DESCRIPTION "Returns the total number of messages that have failed to be forwarded since the last reset."
      ::= { safAgentRuntimeEntry 120  }
   
   
   safAgentRuntimePausedForReceiving OBJECT-TYPE
      SYNTAX      OCTET STRING
      MAX-ACCESS  read-only
      STATUS      current
      DESCRIPTION "Indicates whether or not the receiving agent is paused for receiving at the current time."
      ::= { safAgentRuntimeEntry 121  }
   
   
   safConversationRuntimeTable OBJECT-TYPE
      SYNTAX      SEQUENCE OF SafConversationRuntimeEntry
      MAX-ACCESS  not-accessible
      STATUS      current
      DESCRIPTION "This table is used for monitoring a WebLogic Store And Forward Agent."
      ::= { wls 471  }
      
   
   safConversationRuntimeEntry OBJECT-TYPE
      SYNTAX      SafConversationRuntimeEntry
      MAX-ACCESS  not-accessible
      STATUS      current
      DESCRIPTION "Entry of SafConversationRuntimeTable"
      INDEX { safConversationRuntimeIndex}
      ::= { safConversationRuntimeTable 1 }
      
   SafConversationRuntimeEntry ::=
      SEQUENCE
      {
         safConversationRuntimeIndex DisplayString (SIZE (1..16)),
         safConversationRuntimeObjectName DisplayString (SIZE (1..256)),
         safConversationRuntimeType DisplayString (SIZE (1..64)),
         safConversationRuntimeName DisplayString (SIZE (1..64)),
         safConversationRuntimeParent DisplayString (SIZE (1..256)),
         safConversationRuntimeConversationName DisplayString (SIZE (1..64)),
         safConversationRuntimeDestinationURL DisplayString (SIZE (1..64)),
         safConversationRuntimeQOS DisplayString (SIZE (1..64))
      }
      
   
   safConversationRuntimeIndex OBJECT-TYPE
      SYNTAX      DisplayString (SIZE (1..16))
      MAX-ACCESS  read-only
      STATUS      current
      DESCRIPTION "Unique value directed from ObjectName which is used as table index"
      ::= { safConversationRuntimeEntry 1  }
   
   
   safConversationRuntimeObjectName OBJECT-TYPE
      SYNTAX      DisplayString (SIZE (1..256))
      MAX-ACCESS  read-only
      STATUS      current
      DESCRIPTION "JMX-standard MBean name"
      ::= { safConversationRuntimeEntry 5  }
   
   
   safConversationRuntimeType OBJECT-TYPE
      SYNTAX      DisplayString (SIZE (1..64))
      MAX-ACCESS  read-only
      STATUS      current
      DESCRIPTION "BEA-proprietary MBean type"
      ::= { safConversationRuntimeEntry 10  }
   
   
   safConversationRuntimeName OBJECT-TYPE
      SYNTAX      DisplayString (SIZE (1..64))
      MAX-ACCESS  read-only
      STATUS      current
      DESCRIPTION "BEA-proprietary MBean name"
      ::= { safConversationRuntimeEntry 15  }
   
   
   safConversationRuntimeParent OBJECT-TYPE
      SYNTAX      DisplayString (SIZE (1..256))
      MAX-ACCESS  read-only
      STATUS      current
      DESCRIPTION "BEA-proprietary Parent object's identification, with syntax
      <type>:<name>"
      ::= { safConversationRuntimeEntry 20  }
   
   
   safConversationRuntimeConversationName OBJECT-TYPE
      SYNTAX      DisplayString (SIZE (1..64))
      MAX-ACCESS  read-only
      STATUS      current
      DESCRIPTION "Returns the name of the conversation."
      ::= { safConversationRuntimeEntry 25  }
   
   
   safConversationRuntimeDestinationURL OBJECT-TYPE
      SYNTAX      DisplayString (SIZE (1..64))
      MAX-ACCESS  read-only
      STATUS      current
      DESCRIPTION "Returns the name of the conversation."
      ::= { safConversationRuntimeEntry 30  }
   
   
   safConversationRuntimeQOS OBJECT-TYPE
      SYNTAX      DisplayString (SIZE (1..64))
      MAX-ACCESS  read-only
      STATUS      current
      DESCRIPTION "Returns the name of the conversation."
      ::= { safConversationRuntimeEntry 35  }
   
   
   safRemoteEndpointRuntimeTable OBJECT-TYPE
      SYNTAX      SEQUENCE OF SafRemoteEndpointRuntimeEntry
      MAX-ACCESS  not-accessible
      STATUS      current
      DESCRIPTION "This table is used for monitoring a WebLogic Store And Forward RemoteEndpoint."
      ::= { wls 472  }
      
   
   safRemoteEndpointRuntimeEntry OBJECT-TYPE
      SYNTAX      SafRemoteEndpointRuntimeEntry
      MAX-ACCESS  not-accessible
      STATUS      current
      DESCRIPTION "Entry of SafRemoteEndpointRuntimeTable"
      INDEX { safRemoteEndpointRuntimeIndex}
      ::= { safRemoteEndpointRuntimeTable 1 }
      
   SafRemoteEndpointRuntimeEntry ::=
      SEQUENCE
      {
         safRemoteEndpointRuntimeIndex DisplayString (SIZE (1..16)),
         safRemoteEndpointRuntimeObjectName DisplayString (SIZE (1..256)),
         safRemoteEndpointRuntimeType DisplayString (SIZE (1..64)),
         safRemoteEndpointRuntimeName DisplayString (SIZE (1..64)),
         safRemoteEndpointRuntimeParent DisplayString (SIZE (1..256)),
         safRemoteEndpointRuntimeURL DisplayString (SIZE (1..128)),
         safRemoteEndpointRuntimeEndpointType DisplayString (SIZE (1..256)),
         safRemoteEndpointRuntimePausedForIncoming INTEGER
                     {
                        true(1),
                        false(2)
                     }
         ,
         safRemoteEndpointRuntimePausedForForwarding INTEGER
                     {
                        true(1),
                        false(2)
                     }
         ,
         safRemoteEndpointRuntimeDowntimeHigh Counter64,
         safRemoteEndpointRuntimeDowntimeTotal Counter64,
         safRemoteEndpointRuntimeUptimeHigh Counter64,
         safRemoteEndpointRuntimeUptimeTotal Counter64,
         safRemoteEndpointRuntimeMessagesCurrentCount Counter64,
         safRemoteEndpointRuntimeMessagesPendingCount Counter64,
         safRemoteEndpointRuntimeMessagesHighCount Counter64,
         safRemoteEndpointRuntimeMessagesReceivedCount Counter64,
         safRemoteEndpointRuntimeMessagesThresholdTime Counter64,
         safRemoteEndpointRuntimeBytesPendingCount Counter64,
         safRemoteEndpointRuntimeBytesCurrentCount Counter64,
         safRemoteEndpointRuntimeBytesHighCount Counter64,
         safRemoteEndpointRuntimeBytesReceivedCount Counter64,
         safRemoteEndpointRuntimeBytesThresholdTime Counter64,
         safRemoteEndpointRuntimeFailedMessagesTotal Counter64
      }
      
   
   safRemoteEndpointRuntimeIndex OBJECT-TYPE
      SYNTAX      DisplayString (SIZE (1..16))
      MAX-ACCESS  read-only
      STATUS      current
      DESCRIPTION "Unique value directed from ObjectName which is used as table index"
      ::= { safRemoteEndpointRuntimeEntry 1  }
   
   
   safRemoteEndpointRuntimeObjectName OBJECT-TYPE
      SYNTAX      DisplayString (SIZE (1..256))
      MAX-ACCESS  read-only
      STATUS      current
      DESCRIPTION "JMX-standard MBean name"
      ::= { safRemoteEndpointRuntimeEntry 5  }
   
   
   safRemoteEndpointRuntimeType OBJECT-TYPE
      SYNTAX      DisplayString (SIZE (1..64))
      MAX-ACCESS  read-only
      STATUS      current
      DESCRIPTION "BEA-proprietary MBean type"
      ::= { safRemoteEndpointRuntimeEntry 10  }
   
   
   safRemoteEndpointRuntimeName OBJECT-TYPE
      SYNTAX      DisplayString (SIZE (1..64))
      MAX-ACCESS  read-only
      STATUS      current
      DESCRIPTION "BEA-proprietary MBean name"
      ::= { safRemoteEndpointRuntimeEntry 15  }
   
   
   safRemoteEndpointRuntimeParent OBJECT-TYPE
      SYNTAX      DisplayString (SIZE (1..256))
      MAX-ACCESS  read-only
      STATUS      current
      DESCRIPTION "BEA-proprietary Parent object's identification, with syntax
      <type>:<name>"
      ::= { safRemoteEndpointRuntimeEntry 20  }
   
   
   safRemoteEndpointRuntimeURL OBJECT-TYPE
      SYNTAX      DisplayString (SIZE (1..128))
      MAX-ACCESS  read-only
      STATUS      current
      DESCRIPTION "Returns the URL of the remote endpoint."
      ::= { safRemoteEndpointRuntimeEntry 25  }
   
   
   safRemoteEndpointRuntimeEndpointType OBJECT-TYPE
      SYNTAX      DisplayString (SIZE (1..256))
      MAX-ACCESS  read-only
      STATUS      current
      DESCRIPTION "Returns type value of the remote endpoint, either JMS or WebServices."
      ::= { safRemoteEndpointRuntimeEntry 30  }
   
   
   safRemoteEndpointRuntimePausedForIncoming OBJECT-TYPE
      SYNTAX      INTEGER
                  {
                     true(1),
                     false(2)
                  }
      
      MAX-ACCESS  read-only
      STATUS      current
      DESCRIPTION "Indicates whether or not the remote endpoint is paused for incoming messages at the current time."
      ::= { safRemoteEndpointRuntimeEntry 35  }
   
   
   safRemoteEndpointRuntimePausedForForwarding OBJECT-TYPE
      SYNTAX      INTEGER
                  {
                     true(1),
                     false(2)
                  }
      
      MAX-ACCESS  read-only
      STATUS      current
      DESCRIPTION "Indicates whether or not the remote endpoint is paused for forwarding at the current time."
      ::= { safRemoteEndpointRuntimeEntry 40  }
   
   
   safRemoteEndpointRuntimeDowntimeHigh OBJECT-TYPE
      SYNTAX      Counter64
      MAX-ACCESS  read-only
      STATUS      current
      DESCRIPTION "eturns the longest time, in seconds, that the remote endpoint has not been available since the last reset."
      ::= { safRemoteEndpointRuntimeEntry 50  }
   
   
   safRemoteEndpointRuntimeDowntimeTotal OBJECT-TYPE
      SYNTAX      Counter64
      MAX-ACCESS  read-only
      STATUS      current
      DESCRIPTION "Returns the total time, in seconds, that the remote endpoint has not been available since the last reset."
      ::= { safRemoteEndpointRuntimeEntry 55  }
   
   
   safRemoteEndpointRuntimeUptimeHigh OBJECT-TYPE
      SYNTAX      Counter64
      MAX-ACCESS  read-only
      STATUS      current
      DESCRIPTION "Returns the longest time, in seconds, that the remote endpoint has been available since the last reset."
      ::= { safRemoteEndpointRuntimeEntry 60  }
   
   
   safRemoteEndpointRuntimeUptimeTotal OBJECT-TYPE
      SYNTAX      Counter64
      MAX-ACCESS  read-only
      STATUS      current
      DESCRIPTION "Returns the total time, in seconds, that the remote endpoint has been available since the last reset."
      ::= { safRemoteEndpointRuntimeEntry 65  }
   
   
   safRemoteEndpointRuntimeMessagesCurrentCount OBJECT-TYPE
      SYNTAX      Counter64
      MAX-ACCESS  read-only
      STATUS      current
      DESCRIPTION "Returns the current number of messages. This number includes the pending messages."
      ::= { safRemoteEndpointRuntimeEntry 85  }
   
   
   safRemoteEndpointRuntimeMessagesPendingCount OBJECT-TYPE
      SYNTAX      Counter64
      MAX-ACCESS  read-only
      STATUS      current
      DESCRIPTION "Returns the number of pending messages. Pending messages are over and above the current number of messages.
      A pending message is one that has either been sent in a transaction and not committed, or been forwarded
      but has not been acknowledged."
      ::= { safRemoteEndpointRuntimeEntry 90  }
   
   
   safRemoteEndpointRuntimeMessagesHighCount OBJECT-TYPE
      SYNTAX      Counter64
      MAX-ACCESS  read-only
      STATUS      current
      DESCRIPTION "Returns the peak number of messages since the last reset."
      ::= { safRemoteEndpointRuntimeEntry 95  }
   
   
   safRemoteEndpointRuntimeMessagesReceivedCount OBJECT-TYPE
      SYNTAX      Counter64
      MAX-ACCESS  read-only
      STATUS      current
      DESCRIPTION "The number of messages received since the last reset."
      ::= { safRemoteEndpointRuntimeEntry 100  }
   
   
   safRemoteEndpointRuntimeMessagesThresholdTime OBJECT-TYPE
      SYNTAX      Counter64
      MAX-ACCESS  read-only
      STATUS      current
      DESCRIPTION "Returns the amount of time in the threshold condition since the last reset."
      ::= { safRemoteEndpointRuntimeEntry 105  }
   
   
   safRemoteEndpointRuntimeBytesPendingCount OBJECT-TYPE
      SYNTAX      Counter64
      MAX-ACCESS  read-only
      STATUS      current
      DESCRIPTION "Returns the number of pending bytes. Pending bytes are over and above the current number of bytes."
      ::= { safRemoteEndpointRuntimeEntry 110  }
   
   
   safRemoteEndpointRuntimeBytesCurrentCount OBJECT-TYPE
      SYNTAX      Counter64
      MAX-ACCESS  read-only
      STATUS      current
      DESCRIPTION "Returns the current number of bytes. This number does not include the pending bytes."
      ::= { safRemoteEndpointRuntimeEntry 115  }
   
   
   safRemoteEndpointRuntimeBytesHighCount OBJECT-TYPE
      SYNTAX      Counter64
      MAX-ACCESS  read-only
      STATUS      current
      DESCRIPTION "Returns the peak number of bytes since the last reset."
      ::= { safRemoteEndpointRuntimeEntry 120  }
   
   
   safRemoteEndpointRuntimeBytesReceivedCount OBJECT-TYPE
      SYNTAX      Counter64
      MAX-ACCESS  read-only
      STATUS      current
      DESCRIPTION "The number of bytes received since the last reset."
      ::= { safRemoteEndpointRuntimeEntry 125  }
   
   
   safRemoteEndpointRuntimeBytesThresholdTime OBJECT-TYPE
      SYNTAX      Counter64
      MAX-ACCESS  read-only
      STATUS      current
      DESCRIPTION "Returns the amount of time in the threshold condition since the last reset."
      ::= { safRemoteEndpointRuntimeEntry 130  }
   
   
   safRemoteEndpointRuntimeFailedMessagesTotal OBJECT-TYPE
      SYNTAX      Counter64
      MAX-ACCESS  read-only
      STATUS      current
      DESCRIPTION "Returns the total number of messages that have failed to be forwarded since the last reset."
      ::= { safRemoteEndpointRuntimeEntry 135  }
   
   
   wldfDbstoreArchiveRuntimeTable OBJECT-TYPE
      SYNTAX      SEQUENCE OF WldfDbstoreArchiveRuntimeEntry
      MAX-ACCESS  not-accessible
      STATUS      current
      DESCRIPTION "This table is used for monitoring a WebLogic WLDF database backed archive."
      ::= { wls 480  }
      
   
   wldfDbstoreArchiveRuntimeEntry OBJECT-TYPE
      SYNTAX      WldfDbstoreArchiveRuntimeEntry
      MAX-ACCESS  not-accessible
      STATUS      current
      DESCRIPTION "Entry of WLDFDbStoreArchiveRuntimeTable"
      INDEX { wldfDbstoreArchiveRuntimeIndex}
      ::= { wldfDbstoreArchiveRuntimeTable 1 }
      
   WldfDbstoreArchiveRuntimeEntry ::=
      SEQUENCE
      {
         wldfDbstoreArchiveRuntimeIndex DisplayString (SIZE (1..16)),
         wldfDbstoreArchiveRuntimeObjectName DisplayString (SIZE (1..256)),
         wldfDbstoreArchiveRuntimeType DisplayString (SIZE (1..64)),
         wldfDbstoreArchiveRuntimeName DisplayString (SIZE (1..64)),
         wldfDbstoreArchiveRuntimeParent DisplayString (SIZE (1..256)),
         wldfDbstoreArchiveRuntimeRecordSeekCount Counter64,
         wldfDbstoreArchiveRuntimeRecordSeekTime Counter64,
         wldfDbstoreArchiveRuntimeRetrievedRecordCount Counter64,
         wldfDbstoreArchiveRuntimeRecordRetrievalTime Counter64,
         wldfDbstoreArchiveRuntimeInsertionCount Counter64,
         wldfDbstoreArchiveRuntimeInsertionTime Counter64,
         wldfDbstoreArchiveRuntimeDeletionCount Counter64,
         wldfDbstoreArchiveRuntimeDeletionTime Counter64,
         wldfDbstoreArchiveRuntimeLastDataRetirementStartTime Counter64,
         wldfDbstoreArchiveRuntimeDataRetirementCycles INTEGER,
         wldfDbstoreArchiveRuntimeDataRetirementTotalTime Counter64,
         wldfDbstoreArchiveRuntimeRetiredRecordCount Counter64,
         wldfDbstoreArchiveRuntimeLastDataRetirementTime Counter64
      }
      
   
   wldfDbstoreArchiveRuntimeIndex OBJECT-TYPE
      SYNTAX      DisplayString (SIZE (1..16))
      MAX-ACCESS  read-only
      STATUS      current
      DESCRIPTION "Unique value directed from ObjectName which is used as table index"
      ::= { wldfDbstoreArchiveRuntimeEntry 1  }
   
   
   wldfDbstoreArchiveRuntimeObjectName OBJECT-TYPE
      SYNTAX      DisplayString (SIZE (1..256))
      MAX-ACCESS  read-only
      STATUS      current
      DESCRIPTION "JMX-standard MBean name"
      ::= { wldfDbstoreArchiveRuntimeEntry 5  }
   
   
   wldfDbstoreArchiveRuntimeType OBJECT-TYPE
      SYNTAX      DisplayString (SIZE (1..64))
      MAX-ACCESS  read-only
      STATUS      current
      DESCRIPTION "BEA-proprietary MBean type"
      ::= { wldfDbstoreArchiveRuntimeEntry 10  }
   
   
   wldfDbstoreArchiveRuntimeName OBJECT-TYPE
      SYNTAX      DisplayString (SIZE (1..64))
      MAX-ACCESS  read-only
      STATUS      current
      DESCRIPTION "BEA-proprietary MBean name"
      ::= { wldfDbstoreArchiveRuntimeEntry 15  }
   
   
   wldfDbstoreArchiveRuntimeParent OBJECT-TYPE
      SYNTAX      DisplayString (SIZE (1..256))
      MAX-ACCESS  read-only
      STATUS      current
      DESCRIPTION "BEA-proprietary Parent object's identification, with syntax
      <type>:<name>"
      ::= { wldfDbstoreArchiveRuntimeEntry 20  }
   
   
   wldfDbstoreArchiveRuntimeRecordSeekCount OBJECT-TYPE
      SYNTAX      Counter64
      MAX-ACCESS  read-only
      STATUS      current
      DESCRIPTION "Return the cummulative number of seek operations executed against the archive."
      ::= { wldfDbstoreArchiveRuntimeEntry 25  }
   
   
   wldfDbstoreArchiveRuntimeRecordSeekTime OBJECT-TYPE
      SYNTAX      Counter64
      MAX-ACCESS  read-only
      STATUS      current
      DESCRIPTION "Return the Cummulative time spent locating the first record while executing a query, in milliseconds."
      ::= { wldfDbstoreArchiveRuntimeEntry 30  }
   
   
   wldfDbstoreArchiveRuntimeRetrievedRecordCount OBJECT-TYPE
      SYNTAX      Counter64
      MAX-ACCESS  read-only
      STATUS      current
      DESCRIPTION "Return the Cummulative number of records retrieved from the archive."
      ::= { wldfDbstoreArchiveRuntimeEntry 35  }
   
   
   wldfDbstoreArchiveRuntimeRecordRetrievalTime OBJECT-TYPE
      SYNTAX      Counter64
      MAX-ACCESS  read-only
      STATUS      current
      DESCRIPTION "Return the Cummulative time spent for fetching records, in milliseconds."
      ::= { wldfDbstoreArchiveRuntimeEntry 40  }
   
   
   wldfDbstoreArchiveRuntimeInsertionCount OBJECT-TYPE
      SYNTAX      Counter64
      MAX-ACCESS  read-only
      STATUS      current
      DESCRIPTION "Return the Number of new records created."
      ::= { wldfDbstoreArchiveRuntimeEntry 45  }
   
   
   wldfDbstoreArchiveRuntimeInsertionTime OBJECT-TYPE
      SYNTAX      Counter64
      MAX-ACCESS  read-only
      STATUS      current
      DESCRIPTION "Return the Cummulative time spent to insert records, in milliseconds."
      ::= { wldfDbstoreArchiveRuntimeEntry 50  }
   
   
   wldfDbstoreArchiveRuntimeDeletionCount OBJECT-TYPE
      SYNTAX      Counter64
      MAX-ACCESS  read-only
      STATUS      current
      DESCRIPTION "Return the Number of records deleted."
      ::= { wldfDbstoreArchiveRuntimeEntry 55  }
   
   
   wldfDbstoreArchiveRuntimeDeletionTime OBJECT-TYPE
      SYNTAX      Counter64
      MAX-ACCESS  read-only
      STATUS      current
      DESCRIPTION "Return the Cummulative time spent to delete records, in milliseconds."
      ::= { wldfDbstoreArchiveRuntimeEntry 60  }
   
   
   wldfDbstoreArchiveRuntimeLastDataRetirementStartTime OBJECT-TYPE
      SYNTAX      Counter64
      MAX-ACCESS  read-only
      STATUS      current
      DESCRIPTION ""
      ::= { wldfDbstoreArchiveRuntimeEntry 61  }
   
   
   wldfDbstoreArchiveRuntimeDataRetirementCycles OBJECT-TYPE
      SYNTAX      INTEGER
      MAX-ACCESS  read-only
      STATUS      current
      DESCRIPTION ""
      ::= { wldfDbstoreArchiveRuntimeEntry 62  }
   
   
   wldfDbstoreArchiveRuntimeDataRetirementTotalTime OBJECT-TYPE
      SYNTAX      Counter64
      MAX-ACCESS  read-only
      STATUS      current
      DESCRIPTION ""
      ::= { wldfDbstoreArchiveRuntimeEntry 63  }
   
   
   wldfDbstoreArchiveRuntimeRetiredRecordCount OBJECT-TYPE
      SYNTAX      Counter64
      MAX-ACCESS  read-only
      STATUS      current
      DESCRIPTION ""
      ::= { wldfDbstoreArchiveRuntimeEntry 64  }
   
   
   wldfDbstoreArchiveRuntimeLastDataRetirementTime OBJECT-TYPE
      SYNTAX      Counter64
      MAX-ACCESS  read-only
      STATUS      current
      DESCRIPTION ""
      ::= { wldfDbstoreArchiveRuntimeEntry 65  }
   
   
   wldfFileArchiveRuntimeTable OBJECT-TYPE
      SYNTAX      SEQUENCE OF WldfFileArchiveRuntimeEntry
      MAX-ACCESS  not-accessible
      STATUS      current
      DESCRIPTION "This table is used for monitoring a WebLogic WLDF File backed archive."
      ::= { wls 481  }
      
   
   wldfFileArchiveRuntimeEntry OBJECT-TYPE
      SYNTAX      WldfFileArchiveRuntimeEntry
      MAX-ACCESS  not-accessible
      STATUS      current
      DESCRIPTION "Entry of WLDFFileArchiveRuntimeTable"
      INDEX { wldfFileArchiveRuntimeIndex}
      ::= { wldfFileArchiveRuntimeTable 1 }
      
   WldfFileArchiveRuntimeEntry ::=
      SEQUENCE
      {
         wldfFileArchiveRuntimeIndex DisplayString (SIZE (1..16)),
         wldfFileArchiveRuntimeObjectName DisplayString (SIZE (1..256)),
         wldfFileArchiveRuntimeType DisplayString (SIZE (1..64)),
         wldfFileArchiveRuntimeName DisplayString (SIZE (1..64)),
         wldfFileArchiveRuntimeParent DisplayString (SIZE (1..256)),
         wldfFileArchiveRuntimeRecordSeekCount Counter64,
         wldfFileArchiveRuntimeRecordSeekTime Counter64,
         wldfFileArchiveRuntimeRetrievedRecordCount Counter64,
         wldfFileArchiveRuntimeRecordRetrievalTime Counter64,
         wldfFileArchiveRuntimeRotatedFilesCount INTEGER,
         wldfFileArchiveRuntimeIndexCycleCount INTEGER,
         wldfFileArchiveRuntimeIndexTime Counter64,
         wldfFileArchiveRuntimeIncrementalIndexCycleCount INTEGER,
         wldfFileArchiveRuntimeIncrementalIndexTime Counter64
      }
      
   
   wldfFileArchiveRuntimeIndex OBJECT-TYPE
      SYNTAX      DisplayString (SIZE (1..16))
      MAX-ACCESS  read-only
      STATUS      current
      DESCRIPTION "Unique value directed from ObjectName which is used as table index"
      ::= { wldfFileArchiveRuntimeEntry 1  }
   
   
   wldfFileArchiveRuntimeObjectName OBJECT-TYPE
      SYNTAX      DisplayString (SIZE (1..256))
      MAX-ACCESS  read-only
      STATUS      current
      DESCRIPTION "JMX-standard MBean name"
      ::= { wldfFileArchiveRuntimeEntry 5  }
   
   
   wldfFileArchiveRuntimeType OBJECT-TYPE
      SYNTAX      DisplayString (SIZE (1..64))
      MAX-ACCESS  read-only
      STATUS      current
      DESCRIPTION "BEA-proprietary MBean type"
      ::= { wldfFileArchiveRuntimeEntry 10  }
   
   
   wldfFileArchiveRuntimeName OBJECT-TYPE
      SYNTAX      DisplayString (SIZE (1..64))
      MAX-ACCESS  read-only
      STATUS      current
      DESCRIPTION "BEA-proprietary MBean name"
      ::= { wldfFileArchiveRuntimeEntry 15  }
   
   
   wldfFileArchiveRuntimeParent OBJECT-TYPE
      SYNTAX      DisplayString (SIZE (1..256))
      MAX-ACCESS  read-only
      STATUS      current
      DESCRIPTION "BEA-proprietary Parent object's identification, with syntax
      <type>:<name>"
      ::= { wldfFileArchiveRuntimeEntry 20  }
   
   
   wldfFileArchiveRuntimeRecordSeekCount OBJECT-TYPE
      SYNTAX      Counter64
      MAX-ACCESS  read-only
      STATUS      current
      DESCRIPTION "Return the cummulative number of seek operations executed against the archive."
      ::= { wldfFileArchiveRuntimeEntry 25  }
   
   
   wldfFileArchiveRuntimeRecordSeekTime OBJECT-TYPE
      SYNTAX      Counter64
      MAX-ACCESS  read-only
      STATUS      current
      DESCRIPTION "Return the Cummulative time spent locating the first record while executing a query, in milliseconds."
      ::= { wldfFileArchiveRuntimeEntry 30  }
   
   
   wldfFileArchiveRuntimeRetrievedRecordCount OBJECT-TYPE
      SYNTAX      Counter64
      MAX-ACCESS  read-only
      STATUS      current
      DESCRIPTION "Return the Cummulative number of records retrieved from the archive."
      ::= { wldfFileArchiveRuntimeEntry 35  }
   
   
   wldfFileArchiveRuntimeRecordRetrievalTime OBJECT-TYPE
      SYNTAX      Counter64
      MAX-ACCESS  read-only
      STATUS      current
      DESCRIPTION "Return the Cummulative time spent for fetching records, in milliseconds."
      ::= { wldfFileArchiveRuntimeEntry 40  }
   
   
   wldfFileArchiveRuntimeRotatedFilesCount OBJECT-TYPE
      SYNTAX      INTEGER
      MAX-ACCESS  read-only
      STATUS      current
      DESCRIPTION "Return the Number of rotated log file fragments."
      ::= { wldfFileArchiveRuntimeEntry 45  }
   
   
   wldfFileArchiveRuntimeIndexCycleCount OBJECT-TYPE
      SYNTAX      INTEGER
      MAX-ACCESS  read-only
      STATUS      current
      DESCRIPTION "Return the Number of times indexing cycles were executed."
      ::= { wldfFileArchiveRuntimeEntry 50  }
   
   
   wldfFileArchiveRuntimeIndexTime OBJECT-TYPE
      SYNTAX      Counter64
      MAX-ACCESS  read-only
      STATUS      current
      DESCRIPTION "Return the Cummulative indexing time, in milliseconds."
      ::= { wldfFileArchiveRuntimeEntry 55  }
   
   
   wldfFileArchiveRuntimeIncrementalIndexCycleCount OBJECT-TYPE
      SYNTAX      INTEGER
      MAX-ACCESS  read-only
      STATUS      current
      DESCRIPTION "Return the Number of times incremental indexing cycles were executed."
      ::= { wldfFileArchiveRuntimeEntry 60  }
   
   
   wldfFileArchiveRuntimeIncrementalIndexTime OBJECT-TYPE
      SYNTAX      Counter64
      MAX-ACCESS  read-only
      STATUS      current
      DESCRIPTION "Return the Cummulative time spent while incremental indexing, in milliseconds."
      ::= { wldfFileArchiveRuntimeEntry 65  }
   
   
   wldfWlstoreArchiveRuntimeTable OBJECT-TYPE
      SYNTAX      SEQUENCE OF WldfWlstoreArchiveRuntimeEntry
      MAX-ACCESS  not-accessible
      STATUS      current
      DESCRIPTION "This table is used for monitoring a WebLogic WLDF WebLogic Store backed archive."
      ::= { wls 482  }
      
   
   wldfWlstoreArchiveRuntimeEntry OBJECT-TYPE
      SYNTAX      WldfWlstoreArchiveRuntimeEntry
      MAX-ACCESS  not-accessible
      STATUS      current
      DESCRIPTION "Entry of WLDFWlstoreArchiveRuntimeTable"
      INDEX { wldfWlstoreArchiveRuntimeIndex}
      ::= { wldfWlstoreArchiveRuntimeTable 1 }
      
   WldfWlstoreArchiveRuntimeEntry ::=
      SEQUENCE
      {
         wldfWlstoreArchiveRuntimeIndex DisplayString (SIZE (1..16)),
         wldfWlstoreArchiveRuntimeObjectName DisplayString (SIZE (1..256)),
         wldfWlstoreArchiveRuntimeType DisplayString (SIZE (1..64)),
         wldfWlstoreArchiveRuntimeName DisplayString (SIZE (1..64)),
         wldfWlstoreArchiveRuntimeParent DisplayString (SIZE (1..256)),
         wldfWlstoreArchiveRuntimeRecordSeekCount Counter64,
         wldfWlstoreArchiveRuntimeRecordSeekTime Counter64,
         wldfWlstoreArchiveRuntimeRetrievedRecordCount Counter64,
         wldfWlstoreArchiveRuntimeRecordRetrievalTime Counter64,
         wldfWlstoreArchiveRuntimeIndexPageCount INTEGER,
         wldfWlstoreArchiveRuntimeInsertionCount Counter64,
         wldfWlstoreArchiveRuntimeInsertionTime Counter64,
         wldfWlstoreArchiveRuntimeDeletionCount Counter64,
         wldfWlstoreArchiveRuntimeDeletionTime Counter64,
         wldfWlstoreArchiveRuntimeLastDataRetirementStartTime Counter64,
         wldfWlstoreArchiveRuntimeRecordCount Counter64,
         wldfWlstoreArchiveRuntimeDataRetirementCycles INTEGER,
         wldfWlstoreArchiveRuntimeDataRetirementTotalTime Counter64,
         wldfWlstoreArchiveRuntimeRetiredRecordCount Counter64,
         wldfWlstoreArchiveRuntimeLastDataRetirementTime Counter64
      }
      
   
   wldfWlstoreArchiveRuntimeIndex OBJECT-TYPE
      SYNTAX      DisplayString (SIZE (1..16))
      MAX-ACCESS  read-only
      STATUS      current
      DESCRIPTION "Unique value directed from ObjectName which is used as table index"
      ::= { wldfWlstoreArchiveRuntimeEntry 1  }
   
   
   wldfWlstoreArchiveRuntimeObjectName OBJECT-TYPE
      SYNTAX      DisplayString (SIZE (1..256))
      MAX-ACCESS  read-only
      STATUS      current
      DESCRIPTION "JMX-standard MBean name"
      ::= { wldfWlstoreArchiveRuntimeEntry 5  }
   
   
   wldfWlstoreArchiveRuntimeType OBJECT-TYPE
      SYNTAX      DisplayString (SIZE (1..64))
      MAX-ACCESS  read-only
      STATUS      current
      DESCRIPTION "BEA-proprietary MBean type"
      ::= { wldfWlstoreArchiveRuntimeEntry 10  }
   
   
   wldfWlstoreArchiveRuntimeName OBJECT-TYPE
      SYNTAX      DisplayString (SIZE (1..64))
      MAX-ACCESS  read-only
      STATUS      current
      DESCRIPTION "BEA-proprietary MBean name"
      ::= { wldfWlstoreArchiveRuntimeEntry 15  }
   
   
   wldfWlstoreArchiveRuntimeParent OBJECT-TYPE
      SYNTAX      DisplayString (SIZE (1..256))
      MAX-ACCESS  read-only
      STATUS      current
      DESCRIPTION "BEA-proprietary Parent object's identification, with syntax
      <type>:<name>"
      ::= { wldfWlstoreArchiveRuntimeEntry 20  }
   
   
   wldfWlstoreArchiveRuntimeRecordSeekCount OBJECT-TYPE
      SYNTAX      Counter64
      MAX-ACCESS  read-only
      STATUS      current
      DESCRIPTION "Return the cummulative number of seek operations executed against the archive."
      ::= { wldfWlstoreArchiveRuntimeEntry 25  }
   
   
   wldfWlstoreArchiveRuntimeRecordSeekTime OBJECT-TYPE
      SYNTAX      Counter64
      MAX-ACCESS  read-only
      STATUS      current
      DESCRIPTION "Return the Cummulative time spent locating the first record while executing a query, in milliseconds."
      ::= { wldfWlstoreArchiveRuntimeEntry 30  }
   
   
   wldfWlstoreArchiveRuntimeRetrievedRecordCount OBJECT-TYPE
      SYNTAX      Counter64
      MAX-ACCESS  read-only
      STATUS      current
      DESCRIPTION "Return the Cummulative number of records retrieved from the archive."
      ::= { wldfWlstoreArchiveRuntimeEntry 35  }
   
   
   wldfWlstoreArchiveRuntimeRecordRetrievalTime OBJECT-TYPE
      SYNTAX      Counter64
      MAX-ACCESS  read-only
      STATUS      current
      DESCRIPTION "Return the Cummulative time spent for fetching records, in milliseconds."
      ::= { wldfWlstoreArchiveRuntimeEntry 40  }
   
   
   wldfWlstoreArchiveRuntimeIndexPageCount OBJECT-TYPE
      SYNTAX      INTEGER
      MAX-ACCESS  read-only
      STATUS      current
      DESCRIPTION "Return the Number of index pages."
      ::= { wldfWlstoreArchiveRuntimeEntry 45  }
   
   
   wldfWlstoreArchiveRuntimeInsertionCount OBJECT-TYPE
      SYNTAX      Counter64
      MAX-ACCESS  read-only
      STATUS      current
      DESCRIPTION "Return the Number of new records created."
      ::= { wldfWlstoreArchiveRuntimeEntry 50  }
   
   
   wldfWlstoreArchiveRuntimeInsertionTime OBJECT-TYPE
      SYNTAX      Counter64
      MAX-ACCESS  read-only
      STATUS      current
      DESCRIPTION "Return the Cummulative time spent to insert records, in milliseconds."
      ::= { wldfWlstoreArchiveRuntimeEntry 55  }
   
   
   wldfWlstoreArchiveRuntimeDeletionCount OBJECT-TYPE
      SYNTAX      Counter64
      MAX-ACCESS  read-only
      STATUS      current
      DESCRIPTION "Return the Number of records deleted."
      ::= { wldfWlstoreArchiveRuntimeEntry 60  }
   
   
   wldfWlstoreArchiveRuntimeDeletionTime OBJECT-TYPE
      SYNTAX      Counter64
      MAX-ACCESS  read-only
      STATUS      current
      DESCRIPTION "Return the Cummulative time spent to delete records, in milliseconds."
      ::= { wldfWlstoreArchiveRuntimeEntry 65  }
   
   
   wldfWlstoreArchiveRuntimeLastDataRetirementStartTime OBJECT-TYPE
      SYNTAX      Counter64
      MAX-ACCESS  read-only
      STATUS      current
      DESCRIPTION ""
      ::= { wldfWlstoreArchiveRuntimeEntry 66  }
   
   
   wldfWlstoreArchiveRuntimeRecordCount OBJECT-TYPE
      SYNTAX      Counter64
      MAX-ACCESS  read-only
      STATUS      current
      DESCRIPTION "Total number of records in the archive"
      ::= { wldfWlstoreArchiveRuntimeEntry 67  }
   
   
   wldfWlstoreArchiveRuntimeDataRetirementCycles OBJECT-TYPE
      SYNTAX      INTEGER
      MAX-ACCESS  read-only
      STATUS      current
      DESCRIPTION ""
      ::= { wldfWlstoreArchiveRuntimeEntry 68  }
   
   
   wldfWlstoreArchiveRuntimeDataRetirementTotalTime OBJECT-TYPE
      SYNTAX      Counter64
      MAX-ACCESS  read-only
      STATUS      current
      DESCRIPTION ""
      ::= { wldfWlstoreArchiveRuntimeEntry 69  }
   
   
   wldfWlstoreArchiveRuntimeRetiredRecordCount OBJECT-TYPE
      SYNTAX      Counter64
      MAX-ACCESS  read-only
      STATUS      current
      DESCRIPTION ""
      ::= { wldfWlstoreArchiveRuntimeEntry 70  }
   
   
   wldfWlstoreArchiveRuntimeLastDataRetirementTime OBJECT-TYPE
      SYNTAX      Counter64
      MAX-ACCESS  read-only
      STATUS      current
      DESCRIPTION ""
      ::= { wldfWlstoreArchiveRuntimeEntry 71  }
   
   
   wldfHarvesterRuntimeTable OBJECT-TYPE
      SYNTAX      SEQUENCE OF WldfHarvesterRuntimeEntry
      MAX-ACCESS  not-accessible
      STATUS      current
      DESCRIPTION "This table is used for monitoring a WebLogic WLDF Harvester."
      ::= { wls 483  }
      
   
   wldfHarvesterRuntimeEntry OBJECT-TYPE
      SYNTAX      WldfHarvesterRuntimeEntry
      MAX-ACCESS  not-accessible
      STATUS      current
      DESCRIPTION "Entry of WLDFHarvesterRuntimeTable"
      INDEX { wldfHarvesterRuntimeIndex}
      ::= { wldfHarvesterRuntimeTable 1 }
      
   WldfHarvesterRuntimeEntry ::=
      SEQUENCE
      {
         wldfHarvesterRuntimeIndex DisplayString (SIZE (1..16)),
         wldfHarvesterRuntimeObjectName DisplayString (SIZE (1..256)),
         wldfHarvesterRuntimeType DisplayString (SIZE (1..64)),
         wldfHarvesterRuntimeName DisplayString (SIZE (1..64)),
         wldfHarvesterRuntimeParent DisplayString (SIZE (1..256)),
         wldfHarvesterRuntimeSamplePeriod Counter64,
         wldfHarvesterRuntimeTotalSamplingCycles Counter64,
         wldfHarvesterRuntimeMinimumSamplingTime Counter64,
         wldfHarvesterRuntimeMaximumSamplingTime Counter64,
         wldfHarvesterRuntimeTotalSamplingTime Counter64,
         wldfHarvesterRuntimeAverageSamplingTime Counter64,
         wldfHarvesterRuntimeCurrentDataSampleCount Counter64,
         wldfHarvesterRuntimeCurrentSnapshotStartTime Counter64,
         wldfHarvesterRuntimeCurrentSnapshotElapsedTime Counter64,
         wldfHarvesterRuntimeTotalSamplingTimeOutlierCount Counter64,
         wldfHarvesterRuntimeOutlierDetectionFactor OCTET STRING,
         wldfHarvesterRuntimeTotalDataSampleCount Counter64,
         wldfHarvesterRuntimeCurrentSampleTimeAnOutlier OCTET STRING
      }
      
   
   wldfHarvesterRuntimeIndex OBJECT-TYPE
      SYNTAX      DisplayString (SIZE (1..16))
      MAX-ACCESS  read-only
      STATUS      current
      DESCRIPTION "Unique value directed from ObjectName which is used as table index"
      ::= { wldfHarvesterRuntimeEntry 1  }
   
   
   wldfHarvesterRuntimeObjectName OBJECT-TYPE
      SYNTAX      DisplayString (SIZE (1..256))
      MAX-ACCESS  read-only
      STATUS      current
      DESCRIPTION "JMX-standard MBean name"
      ::= { wldfHarvesterRuntimeEntry 5  }
   
   
   wldfHarvesterRuntimeType OBJECT-TYPE
      SYNTAX      DisplayString (SIZE (1..64))
      MAX-ACCESS  read-only
      STATUS      current
      DESCRIPTION "BEA-proprietary MBean type"
      ::= { wldfHarvesterRuntimeEntry 10  }
   
   
   wldfHarvesterRuntimeName OBJECT-TYPE
      SYNTAX      DisplayString (SIZE (1..64))
      MAX-ACCESS  read-only
      STATUS      current
      DESCRIPTION "BEA-proprietary MBean name"
      ::= { wldfHarvesterRuntimeEntry 15  }
   
   
   wldfHarvesterRuntimeParent OBJECT-TYPE
      SYNTAX      DisplayString (SIZE (1..256))
      MAX-ACCESS  read-only
      STATUS      current
      DESCRIPTION "BEA-proprietary Parent object's identification, with syntax <type>:<name>"
      ::= { wldfHarvesterRuntimeEntry 20  }
   
   
   wldfHarvesterRuntimeSamplePeriod OBJECT-TYPE
      SYNTAX      Counter64
      MAX-ACCESS  read-only
      STATUS      current
      DESCRIPTION "Return the current global sample period in nanoseconds."
      ::= { wldfHarvesterRuntimeEntry 25  }
   
   
   wldfHarvesterRuntimeTotalSamplingCycles OBJECT-TYPE
      SYNTAX      Counter64
      MAX-ACCESS  read-only
      STATUS      current
      DESCRIPTION "Return the total number of sampling cycles taken thus far."
      ::= { wldfHarvesterRuntimeEntry 30  }
   
   
   wldfHarvesterRuntimeMinimumSamplingTime OBJECT-TYPE
      SYNTAX      Counter64
      MAX-ACCESS  read-only
      STATUS      current
      DESCRIPTION "Return the minimum sampling time in nanoseconds."
      ::= { wldfHarvesterRuntimeEntry 35  }
   
   
   wldfHarvesterRuntimeMaximumSamplingTime OBJECT-TYPE
      SYNTAX      Counter64
      MAX-ACCESS  read-only
      STATUS      current
      DESCRIPTION "Return the maximum sampling time in nanoseconds."
      ::= { wldfHarvesterRuntimeEntry 40  }
   
   
   wldfHarvesterRuntimeTotalSamplingTime OBJECT-TYPE
      SYNTAX      Counter64
      MAX-ACCESS  read-only
      STATUS      current
      DESCRIPTION "Return the total amount of time spent (in nanoseconds) in sampling cycles."
      ::= { wldfHarvesterRuntimeEntry 45  }
   
   
   wldfHarvesterRuntimeAverageSamplingTime OBJECT-TYPE
      SYNTAX      Counter64
      MAX-ACCESS  read-only
      STATUS      current
      DESCRIPTION "Return the average amount of time spent (in nanoseconds) in sampling cycles."
      ::= { wldfHarvesterRuntimeEntry 50  }
   
   
   wldfHarvesterRuntimeCurrentDataSampleCount OBJECT-TYPE
      SYNTAX      Counter64
      MAX-ACCESS  read-only
      STATUS      current
      DESCRIPTION "Return the number of collected data samples in the current snapshot."
      ::= { wldfHarvesterRuntimeEntry 55  }
   
   
   wldfHarvesterRuntimeCurrentSnapshotStartTime OBJECT-TYPE
      SYNTAX      Counter64
      MAX-ACCESS  read-only
      STATUS      current
      DESCRIPTION "Return the the start time (in nanoseconds) of a taken snapshot."
      ::= { wldfHarvesterRuntimeEntry 60  }
   
   
   wldfHarvesterRuntimeCurrentSnapshotElapsedTime OBJECT-TYPE
      SYNTAX      Counter64
      MAX-ACCESS  read-only
      STATUS      current
      DESCRIPTION "Return the elapsed time (in nanoseconds) of a taken snapshot."
      ::= { wldfHarvesterRuntimeEntry 65  }
   
   
   wldfHarvesterRuntimeTotalSamplingTimeOutlierCount OBJECT-TYPE
      SYNTAX      Counter64
      MAX-ACCESS  read-only
      STATUS      current
      DESCRIPTION "The number of times withing this server session that the sampling time differed significantly enough from the average to be considered a statistical outlier.  The Harvester removes these values form the ongoing averages."
      ::= { wldfHarvesterRuntimeEntry 66  }
   
   
   wldfHarvesterRuntimeOutlierDetectionFactor OBJECT-TYPE
      SYNTAX      OCTET STRING
      MAX-ACCESS  read-only
      STATUS      current
      DESCRIPTION "The multiplicative factor used to determine a statistical outlier. If the actual sampling time exceeds this the session average multiplied by the outlier detection factor, then the sampling time is considered to be a statistical outlier."
      ::= { wldfHarvesterRuntimeEntry 67  }
   
   
   wldfHarvesterRuntimeTotalDataSampleCount OBJECT-TYPE
      SYNTAX      Counter64
      MAX-ACCESS  read-only
      STATUS      current
      DESCRIPTION "The number of configured data samples that have been collected so far in this server session."
      ::= { wldfHarvesterRuntimeEntry 68  }
   
   
   wldfHarvesterRuntimeCurrentSampleTimeAnOutlier OBJECT-TYPE
      SYNTAX      OCTET STRING
      MAX-ACCESS  read-only
      STATUS      current
      DESCRIPTION "Whether or not the sampling time for the most recent data sample differed significantly enough from the average to be considered a statistical outlier."
      ::= { wldfHarvesterRuntimeEntry 69  }
   
   
   wldfInstrumentationRuntimeTable OBJECT-TYPE
      SYNTAX      SEQUENCE OF WldfInstrumentationRuntimeEntry
      MAX-ACCESS  not-accessible
      STATUS      current
      DESCRIPTION "This table is used for monitoring the WebLogic WLDF Instrumentation framework."
      ::= { wls 484  }
      
   
   wldfInstrumentationRuntimeEntry OBJECT-TYPE
      SYNTAX      WldfInstrumentationRuntimeEntry
      MAX-ACCESS  not-accessible
      STATUS      current
      DESCRIPTION "Entry of WLDFInstrumentationRuntimeTable"
      INDEX { wldfInstrumentationRuntimeIndex}
      ::= { wldfInstrumentationRuntimeTable 1 }
      
   WldfInstrumentationRuntimeEntry ::=
      SEQUENCE
      {
         wldfInstrumentationRuntimeIndex DisplayString (SIZE (1..16)),
         wldfInstrumentationRuntimeObjectName DisplayString (SIZE (1..256)),
         wldfInstrumentationRuntimeType DisplayString (SIZE (1..64)),
         wldfInstrumentationRuntimeName DisplayString (SIZE (1..64)),
         wldfInstrumentationRuntimeParent DisplayString (SIZE (1..256)),
         wldfInstrumentationRuntimeInspectedClassesCount INTEGER,
         wldfInstrumentationRuntimeModifiedClassesCount INTEGER,
         wldfInstrumentationRuntimeMinWeavingTime Counter64,
         wldfInstrumentationRuntimeMaxWeavingTime Counter64,
         wldfInstrumentationRuntimeTotalWeavingTime Counter64,
         wldfInstrumentationRuntimeExecutionJoinpointCount INTEGER,
         wldfInstrumentationRuntimeCallJoinpointCount INTEGER,
         wldfInstrumentationRuntimeClassweaveAbortCount INTEGER
      }
      
   
   wldfInstrumentationRuntimeIndex OBJECT-TYPE
      SYNTAX      DisplayString (SIZE (1..16))
      MAX-ACCESS  read-only
      STATUS      current
      DESCRIPTION "Unique value directed from ObjectName which is used as table index"
      ::= { wldfInstrumentationRuntimeEntry 1  }
   
   
   wldfInstrumentationRuntimeObjectName OBJECT-TYPE
      SYNTAX      DisplayString (SIZE (1..256))
      MAX-ACCESS  read-only
      STATUS      current
      DESCRIPTION "JMX-standard MBean name"
      ::= { wldfInstrumentationRuntimeEntry 5  }
   
   
   wldfInstrumentationRuntimeType OBJECT-TYPE
      SYNTAX      DisplayString (SIZE (1..64))
      MAX-ACCESS  read-only
      STATUS      current
      DESCRIPTION "BEA-proprietary MBean type"
      ::= { wldfInstrumentationRuntimeEntry 10  }
   
   
   wldfInstrumentationRuntimeName OBJECT-TYPE
      SYNTAX      DisplayString (SIZE (1..64))
      MAX-ACCESS  read-only
      STATUS      current
      DESCRIPTION "BEA-proprietary MBean name"
      ::= { wldfInstrumentationRuntimeEntry 15  }
   
   
   wldfInstrumentationRuntimeParent OBJECT-TYPE
      SYNTAX      DisplayString (SIZE (1..256))
      MAX-ACCESS  read-only
      STATUS      current
      DESCRIPTION "BEA-proprietary Parent object's identification, with syntax <type>:<name>"
      ::= { wldfInstrumentationRuntimeEntry 20  }
   
   
   wldfInstrumentationRuntimeInspectedClassesCount OBJECT-TYPE
      SYNTAX      INTEGER
      MAX-ACCESS  read-only
      STATUS      current
      DESCRIPTION "Return the number of inspected classes for weaving.."
      ::= { wldfInstrumentationRuntimeEntry 25  }
   
   
   wldfInstrumentationRuntimeModifiedClassesCount OBJECT-TYPE
      SYNTAX      INTEGER
      MAX-ACCESS  read-only
      STATUS      current
      DESCRIPTION "Return the number of modified classes."
      ::= { wldfInstrumentationRuntimeEntry 30  }
   
   
   wldfInstrumentationRuntimeMinWeavingTime OBJECT-TYPE
      SYNTAX      Counter64
      MAX-ACCESS  read-only
      STATUS      current
      DESCRIPTION "Return the minimum weaving time (in nano-seconds) for a class."
      ::= { wldfInstrumentationRuntimeEntry 35  }
   
   
   wldfInstrumentationRuntimeMaxWeavingTime OBJECT-TYPE
      SYNTAX      Counter64
      MAX-ACCESS  read-only
      STATUS      current
      DESCRIPTION "Return the maximum weaving time (in nano-seconds) for a class."
      ::= { wldfInstrumentationRuntimeEntry 40  }
   
   
   wldfInstrumentationRuntimeTotalWeavingTime OBJECT-TYPE
      SYNTAX      Counter64
      MAX-ACCESS  read-only
      STATUS      current
      DESCRIPTION "Return the total weaving time (in nano-seconds) for a class."
      ::= { wldfInstrumentationRuntimeEntry 45  }
   
   
   wldfInstrumentationRuntimeExecutionJoinpointCount OBJECT-TYPE
      SYNTAX      INTEGER
      MAX-ACCESS  read-only
      STATUS      current
      DESCRIPTION "Return the number of affected EXECUTION joinpoints."
      ::= { wldfInstrumentationRuntimeEntry 50  }
   
   
   wldfInstrumentationRuntimeCallJoinpointCount OBJECT-TYPE
      SYNTAX      INTEGER
      MAX-ACCESS  read-only
      STATUS      current
      DESCRIPTION "Return the number of affected CALL joinpoints."
      ::= { wldfInstrumentationRuntimeEntry 55  }
   
   
   wldfInstrumentationRuntimeClassweaveAbortCount OBJECT-TYPE
      SYNTAX      INTEGER
      MAX-ACCESS  read-only
      STATUS      current
      DESCRIPTION "Number of classes for which the class weaving aborted with some exceptional situation"
      ::= { wldfInstrumentationRuntimeEntry 56  }
   
   
   wldfWatchNotificationRuntimeTable OBJECT-TYPE
      SYNTAX      SEQUENCE OF WldfWatchNotificationRuntimeEntry
      MAX-ACCESS  not-accessible
      STATUS      current
      DESCRIPTION "This table is used for monitoring the WebLogic WLDF WatchNotification framework."
      ::= { wls 485  }
      
   
   wldfWatchNotificationRuntimeEntry OBJECT-TYPE
      SYNTAX      WldfWatchNotificationRuntimeEntry
      MAX-ACCESS  not-accessible
      STATUS      current
      DESCRIPTION "Entry of WLDFWatchNotificationRuntimeTable"
      INDEX { wldfWatchNotificationRuntimeIndex}
      ::= { wldfWatchNotificationRuntimeTable 1 }
      
   WldfWatchNotificationRuntimeEntry ::=
      SEQUENCE
      {
         wldfWatchNotificationRuntimeIndex DisplayString (SIZE (1..16)),
         wldfWatchNotificationRuntimeObjectName DisplayString (SIZE (1..256)),
         wldfWatchNotificationRuntimeType DisplayString (SIZE (1..64)),
         wldfWatchNotificationRuntimeName DisplayString (SIZE (1..64)),
         wldfWatchNotificationRuntimeParent DisplayString (SIZE (1..256)),
         wldfWatchNotificationRuntimeTotalHarvesterEvaluationCycles Counter64,
         wldfWatchNotificationRuntimeTotalHarvesterWatchEvaluations Counter64,
         wldfWatchNotificationRuntimeTotalHarvesterWatchesTriggered Counter64,
         wldfWatchNotificationRuntimeAverageHarvesterWatchEvaluationTime Counter64,
         wldfWatchNotificationRuntimeTotalLogEvaluationCycles Counter64,
         wldfWatchNotificationRuntimeTotalLogWatchEvaluations Counter64,
         wldfWatchNotificationRuntimeTotalLogWatchesTriggered Counter64,
         wldfWatchNotificationRuntimeAverageLogWatchEvaluationTime Counter64,
         wldfWatchNotificationRuntimeTotalEventDataEvaluationCycles Counter64,
         wldfWatchNotificationRuntimeTotalEventDataWatchEvaluations Counter64,
         wldfWatchNotificationRuntimeTotalEventDataWatchesTriggered Counter64,
         wldfWatchNotificationRuntimeAverageEventDataWatchEvaluationTime Counter64,
         wldfWatchNotificationRuntimeCurrentActiveAlarmsCount INTEGER,
         wldfWatchNotificationRuntimeMaximumActiveAlarmsCount INTEGER,
         wldfWatchNotificationRuntimeTotalActiveManualResetAlarms Counter64,
         wldfWatchNotificationRuntimeTotalActiveAutomaticResetAlarms Counter64,
         wldfWatchNotificationRuntimeTotalNotificationsPerformed Counter64,
         wldfWatchNotificationRuntimeTotalDIMGNotificationsPerformed Counter64,
         wldfWatchNotificationRuntimeTotalSNMPNotificationsPerformed Counter64,
         wldfWatchNotificationRuntimeMinimumEventDataWatchEvaluationTime Counter64,
         wldfWatchNotificationRuntimeMinimumHarvesterWatchEvaluationTime Counter64,
         wldfWatchNotificationRuntimeTotalFailedJMXNotifications Counter64,
         wldfWatchNotificationRuntimeTotalJMXNotificationsPerformed Counter64,
         wldfWatchNotificationRuntimeTotalSMTPNotificationsPerformed Counter64,
         wldfWatchNotificationRuntimeTotalJMSNotificationsPerformed Counter64,
         wldfWatchNotificationRuntimeMaximumLogWatchEvaluationTime Counter64,
         wldfWatchNotificationRuntimeTotalFailedJMSNotifications Counter64,
         wldfWatchNotificationRuntimeMinimumLogWatchEvaluationTime Counter64,
         wldfWatchNotificationRuntimeMaximumHarvesterWatchEvaluationTime Counter64,
         wldfWatchNotificationRuntimeTotalFailedDIMGNotifications Counter64,
         wldfWatchNotificationRuntimeMaximumEventDataWatchEvaluationTime Counter64,
         wldfWatchNotificationRuntimeTotalFailedNotifications Counter64,
         wldfWatchNotificationRuntimeTotalFailedSMTPNotifications Counter64,
         wldfWatchNotificationRuntimeTotalFailedSNMPNotifications Counter64
      }
      
   
   wldfWatchNotificationRuntimeIndex OBJECT-TYPE
      SYNTAX      DisplayString (SIZE (1..16))
      MAX-ACCESS  read-only
      STATUS      current
      DESCRIPTION "Unique value directed from ObjectName which is used as table index"
      ::= { wldfWatchNotificationRuntimeEntry 1  }
   
   
   wldfWatchNotificationRuntimeObjectName OBJECT-TYPE
      SYNTAX      DisplayString (SIZE (1..256))
      MAX-ACCESS  read-only
      STATUS      current
      DESCRIPTION "JMX-standard MBean name"
      ::= { wldfWatchNotificationRuntimeEntry 5  }
   
   
   wldfWatchNotificationRuntimeType OBJECT-TYPE
      SYNTAX      DisplayString (SIZE (1..64))
      MAX-ACCESS  read-only
      STATUS      current
      DESCRIPTION "BEA-proprietary MBean type"
      ::= { wldfWatchNotificationRuntimeEntry 10  }
   
   
   wldfWatchNotificationRuntimeName OBJECT-TYPE
      SYNTAX      DisplayString (SIZE (1..64))
      MAX-ACCESS  read-only
      STATUS      current
      DESCRIPTION "BEA-proprietary MBean name"
      ::= { wldfWatchNotificationRuntimeEntry 15  }
   
   
   wldfWatchNotificationRuntimeParent OBJECT-TYPE
      SYNTAX      DisplayString (SIZE (1..256))
      MAX-ACCESS  read-only
      STATUS      current
      DESCRIPTION "BEA-proprietary Parent object's identification, with syntax <type>:<name>"
      ::= { wldfWatchNotificationRuntimeEntry 20  }
   
   
   wldfWatchNotificationRuntimeTotalHarvesterEvaluationCycles OBJECT-TYPE
      SYNTAX      Counter64
      MAX-ACCESS  read-only
      STATUS      current
      DESCRIPTION "Return the total number of times the Harvester has invoked the Watch and Notification component to evaluate
      Harvester watch rules."
      ::= { wldfWatchNotificationRuntimeEntry 25  }
   
   
   wldfWatchNotificationRuntimeTotalHarvesterWatchEvaluations OBJECT-TYPE
      SYNTAX      Counter64
      MAX-ACCESS  read-only
      STATUS      current
      DESCRIPTION "Return the otal number of Harvester watch rules that have been evaluated. On each cycle, the Watch and
      Notification component evaluates all of the enabled Harvester watches."
      ::= { wldfWatchNotificationRuntimeEntry 30  }
   
   
   wldfWatchNotificationRuntimeTotalHarvesterWatchesTriggered OBJECT-TYPE
      SYNTAX      Counter64
      MAX-ACCESS  read-only
      STATUS      current
      DESCRIPTION "Return the total number of Harvester watch rules that have evaluated to true and triggered."
      ::= { wldfWatchNotificationRuntimeEntry 35  }
   
   
   wldfWatchNotificationRuntimeAverageHarvesterWatchEvaluationTime OBJECT-TYPE
      SYNTAX      Counter64
      MAX-ACCESS  read-only
      STATUS      current
      DESCRIPTION "Return the average Harvester evaluation cycle time in milliseconds."
      ::= { wldfWatchNotificationRuntimeEntry 40  }
   
   
   wldfWatchNotificationRuntimeTotalLogEvaluationCycles OBJECT-TYPE
      SYNTAX      Counter64
      MAX-ACCESS  read-only
      STATUS      current
      DESCRIPTION "Return the total number of times a Log event has invoked the Watch and Notification component to
      evaluate Log watch rules."
      ::= { wldfWatchNotificationRuntimeEntry 45  }
   
   
   wldfWatchNotificationRuntimeTotalLogWatchEvaluations OBJECT-TYPE
      SYNTAX      Counter64
      MAX-ACCESS  read-only
      STATUS      current
      DESCRIPTION "Return the total number of Log watch rules that have been evaluated."
      ::= { wldfWatchNotificationRuntimeEntry 50  }
   
   
   wldfWatchNotificationRuntimeTotalLogWatchesTriggered OBJECT-TYPE
      SYNTAX      Counter64
      MAX-ACCESS  read-only
      STATUS      current
      DESCRIPTION "Return the otal number of Log watch rules that have evaluated to true and triggered."
      ::= { wldfWatchNotificationRuntimeEntry 55  }
   
   
   wldfWatchNotificationRuntimeAverageLogWatchEvaluationTime OBJECT-TYPE
      SYNTAX      Counter64
      MAX-ACCESS  read-only
      STATUS      current
      DESCRIPTION "Return the average Log evaluation cycle time in milliseconds."
      ::= { wldfWatchNotificationRuntimeEntry 60  }
   
   
   wldfWatchNotificationRuntimeTotalEventDataEvaluationCycles OBJECT-TYPE
      SYNTAX      Counter64
      MAX-ACCESS  read-only
      STATUS      current
      DESCRIPTION "Return the total number of times a Data Event has invoked the Watch and Notification component to
      evaluate Event Data watch rules."
      ::= { wldfWatchNotificationRuntimeEntry 65  }
   
   
   wldfWatchNotificationRuntimeTotalEventDataWatchEvaluations OBJECT-TYPE
      SYNTAX      Counter64
      MAX-ACCESS  read-only
      STATUS      current
      DESCRIPTION "Return the total number of Event Data watch rules that have been evaluated."
      ::= { wldfWatchNotificationRuntimeEntry 70  }
   
   
   wldfWatchNotificationRuntimeTotalEventDataWatchesTriggered OBJECT-TYPE
      SYNTAX      Counter64
      MAX-ACCESS  read-only
      STATUS      current
      DESCRIPTION "Return the otal number of Event Data watch rules that have evaluated to true and triggered."
      ::= { wldfWatchNotificationRuntimeEntry 75  }
   
   
   wldfWatchNotificationRuntimeAverageEventDataWatchEvaluationTime OBJECT-TYPE
      SYNTAX      Counter64
      MAX-ACCESS  read-only
      STATUS      current
      DESCRIPTION "Return the average Event Data evaluation cycle time in milliseconds."
      ::= { wldfWatchNotificationRuntimeEntry 80  }
   
   
   wldfWatchNotificationRuntimeCurrentActiveAlarmsCount OBJECT-TYPE
      SYNTAX      INTEGER
      MAX-ACCESS  read-only
      STATUS      current
      DESCRIPTION "Return the number of active alarms."
      ::= { wldfWatchNotificationRuntimeEntry 85  }
   
   
   wldfWatchNotificationRuntimeMaximumActiveAlarmsCount OBJECT-TYPE
      SYNTAX      INTEGER
      MAX-ACCESS  read-only
      STATUS      current
      DESCRIPTION "Return the maximum number of active alarms at any one time."
      ::= { wldfWatchNotificationRuntimeEntry 90  }
   
   
   wldfWatchNotificationRuntimeTotalActiveManualResetAlarms OBJECT-TYPE
      SYNTAX      Counter64
      MAX-ACCESS  read-only
      STATUS      current
      DESCRIPTION "Return the total number of active manually reset alarms."
      ::= { wldfWatchNotificationRuntimeEntry 95  }
   
   
   wldfWatchNotificationRuntimeTotalActiveAutomaticResetAlarms OBJECT-TYPE
      SYNTAX      Counter64
      MAX-ACCESS  read-only
      STATUS      current
      DESCRIPTION "Return the total number of active automatically reset alarms."
      ::= { wldfWatchNotificationRuntimeEntry 100  }
   
   
   wldfWatchNotificationRuntimeTotalNotificationsPerformed OBJECT-TYPE
      SYNTAX      Counter64
      MAX-ACCESS  read-only
      STATUS      current
      DESCRIPTION "Return the total number of notifications performed."
      ::= { wldfWatchNotificationRuntimeEntry 105  }
   
   
   wldfWatchNotificationRuntimeTotalDIMGNotificationsPerformed OBJECT-TYPE
      SYNTAX      Counter64
      MAX-ACCESS  read-only
      STATUS      current
      DESCRIPTION "The total number of Diagnostic Image notifications fired.  Diagnostic Image files are not true notifications, but this records the number of image captures requested by the watch component."
      ::= { wldfWatchNotificationRuntimeEntry 106  }
   
   
   wldfWatchNotificationRuntimeTotalSNMPNotificationsPerformed OBJECT-TYPE
      SYNTAX      Counter64
      MAX-ACCESS  read-only
      STATUS      current
      DESCRIPTION "The total number of SNMP notifications successfully fired."
      ::= { wldfWatchNotificationRuntimeEntry 107  }
   
   
   wldfWatchNotificationRuntimeMinimumEventDataWatchEvaluationTime OBJECT-TYPE
      SYNTAX      Counter64
      MAX-ACCESS  read-only
      STATUS      current
      DESCRIPTION "The minimum time spent evaluating Log watches."
      ::= { wldfWatchNotificationRuntimeEntry 108  }
   
   
   wldfWatchNotificationRuntimeMinimumHarvesterWatchEvaluationTime OBJECT-TYPE
      SYNTAX      Counter64
      MAX-ACCESS  read-only
      STATUS      current
      DESCRIPTION "The minimum time spent evaluating Harvester watches."
      ::= { wldfWatchNotificationRuntimeEntry 109  }
   
   
   wldfWatchNotificationRuntimeTotalFailedJMXNotifications OBJECT-TYPE
      SYNTAX      Counter64
      MAX-ACCESS  read-only
      STATUS      current
      DESCRIPTION "The total number of failed JMX notification attempts."
      ::= { wldfWatchNotificationRuntimeEntry 110  }
   
   
   wldfWatchNotificationRuntimeTotalJMXNotificationsPerformed OBJECT-TYPE
      SYNTAX      Counter64
      MAX-ACCESS  read-only
      STATUS      current
      DESCRIPTION "The total number of JMX notifications successfully fired."
      ::= { wldfWatchNotificationRuntimeEntry 111  }
   
   
   wldfWatchNotificationRuntimeTotalSMTPNotificationsPerformed OBJECT-TYPE
      SYNTAX      Counter64
      MAX-ACCESS  read-only
      STATUS      current
      DESCRIPTION "The total number of SMTP notifications successfully fired."
      ::= { wldfWatchNotificationRuntimeEntry 112  }
   
   
   wldfWatchNotificationRuntimeTotalJMSNotificationsPerformed OBJECT-TYPE
      SYNTAX      Counter64
      MAX-ACCESS  read-only
      STATUS      current
      DESCRIPTION "The total number of JMS notifications successfully fired."
      ::= { wldfWatchNotificationRuntimeEntry 113  }
   
   
   wldfWatchNotificationRuntimeMaximumLogWatchEvaluationTime OBJECT-TYPE
      SYNTAX      Counter64
      MAX-ACCESS  read-only
      STATUS      current
      DESCRIPTION "The maximum time spent evaluating Log watches."
      ::= { wldfWatchNotificationRuntimeEntry 114  }
   
   
   wldfWatchNotificationRuntimeTotalFailedJMSNotifications OBJECT-TYPE
      SYNTAX      Counter64
      MAX-ACCESS  read-only
      STATUS      current
      DESCRIPTION "The total number of failed JMS notification attempts."
      ::= { wldfWatchNotificationRuntimeEntry 115  }
   
   
   wldfWatchNotificationRuntimeMinimumLogWatchEvaluationTime OBJECT-TYPE
      SYNTAX      Counter64
      MAX-ACCESS  read-only
      STATUS      current
      DESCRIPTION "The minimum time spent evaluating Log watches."
      ::= { wldfWatchNotificationRuntimeEntry 116  }
   
   
   wldfWatchNotificationRuntimeMaximumHarvesterWatchEvaluationTime OBJECT-TYPE
      SYNTAX      Counter64
      MAX-ACCESS  read-only
      STATUS      current
      DESCRIPTION "The maximum time spent evaluating Harvester watches."
      ::= { wldfWatchNotificationRuntimeEntry 117  }
   
   
   wldfWatchNotificationRuntimeTotalFailedDIMGNotifications OBJECT-TYPE
      SYNTAX      Counter64
      MAX-ACCESS  read-only
      STATUS      current
      DESCRIPTION "The total number of failed Diagnostic Image notification requests."
      ::= { wldfWatchNotificationRuntimeEntry 118  }
   
   
   wldfWatchNotificationRuntimeMaximumEventDataWatchEvaluationTime OBJECT-TYPE
      SYNTAX      Counter64
      MAX-ACCESS  read-only
      STATUS      current
      DESCRIPTION "The maximum time spent evaluating EventData watches."
      ::= { wldfWatchNotificationRuntimeEntry 119  }
   
   
   wldfWatchNotificationRuntimeTotalFailedNotifications OBJECT-TYPE
      SYNTAX      Counter64
      MAX-ACCESS  read-only
      STATUS      current
      DESCRIPTION "The total number of failed notification requests. that failed."
      ::= { wldfWatchNotificationRuntimeEntry 120  }
   
   
   wldfWatchNotificationRuntimeTotalFailedSMTPNotifications OBJECT-TYPE
      SYNTAX      Counter64
      MAX-ACCESS  read-only
      STATUS      current
      DESCRIPTION "The total number of failed SMTP notification attempts."
      ::= { wldfWatchNotificationRuntimeEntry 121  }
   
   
   wldfWatchNotificationRuntimeTotalFailedSNMPNotifications OBJECT-TYPE
      SYNTAX      Counter64
      MAX-ACCESS  read-only
      STATUS      current
      DESCRIPTION "The total number of failed SNMP notification attempts."
      ::= { wldfWatchNotificationRuntimeEntry 122  }
   
   
   applicationTable OBJECT-TYPE
      SYNTAX      SEQUENCE OF ApplicationEntry
      MAX-ACCESS  not-accessible
      STATUS      current
      DESCRIPTION "An application represents a J2EE application contained in a EAR
      file or EAR directory. The EAR file contains a set of components
      such as WAR, EJB and JMS JAR components, each of which can be
      deployed on one or more Roles. A Role is a set of server, with a
      server serving more than one Role. For example a Role may be the
      whole Domain, a set of servers that implement the role, or a
      specific server. These components might include EJBs, servlets, JMS
      destinations, WebLogic startup and shutdown classes."
      ::= { wls 500  }
      
   
   applicationEntry OBJECT-TYPE
      SYNTAX      ApplicationEntry
      MAX-ACCESS  not-accessible
      STATUS      current
      DESCRIPTION "Entry of applicationTable"
      INDEX { applicationIndex}
      ::= { applicationTable 1 }
      
   ApplicationEntry ::=
      SEQUENCE
      {
         applicationIndex     DisplayString (SIZE (1..16)),
         applicationObjectName DisplayString (SIZE (1..256)),
         applicationType      DisplayString (SIZE (1..64)),
         applicationName      DisplayString (SIZE (1..64)),
         applicationParent    DisplayString (SIZE (1..256)),
         applicationDeployed  INTEGER
                     {
                        true(1),
                        false(2)
                     }
         ,
         applicationComponents DisplayString (SIZE (1..25)),
         applicationApplicationDescriptor DisplayString (SIZE (1..256)),
         applicationPath      DisplayString (SIZE (1..1024)),
         applicationAltDescriptorPath DisplayString,
         applicationAltWLSDescriptorPath DisplayString,
         applicationDeploymentTimeout INTEGER,
         applicationDeploymentType DisplayString,
         applicationLoadOrder INTEGER,
         applicationStagingMode DisplayString,
         applicationStagingPath DisplayString,
         applicationTwoPhase  INTEGER
      }
      
   
   applicationIndex OBJECT-TYPE
      SYNTAX      DisplayString (SIZE (1..16))
      MAX-ACCESS  read-only
      STATUS      current
      DESCRIPTION "Unique value directed from ObjectName which is used as table index"
      ::= { applicationEntry 1  }
   
   
   applicationObjectName OBJECT-TYPE
      SYNTAX      DisplayString (SIZE (1..256))
      MAX-ACCESS  read-only
      STATUS      current
      DESCRIPTION "JMX-standard MBean name"
      ::= { applicationEntry 5  }
   
   
   applicationType OBJECT-TYPE
      SYNTAX      DisplayString (SIZE (1..64))
      MAX-ACCESS  read-only
      STATUS      current
      DESCRIPTION "BEA-proprietary MBean type"
      ::= { applicationEntry 10  }
   
   
   applicationName OBJECT-TYPE
      SYNTAX      DisplayString (SIZE (1..64))
      MAX-ACCESS  read-only
      STATUS      current
      DESCRIPTION "BEA-proprietary MBean name"
      ::= { applicationEntry 15  }
   
   
   applicationParent OBJECT-TYPE
      SYNTAX      DisplayString (SIZE (1..256))
      MAX-ACCESS  read-only
      STATUS      current
      DESCRIPTION "BEA-proprietary Parent object's identification, with syntax
      <type>:<name>"
      ::= { applicationEntry 20  }
   
   
   applicationDeployed OBJECT-TYPE
      SYNTAX      INTEGER
                  {
                     true(1),
                     false(2)
                  }
      
      MAX-ACCESS  read-only
      STATUS      current
      DESCRIPTION "A boolean value (true Or false). Returns whether or not this application is deployed."
      ::= { applicationEntry 30  }
   
   
   applicationComponents OBJECT-TYPE
      SYNTAX      DisplayString (SIZE (1..25))
      MAX-ACCESS  read-only
      STATUS      current
      DESCRIPTION "The components that make up this application."
      ::= { applicationEntry 35  }
   
   
   applicationApplicationDescriptor OBJECT-TYPE
      SYNTAX      DisplayString (SIZE (1..256))
      MAX-ACCESS  read-only
      STATUS      current
      DESCRIPTION "The descriptor mbean for the application."
      ::= { applicationEntry 40  }
   
   
   applicationPath OBJECT-TYPE
      SYNTAX      DisplayString (SIZE (1..1024))
      MAX-ACCESS  read-only
      STATUS      current
      DESCRIPTION "The path pointing to the application's EAR file. 
      The file is relative to the Admin Server's file system."
      ::= { applicationEntry 45  }
   
   
   applicationAltDescriptorPath OBJECT-TYPE
      SYNTAX      DisplayString
      MAX-ACCESS  read-only
      STATUS      current
      DESCRIPTION "Defines a path on the filesystem for the application descriptor for this application"
      ::= { applicationEntry 46  }
   
   
   applicationAltWLSDescriptorPath OBJECT-TYPE
      SYNTAX      DisplayString
      MAX-ACCESS  read-only
      STATUS      current
      DESCRIPTION "Defines a path on the filesystem for the WLS-specific application descriptor for this application."
      ::= { applicationEntry 47  }
   
   
   applicationDeploymentTimeout OBJECT-TYPE
      SYNTAX      INTEGER
      MAX-ACCESS  read-only
      STATUS      current
      DESCRIPTION "Milliseconds granted for a cluster deployment task on this application."
      ::= { applicationEntry 48  }
   
   
   applicationDeploymentType OBJECT-TYPE
      SYNTAX      DisplayString
      MAX-ACCESS  read-only
      STATUS      current
      DESCRIPTION "Specifies the category of this application."
      ::= { applicationEntry 49  }
   
   
   applicationLoadOrder OBJECT-TYPE
      SYNTAX      INTEGER
      MAX-ACCESS  read-only
      STATUS      current
      DESCRIPTION "Specifies the order applications are loaded at server startup."
      ::= { applicationEntry 50  }
   
   
   applicationStagingMode OBJECT-TYPE
      SYNTAX      DisplayString
      MAX-ACCESS  read-only
      STATUS      current
      DESCRIPTION "Indicates whether this application is being staged."
      ::= { applicationEntry 51  }
   
   
   applicationStagingPath OBJECT-TYPE
      SYNTAX      DisplayString
      MAX-ACCESS  read-only
      STATUS      current
      DESCRIPTION "Identifies the directory path on the managed server relative to the server's StagingDirectoryName."
      ::= { applicationEntry 52  }
   
   
   applicationTwoPhase OBJECT-TYPE
      SYNTAX      INTEGER
      MAX-ACCESS  read-only
      STATUS      current
      DESCRIPTION "Indicates whether this application is deployed using the 2 phase deployment."
      ::= { applicationEntry 53  }
   
   
   bridgeDestinationCommonTable OBJECT-TYPE
      SYNTAX      SEQUENCE OF BridgeDestinationCommonEntry
      MAX-ACCESS  not-accessible
      STATUS      current
      DESCRIPTION "."
      ::= { wls 505  }
      
   
   bridgeDestinationCommonEntry OBJECT-TYPE
      SYNTAX      BridgeDestinationCommonEntry
      MAX-ACCESS  not-accessible
      STATUS      current
      DESCRIPTION "Entry of bridgeDestinationCommonTable"
      INDEX { bridgeDestinationCommonIndex}
      ::= { bridgeDestinationCommonTable 1 }
      
   BridgeDestinationCommonEntry ::=
      SEQUENCE
      {
         bridgeDestinationCommonIndex DisplayString (SIZE (1..16)),
         bridgeDestinationCommonObjectName DisplayString (SIZE (1..256)),
         bridgeDestinationCommonType DisplayString (SIZE (1..64)),
         bridgeDestinationCommonName DisplayString (SIZE (1..64)),
         bridgeDestinationCommonParent DisplayString (SIZE (1..256)),
         bridgeDestinationCommonAdapterJNDIName DisplayString,
         bridgeDestinationCommonClasspath DisplayString,
         bridgeDestinationCommonUserName DisplayString
      }
      
   
   bridgeDestinationCommonIndex OBJECT-TYPE
      SYNTAX      DisplayString (SIZE (1..16))
      MAX-ACCESS  read-only
      STATUS      current
      DESCRIPTION "Unique value directed from ObjectName which is used as table index"
      ::= { bridgeDestinationCommonEntry 1  }
   
   
   bridgeDestinationCommonObjectName OBJECT-TYPE
      SYNTAX      DisplayString (SIZE (1..256))
      MAX-ACCESS  read-only
      STATUS      current
      DESCRIPTION "JMX-standard MBean name"
      ::= { bridgeDestinationCommonEntry 5  }
   
   
   bridgeDestinationCommonType OBJECT-TYPE
      SYNTAX      DisplayString (SIZE (1..64))
      MAX-ACCESS  read-only
      STATUS      current
      DESCRIPTION "BEA-proprietary MBean type"
      ::= { bridgeDestinationCommonEntry 10  }
   
   
   bridgeDestinationCommonName OBJECT-TYPE
      SYNTAX      DisplayString (SIZE (1..64))
      MAX-ACCESS  read-only
      STATUS      current
      DESCRIPTION "BEA-proprietary MBean name"
      ::= { bridgeDestinationCommonEntry 15  }
   
   
   bridgeDestinationCommonParent OBJECT-TYPE
      SYNTAX      DisplayString (SIZE (1..256))
      MAX-ACCESS  read-only
      STATUS      current
      DESCRIPTION "BEA-proprietary Parent object's identification, with syntax
      <type>:<name>"
      ::= { bridgeDestinationCommonEntry 20  }
   
   
   bridgeDestinationCommonAdapterJNDIName OBJECT-TYPE
      SYNTAX      DisplayString
      MAX-ACCESS  read-only
      STATUS      current
      DESCRIPTION "Generated Object."
      ::= { bridgeDestinationCommonEntry 21  }
   
   
   bridgeDestinationCommonClasspath OBJECT-TYPE
      SYNTAX      DisplayString
      MAX-ACCESS  read-only
      STATUS      current
      DESCRIPTION "Generated Object."
      ::= { bridgeDestinationCommonEntry 22  }
   
   
   bridgeDestinationCommonUserName OBJECT-TYPE
      SYNTAX      DisplayString
      MAX-ACCESS  read-only
      STATUS      current
      DESCRIPTION "Generated Object."
      ::= { bridgeDestinationCommonEntry 23  }
   
   
   clusterTable OBJECT-TYPE
      SYNTAX      SEQUENCE OF ClusterEntry
      MAX-ACCESS  not-accessible
      STATUS      current
      DESCRIPTION "This table represents a cluster in the domain. Servers join a
      cluster by calling ServerMBean.setCluster with the logical name of
      the cluster. A configuration may define zero or more clusters. They
      may be looked up by logical name."
      ::= { wls 510  }
      
   
   clusterEntry OBJECT-TYPE
      SYNTAX      ClusterEntry
      MAX-ACCESS  not-accessible
      STATUS      current
      DESCRIPTION "Entry of clusterTable"
      INDEX { clusterIndex}
      ::= { clusterTable 1 }
      
   ClusterEntry ::=
      SEQUENCE
      {
         clusterIndex         DisplayString (SIZE (1..16)),
         clusterObjectName    DisplayString (SIZE (1..256)),
         clusterType          DisplayString (SIZE (1..64)),
         clusterName          DisplayString (SIZE (1..64)),
         clusterParent        DisplayString (SIZE (1..256)),
         clusterServers       DisplayString (SIZE (1..2048)),
         clusterClusterAddress DisplayString (SIZE (1..256)),
         clusterMulticastAddress DisplayString (SIZE (1..256)),
         clusterMulticastTTL  INTEGER,
         clusterMulticastSendDelay INTEGER,
         clusterDefaultLoadAlgorithm DisplayString (SIZE (1..32)),
         clusterServiceAgeThresholdSeconds INTEGER,
         clusterMulticastBufferSize INTEGER,
         clusterMulticastPort INTEGER,
         clusterClientCertProxyEnabled INTEGER,
         clusterWeblogicPluginEnabled INTEGER,
         clusterHealthCheckIntervalMillis INTEGER,
         clusterHealthCheckPeriodsUntilFencing INTEGER,
         clusterSessionFlushInterval INTEGER,
         clusterAdditionalAutoMigrationAttempts INTEGER,
         clusterRemoteClusterAddress OCTET STRING,
         clusterFrontendHTTPPort INTEGER,
         clusterMulticastDataEncryption OCTET STRING,
         clusterSecureReplicationEnabled OCTET STRING,
         clusterJobSchedulerTableName OCTET STRING,
         clusterReplicationTimeoutEnabled OCTET STRING,
         clusterAsyncSessionQueueTimeout INTEGER,
         clusterInterClusterCommLinkHealthCheckInterval INTEGER,
         clusterSessionFlushThreshold INTEGER,
         clusterClusterType   OCTET STRING,
         clusterGreedySessionFlushInterval INTEGER,
         clusterPersistSessionsOnShutdown OCTET STRING,
         clusterMigrationBasis OCTET STRING,
         clusterHttpTraceSupportEnabled OCTET STRING,
         clusterReplicationChannel OCTET STRING,
         clusterFencingGracePeriodMillis INTEGER,
         clusterFrontendHost  OCTET STRING,
         clusterMemberWarmupTimeoutSeconds INTEGER,
         clusterFrontendHTTPSPort INTEGER,
         clusterClusterBroadcastChannel OCTET STRING,
         clusterIdlePeriodsUntilTimeout INTEGER,
         clusterNumberOfServersInClusterAddress INTEGER,
         clusterClusterMessagingMode OCTET STRING,
         clusterMillisToSleepBetweenAutoMigrationAttempts Counter64,
         clusterAutoMigrationTableName OCTET STRING,
         clusterWANSessionPersistenceTableName OCTET STRING
      }
      
   
   clusterIndex OBJECT-TYPE
      SYNTAX      DisplayString (SIZE (1..16))
      MAX-ACCESS  read-only
      STATUS      current
      DESCRIPTION "Unique value directed from ObjectName which is used as table index"
      ::= { clusterEntry 1  }
   
   
   clusterObjectName OBJECT-TYPE
      SYNTAX      DisplayString (SIZE (1..256))
      MAX-ACCESS  read-only
      STATUS      current
      DESCRIPTION "JMX-standard MBean name"
      ::= { clusterEntry 5  }
   
   
   clusterType OBJECT-TYPE
      SYNTAX      DisplayString (SIZE (1..64))
      MAX-ACCESS  read-only
      STATUS      current
      DESCRIPTION "BEA-proprietary MBean type"
      ::= { clusterEntry 10  }
   
   
   clusterName OBJECT-TYPE
      SYNTAX      DisplayString (SIZE (1..64))
      MAX-ACCESS  read-only
      STATUS      current
      DESCRIPTION "BEA-proprietary MBean name"
      ::= { clusterEntry 15  }
   
   
   clusterParent OBJECT-TYPE
      SYNTAX      DisplayString (SIZE (1..256))
      MAX-ACCESS  read-only
      STATUS      current
      DESCRIPTION "BEA-proprietary Parent object's identification, with syntax
      <type>:<name>"
      ::= { clusterEntry 20  }
   
   
   clusterServers OBJECT-TYPE
      SYNTAX      DisplayString (SIZE (1..2048))
      MAX-ACCESS  read-only
      STATUS      current
      DESCRIPTION "The servers which have declared membership in this cluster."
      ::= { clusterEntry 25  }
   
   
   clusterClusterAddress OBJECT-TYPE
      SYNTAX      DisplayString (SIZE (1..256))
      MAX-ACCESS  read-only
      STATUS      current
      DESCRIPTION "The address to be used by clients to connect to this
      cluster. This address may be either a DNS host name that maps to
      multiple IP addresses or a comma separated list of single address
      host names or IP addresses."
      ::= { clusterEntry 30  }
   
   
   clusterMulticastAddress OBJECT-TYPE
      SYNTAX      DisplayString (SIZE (1..256))
      MAX-ACCESS  read-only
      STATUS      current
      DESCRIPTION "The multicast address used by cluster members to communicate with
      each other."
      ::= { clusterEntry 35  }
   
   
   clusterMulticastTTL OBJECT-TYPE
      SYNTAX      INTEGER
      MAX-ACCESS  read-only
      STATUS      current
      DESCRIPTION "The number of network hops that a cluster multicast
      message is allowed to travel. 1 restricts the cluster to one
      subnet. The minimum value is 1 and the maximum value is 255,
      inclusive."
      ::= { clusterEntry 40  }
   
   
   clusterMulticastSendDelay OBJECT-TYPE
      SYNTAX      INTEGER
      MAX-ACCESS  read-only
      STATUS      current
      DESCRIPTION "The number of milliseconds to delay sending message fragments
      over multicast in order to avoid OS-level buffer overflow. The default
      should be fine in most cases, but it may need to be tuned for odd
      configurations."
      ::= { clusterEntry 45  }
   
   
   clusterDefaultLoadAlgorithm OBJECT-TYPE
      SYNTAX      DisplayString (SIZE (1..32))
      MAX-ACCESS  read-only
      STATUS      current
      DESCRIPTION "The algorithm to be used for load-balancing between
      replicated services if none is specified for a particular
      service."
      ::= { clusterEntry 50  }
   
   
   clusterServiceAgeThresholdSeconds OBJECT-TYPE
      SYNTAX      INTEGER
      MAX-ACCESS  read-only
      STATUS      current
      DESCRIPTION "he number of seconds by which the age of two conflicting
      services must differ before one is considered older than the
      other."
      ::= { clusterEntry 55  }
   
   
   clusterMulticastBufferSize OBJECT-TYPE
      SYNTAX      INTEGER
      MAX-ACCESS  read-only
      STATUS      current
      DESCRIPTION "Returns the multicast socket send/receive buffer size."
      ::= { clusterEntry 56  }
   
   
   clusterMulticastPort OBJECT-TYPE
      SYNTAX      INTEGER
      MAX-ACCESS  read-only
      STATUS      current
      DESCRIPTION "Defines the multicast port used by cluster members to communicate with each other."
      ::= { clusterEntry 57  }
   
   
   clusterClientCertProxyEnabled OBJECT-TYPE
      SYNTAX      INTEGER
      MAX-ACCESS  read-only
      STATUS      current
      DESCRIPTION "Gets the clientCertProxyEnabled attribute of the ClusterMBean object"
      ::= { clusterEntry 58  }
   
   
   clusterWeblogicPluginEnabled OBJECT-TYPE
      SYNTAX      INTEGER
      MAX-ACCESS  read-only
      STATUS      current
      DESCRIPTION "Gets the weblogicPluginEnabled attribute of the ClusterMBean object"
      ::= { clusterEntry 59  }
   
   
   clusterHealthCheckIntervalMillis OBJECT-TYPE
      SYNTAX      INTEGER
      MAX-ACCESS  read-only
      STATUS      current
      DESCRIPTION "Interval in milliseconds at which Migratable Servers and Cluster Masters prove their liveness via the database."
      ::= { clusterEntry 60  }
   
   
   clusterHealthCheckPeriodsUntilFencing OBJECT-TYPE
      SYNTAX      INTEGER
      MAX-ACCESS  read-only
      STATUS      current
      DESCRIPTION "Maximum number of periods that a cluster member will wait before timing out a Cluster Master and also the maximum number of periods the Cluster Master will wait before timing out a Migratable Server."
      ::= { clusterEntry 61  }
   
   
   clusterSessionFlushInterval OBJECT-TYPE
      SYNTAX      INTEGER
      MAX-ACCESS  read-only
      STATUS      current
      DESCRIPTION "Interval in seconds until HTTP Sessions are periodically flushed to the backup cluster to dump session state on disk."
      ::= { clusterEntry 62  }
   
   
   clusterAdditionalAutoMigrationAttempts OBJECT-TYPE
      SYNTAX      INTEGER
      MAX-ACCESS  read-only
      STATUS      current
      DESCRIPTION "A migratable server could fail to come up on every possible configured machine. This attribute controls how many further attempts, after the first one, should be tried.  Note that each attempt specified here indicates another full circut of migrations amongst all the configured machines. So for a 3-server cluster, and the default value of 3, a total of 9 migrations will be attempted.  If it is set to -1, migrations will go on forever until the server starts."
      ::= { clusterEntry 63  }
   
   
   clusterRemoteClusterAddress OBJECT-TYPE
      SYNTAX      OCTET STRING
      MAX-ACCESS  read-only
      STATUS      current
      DESCRIPTION "Set the foreign cluster. Cluster infrastructure uses this address to connect to foreign cluster for HTTP Session WAN/MAN failover."
      ::= { clusterEntry 64  }
   
   
   clusterFrontendHTTPPort OBJECT-TYPE
      SYNTAX      INTEGER
      MAX-ACCESS  read-only
      STATUS      current
      DESCRIPTION "The name of the HTTP port to which all redirected URLs will be sent.  Sets the FrontendHTTPPort for the default webserver (not virtual hosts) for all the servers in the cluster. Provides a method to ensure that the webapp will always have the correct PORT information, even when the request is coming through a firewall or a proxy. If this parameter is configured, the HOST header will be ignored and the information in this parameter will be used in its place, when constructing the absolute urls for redirects."
      ::= { clusterEntry 65  }
   
   
   clusterMulticastDataEncryption OBJECT-TYPE
      SYNTAX      OCTET STRING
      MAX-ACCESS  read-only
      STATUS      current
      DESCRIPTION "Enables multicast data to be incrypted. Only the multicast data is encrypted. Multicast header information is not encrypted."
      ::= { clusterEntry 66  }
   
   
   clusterSecureReplicationEnabled OBJECT-TYPE
      SYNTAX      OCTET STRING
      MAX-ACCESS  read-only
      STATUS      current
      DESCRIPTION "Servers in a cluster replicates session data. If replication channel is defined then the session data will be sent using the replication channel protocol and secured replication settings will be ignored. If no replication channel is defined and secured replication is enabled then session data for in-memory replication will be sent over SSL using default secured channel. However, this added security for replication traffic comes with a significant cluster performance degradation. It should only be enabled if security is of greater concern than the performance degradation."
      ::= { clusterEntry 67  }
   
   
   clusterJobSchedulerTableName OBJECT-TYPE
      SYNTAX      OCTET STRING
      MAX-ACCESS  read-only
      STATUS      current
      DESCRIPTION "The table name to use for storing timers active with the job scheduler"
      ::= { clusterEntry 68  }
   
   
   clusterReplicationTimeoutEnabled OBJECT-TYPE
      SYNTAX      OCTET STRING
      MAX-ACCESS  read-only
      STATUS      current
      DESCRIPTION "Indicates if timeout should be applied to session replication calls."
      ::= { clusterEntry 69  }
   
   
   clusterAsyncSessionQueueTimeout OBJECT-TYPE
      SYNTAX      INTEGER
      MAX-ACCESS  read-only
      STATUS      current
      DESCRIPTION "Interval in seconds until the producer thread will wait for the AsyncSessionQueue to become unblocked.  Should be similar to the RequestTimeOut as that will determine the longest that the queue should remain full."
      ::= { clusterEntry 70  }
   
   
   clusterInterClusterCommLinkHealthCheckInterval OBJECT-TYPE
      SYNTAX      INTEGER
      MAX-ACCESS  read-only
      STATUS      current
      DESCRIPTION "If the cluster link between two clusters goes down, a trigger will run to periodically to see if the link is restored. The duration is specified in milliseconds."
      ::= { clusterEntry 71  }
   
   
   clusterSessionFlushThreshold OBJECT-TYPE
      SYNTAX      INTEGER
      MAX-ACCESS  read-only
      STATUS      current
      DESCRIPTION "When number of sessions to be flushed reaches this threshold limit, sessions will be flushed to the backup cluster before the flush interval. This helps the server to flush sessions faster under load."
      ::= { clusterEntry 72  }
   
   
   clusterClusterType OBJECT-TYPE
      SYNTAX      OCTET STRING
      MAX-ACCESS  read-only
      STATUS      current
      DESCRIPTION "Optimizes cross-cluster replication for the type of network that servers in the clusters use for administrative communication.  To enhance the reliability of HTTP sessions, you can configure servers in one cluster to replicate the session data to servers in a different cluster. In such an environment, configure the clusters to be one of the following types:   man if the clustered servers can send their data through a metro area network (man) in which latency is negligible. With this ClusterType value, servers replicate session state synchronously and in memory only. For example, when serverA in cluster1 starts an HTTP session, its backup server, serverB in cluster2, immediately replicates this session in memory to Server B.   wan if the clusters are far apart or send their data through a wide area network (wan) that experiences significant network latency. With this ClusterType value, a server replicates session state synchronously to the backup server in the same cluster and asynchronously to a server in the remote cluster. For example, when serverA in cluster1 starts an HTTP session, it sends the data to serverB in cluster1 and then asynchronously sends data to serverX in cluster 2. ServerX will persist the session state in the database.  If you persist session data in a replicating database, and if you prefer to use the database to replicate the data instead of WebLogic Server, choose a cluster type of wan and leave the remote cluster address undefined. WebLogic Server saves the session data to the local database and assumes that the database replicates data as needed."
      ::= { clusterEntry 73  }
   
   
   clusterGreedySessionFlushInterval OBJECT-TYPE
      SYNTAX      INTEGER
      MAX-ACCESS  read-only
      STATUS      current
      DESCRIPTION "Interval in seconds until HTTP Sessions are periodically flushed to secondary server."
      ::= { clusterEntry 74  }
   
   
   clusterPersistSessionsOnShutdown OBJECT-TYPE
      SYNTAX      OCTET STRING
      MAX-ACCESS  read-only
      STATUS      current
      DESCRIPTION "When shutting down servers, sessions are not updated. If the primary and secondary servers of a session are shut down with no session updates, the session will be lost. Turning on PersistSessionsOnShutdown will save any active sessions to the database specified in {@link ClusterMBean#getDataSourceForSessionPersistence()} when a server is shutdown. The sessions will not be written at any other time. (For example, they are not saved via this mechanism if there is a server crash.)  This attribute is applicable both to session persistence on server shutdown or session persistence across a WAN.  Rolling upgrade can potential have a bad interaction with traditional in-memory session replication.  As managed servers are shutdown and upgraded, in-memory servlet sessions will be lost if both primary and secondary are rebooted before a new request arrives for the session."
      ::= { clusterEntry 75  }
   
   
   clusterMigrationBasis OBJECT-TYPE
      SYNTAX      OCTET STRING
      MAX-ACCESS  read-only
      STATUS      current
      DESCRIPTION "Controls the mechanism used for server migration."
      ::= { clusterEntry 76  }
   
   
   clusterHttpTraceSupportEnabled OBJECT-TYPE
      SYNTAX      OCTET STRING
      MAX-ACCESS  read-only
      STATUS      current
      DESCRIPTION "Returns the value of HttpTraceSupportEnabled."
      ::= { clusterEntry 77  }
   
   
   clusterReplicationChannel OBJECT-TYPE
      SYNTAX      OCTET STRING
      MAX-ACCESS  read-only
      STATUS      current
      DESCRIPTION "The channel name to be used for replication traffic. Cluster infrastructure uses this channel to send updates for HTTP sessions and stateful session beans. If none is set then the default channel will be used.  In order for this feature to work, the named channel must exist on all members of the cluster and must be configured to use the same protocol. It is valid for the selected channel to be configured to use a secure protocol."
      ::= { clusterEntry 78  }
   
   
   clusterFencingGracePeriodMillis OBJECT-TYPE
      SYNTAX      INTEGER
      MAX-ACCESS  read-only
      STATUS      current
      DESCRIPTION "During automatic migration, if the Cluster Master determines a server to be dead, it waits for this period of time (in milliseconds) before the Cluster Master migrates the service to another server in the cluster."
      ::= { clusterEntry 79  }
   
   
   clusterFrontendHost OBJECT-TYPE
      SYNTAX      OCTET STRING
      MAX-ACCESS  read-only
      STATUS      current
      DESCRIPTION "The name of the host to which all redirected URLs will be sent.  Sets the HTTP FrontendHost for the default webserver (not virtual hosts) for all the servers in the cluster. Provides a method to ensure that the webapp will always have the correct HOST information, even when the request is coming through a firewall or a proxy. If this parameter is configured, the HOST header will be ignored and the information in this parameter will be used in its place, when constructing the absolute urls for redirects."
      ::= { clusterEntry 80  }
   
   
   clusterMemberWarmupTimeoutSeconds OBJECT-TYPE
      SYNTAX      INTEGER
      MAX-ACCESS  read-only
      STATUS      current
      DESCRIPTION "Maximum number of seconds that a cluster member will wait to discover and synchronize with other servers in the cluster. Normally, the member will be able to sync in 30 seconds. If the value of this attribute is higher, that does not necessarily mean that it will take longer for the member to warmup. Instead it defines an upper bound on the time that a server will wait to sync with the servers that it has discoverred. If the value is set 0, servers will not attempt to discover other running server in the cluster during server initialization"
      ::= { clusterEntry 81  }
   
   
   clusterFrontendHTTPSPort OBJECT-TYPE
      SYNTAX      INTEGER
      MAX-ACCESS  read-only
      STATUS      current
      DESCRIPTION "The name of the secure HTTP port to which all redirected URLs will be sent.  Sets the FrontendHTTPSPort for the default webserver (not virtual hosts) for all the servers in the cluster. Provides a method to ensure that the webapp will always have the correct PORT information, even when the request is coming through a firewall or a proxy. If this parameter is configured, the HOST header will be ignored and the information in this parameter will be used in its place, when constructing the absolute urls for redirects."
      ::= { clusterEntry 82  }
   
   
   clusterClusterBroadcastChannel OBJECT-TYPE
      SYNTAX      OCTET STRING
      MAX-ACCESS  read-only
      STATUS      current
      DESCRIPTION "Specifies the channel used to handle communications within a cluster. If no channel is specified the default channel is used. ClusterBroadcastChannel is only are supported if the unicast messaging type is used."
      ::= { clusterEntry 83  }
   
   
   clusterIdlePeriodsUntilTimeout OBJECT-TYPE
      SYNTAX      INTEGER
      MAX-ACCESS  read-only
      STATUS      current
      DESCRIPTION "Maximum number of periods that a cluster member will wait before timing out a member of a cluster.  Maximum number of periods that a cluster member will wait before timing out a member of a cluster."
      ::= { clusterEntry 84  }
   
   
   clusterNumberOfServersInClusterAddress OBJECT-TYPE
      SYNTAX      INTEGER
      MAX-ACCESS  read-only
      STATUS      current
      DESCRIPTION "Number of servers to be listed from this cluster when generating a cluster address automatically. This setting has no effect if Cluster Address is explicitly set."
      ::= { clusterEntry 85  }
   
   
   clusterClusterMessagingMode OBJECT-TYPE
      SYNTAX      OCTET STRING
      MAX-ACCESS  read-only
      STATUS      current
      DESCRIPTION "Specifies the messaging type used in the cluster. Multicast messaging, the default, is provided for backwards compatibility. Unicast message is recommended for new clusters."
      ::= { clusterEntry 86  }
   
   
   clusterMillisToSleepBetweenAutoMigrationAttempts OBJECT-TYPE
      SYNTAX      Counter64
      MAX-ACCESS  read-only
      STATUS      current
      DESCRIPTION "Controls how long of a pause there should be between the migration attempts described in getAdditionalAutoMigrationAttempts(). Note that this delay only happens when the server has failed to come up on every machine."
      ::= { clusterEntry 87  }
   
   
   clusterAutoMigrationTableName OBJECT-TYPE
      SYNTAX      OCTET STRING
      MAX-ACCESS  read-only
      STATUS      current
      DESCRIPTION "Return the name of the table to be used for server migration."
      ::= { clusterEntry 88  }
   
   
   clusterWANSessionPersistenceTableName OBJECT-TYPE
      SYNTAX      OCTET STRING
      MAX-ACCESS  read-only
      STATUS      current
      DESCRIPTION "Return the name of the table to be used for WAN session persistence. "
      ::= { clusterEntry 89  }
   
   
   comTable OBJECT-TYPE
      SYNTAX      SEQUENCE OF ComEntry
      MAX-ACCESS  not-accessible
      STATUS      current
      DESCRIPTION "This table represents a com in the domain."
      ::= { wls 512  }
      
   
   comEntry OBJECT-TYPE
      SYNTAX      ComEntry
      MAX-ACCESS  not-accessible
      STATUS      current
      DESCRIPTION "Entry of comTable"
      INDEX { comIndex}
      ::= { comTable 1 }
      
   ComEntry ::=
      SEQUENCE
      {
         comIndex             DisplayString (SIZE (1..16)),
         comObjectName        DisplayString (SIZE (1..256)),
         comType              DisplayString (SIZE (1..64)),
         comName              DisplayString (SIZE (1..64)),
         comParent            DisplayString (SIZE (1..256)),
         comNTAuthHost        DisplayString (SIZE (1..256)),
         comApartmentThreaded INTEGER,
         comMemoryLoggingEnabled INTEGER,
         comNativeModeEnabled INTEGER,
         comPrefetchEnums     INTEGER,
         comVerboseLoggingEnabled INTEGER
      }
      
   
   comIndex OBJECT-TYPE
      SYNTAX      DisplayString (SIZE (1..16))
      MAX-ACCESS  read-only
      STATUS      current
      DESCRIPTION "Unique value directed from ObjectName which is used as table index"
      ::= { comEntry 1  }
   
   
   comObjectName OBJECT-TYPE
      SYNTAX      DisplayString (SIZE (1..256))
      MAX-ACCESS  read-only
      STATUS      current
      DESCRIPTION "JMX-standard MBean name"
      ::= { comEntry 5  }
   
   
   comType OBJECT-TYPE
      SYNTAX      DisplayString (SIZE (1..64))
      MAX-ACCESS  read-only
      STATUS      current
      DESCRIPTION "BEA-proprietary MBean type"
      ::= { comEntry 10  }
   
   
   comName OBJECT-TYPE
      SYNTAX      DisplayString (SIZE (1..64))
      MAX-ACCESS  read-only
      STATUS      current
      DESCRIPTION "BEA-proprietary MBean name"
      ::= { comEntry 15  }
   
   
   comParent OBJECT-TYPE
      SYNTAX      DisplayString (SIZE (1..256))
      MAX-ACCESS  read-only
      STATUS      current
      DESCRIPTION "BEA-proprietary Parent object's identification, with syntax
      <type>:<name>"
      ::= { comEntry 20  }
   
   
   comNTAuthHost OBJECT-TYPE
      SYNTAX      DisplayString (SIZE (1..256))
      MAX-ACCESS  read-only
      STATUS      current
      DESCRIPTION "The address of the primary domain controller to be used for
      authenticating clients."
      ::= { comEntry 25  }
   
   
   comApartmentThreaded OBJECT-TYPE
      SYNTAX      INTEGER
      MAX-ACCESS  read-only
      STATUS      current
      DESCRIPTION "Controls the flag that is used to initialize COM in native mode.
      *  By default, jCOM initializes COM using the COINIT_MULTITHREADED_FLAG.
      *  If the server logs a Class Not Registered Message when using native mode,
      *  try setting this property.  (COINIT_APARTMENTTHREADED)."
      ::= { comEntry 30  }
   
   
   comMemoryLoggingEnabled OBJECT-TYPE
      SYNTAX      INTEGER
      MAX-ACCESS  read-only
      STATUS      current
      DESCRIPTION "Enables logging of memory usage."
      ::= { comEntry 35  }
   
   
   comNativeModeEnabled OBJECT-TYPE
      SYNTAX      INTEGER
      MAX-ACCESS  read-only
      STATUS      current
      DESCRIPTION "Use native DLLs to allow Java objects to interact with COM Objects."
      ::= { comEntry 45  }
   
   
   comPrefetchEnums OBJECT-TYPE
      SYNTAX      INTEGER
      MAX-ACCESS  read-only
      STATUS      current
      DESCRIPTION "Some COM methods return a COM VariantEnumeration type.  The java2com tool
      *  automatically converts the returned type into a java.lang.Enumeration.
      *  This is not a perfect match since COM enumerations have no equivalent
      *  to the <code>hasMoreElements()</code> call.  The client must continue to
      *  call <code>nextElement</code> until a <code>NoSuchElementException</code>
      *  occurs."
      ::= { comEntry 50  }
   
   
   comVerboseLoggingEnabled OBJECT-TYPE
      SYNTAX      INTEGER
      MAX-ACCESS  read-only
      STATUS      current
      DESCRIPTION "Enables verbose logging."
      ::= { comEntry 55  }
   
   
   domainTable OBJECT-TYPE
      SYNTAX      SEQUENCE OF DomainEntry
      MAX-ACCESS  not-accessible
      STATUS      current
      DESCRIPTION "A WebLogic Domain."
      ::= { wls 530  }
      
   
   domainEntry OBJECT-TYPE
      SYNTAX      DomainEntry
      MAX-ACCESS  not-accessible
      STATUS      current
      DESCRIPTION "Entry of domainTable"
      INDEX { domainIndex}
      ::= { domainTable 1 }
      
   DomainEntry ::=
      SEQUENCE
      {
         domainIndex          DisplayString (SIZE (1..16)),
         domainObjectName     DisplayString (SIZE (1..256)),
         domainType           DisplayString (SIZE (1..64)),
         domainName           DisplayString (SIZE (1..64)),
         domainParent         DisplayString (SIZE (1..256)),
         domainLastModificationTime Counter64,
         domainActive         INTEGER
                     {
                        true(1),
                        false(2)
                     }
         ,
         domainRootDirectory  DisplayString (SIZE (1..256)),
         domainJTA            DisplayString (SIZE (1..256)),
         domainLog            DisplayString (SIZE (1..64)),
         domainSNMPAgent      DisplayString (SIZE (1..64)),
         domainAdministrationPort INTEGER,
         domainArchiveConfigurationCount INTEGER,
         domainConfigurationVersion DisplayString,
         domainConsoleContextPath DisplayString,
         domainAdministrationPortEnabled INTEGER,
         domainClusterConstraintsEnabled INTEGER,
         domainConsoleEnabled INTEGER,
         domainInternalAppsDeployOnDemandEnabled OCTET STRING,
         domainDomainVersion  OCTET STRING,
         domainConfigBackupEnabled OCTET STRING,
         domainConsoleExtensionDirectory OCTET STRING,
         domainConfigurationAuditType OCTET STRING,
         domainAdminServerName OCTET STRING,
         domainAdministrationProtocol OCTET STRING,
         domainProductionModeEnabled OCTET STRING
      }
      
   
   domainIndex OBJECT-TYPE
      SYNTAX      DisplayString (SIZE (1..16))
      MAX-ACCESS  read-only
      STATUS      current
      DESCRIPTION "Unique value directed from ObjectName which is used as table index"
      ::= { domainEntry 1  }
   
   
   domainObjectName OBJECT-TYPE
      SYNTAX      DisplayString (SIZE (1..256))
      MAX-ACCESS  read-only
      STATUS      current
      DESCRIPTION "JMX-standard MBean name"
      ::= { domainEntry 5  }
   
   
   domainType OBJECT-TYPE
      SYNTAX      DisplayString (SIZE (1..64))
      MAX-ACCESS  read-only
      STATUS      current
      DESCRIPTION "BEA-proprietary MBean type"
      ::= { domainEntry 10  }
   
   
   domainName OBJECT-TYPE
      SYNTAX      DisplayString (SIZE (1..64))
      MAX-ACCESS  read-only
      STATUS      current
      DESCRIPTION "BEA-proprietary MBean name"
      ::= { domainEntry 15  }
   
   
   domainParent OBJECT-TYPE
      SYNTAX      DisplayString (SIZE (1..256))
      MAX-ACCESS  read-only
      STATUS      current
      DESCRIPTION "BEA-proprietary Parent object's identification, with syntax
      <type>:<name>"
      ::= { domainEntry 20  }
   
   
   domainLastModificationTime OBJECT-TYPE
      SYNTAX      Counter64
      MAX-ACCESS  read-only
      STATUS      current
      DESCRIPTION "Return the last time this domain was updated. This is
      guaranteed to be unique for a given transactional modification."
      ::= { domainEntry 25  }
   
   
   domainActive OBJECT-TYPE
      SYNTAX      INTEGER
                  {
                     true(1),
                     false(2)
                  }
      
      MAX-ACCESS  read-only
      STATUS      current
      DESCRIPTION "A boolean value (true Or false). Is this domain active?"
      ::= { domainEntry 30  }
   
   
   domainRootDirectory OBJECT-TYPE
      SYNTAX      DisplayString (SIZE (1..256))
      MAX-ACCESS  read-only
      STATUS      current
      DESCRIPTION "Return the root directory for the domain, relative to the admin
      server."
      ::= { domainEntry 35  }
   
   
   domainJTA OBJECT-TYPE
      SYNTAX      DisplayString (SIZE (1..256))
      MAX-ACCESS  read-only
      STATUS      current
      DESCRIPTION "Return the JTA configuration for this Domain."
      ::= { domainEntry 40  }
   
   
   domainLog OBJECT-TYPE
      SYNTAX      DisplayString (SIZE (1..64))
      MAX-ACCESS  read-only
      STATUS      current
      DESCRIPTION "Return the domain logfile configuration for this domain."
      ::= { domainEntry 45  }
   
   
   domainSNMPAgent OBJECT-TYPE
      SYNTAX      DisplayString (SIZE (1..64))
      MAX-ACCESS  read-only
      STATUS      current
      DESCRIPTION "SNMPAgentMBean is a singleton MBean describing SNMP Agent configuration details.
      This MBean has getters and setters for other SNMP related configuration MBeans."
      ::= { domainEntry 50  }
   
   
   domainAdministrationPort OBJECT-TYPE
      SYNTAX      INTEGER
      MAX-ACCESS  read-only
      STATUS      current
      DESCRIPTION "The common secure administration port for the domain."
      ::= { domainEntry 51  }
   
   
   domainArchiveConfigurationCount OBJECT-TYPE
      SYNTAX      INTEGER
      MAX-ACCESS  read-only
      STATUS      current
      DESCRIPTION "Gets the archiveConfigurationCount attribute of the DomainMBean object"
      ::= { domainEntry 52  }
   
   
   domainConfigurationVersion OBJECT-TYPE
      SYNTAX      DisplayString
      MAX-ACCESS  read-only
      STATUS      current
      DESCRIPTION "The release identifier for the configuration."
      ::= { domainEntry 53  }
   
   
   domainConsoleContextPath OBJECT-TYPE
      SYNTAX      DisplayString
      MAX-ACCESS  read-only
      STATUS      current
      DESCRIPTION "Specifies the context path for the WLS console."
      ::= { domainEntry 54  }
   
   
   domainAdministrationPortEnabled OBJECT-TYPE
      SYNTAX      INTEGER
      MAX-ACCESS  read-only
      STATUS      current
      DESCRIPTION "Indicates whether or not the administration port should be enabled for the domain."
      ::= { domainEntry 55  }
   
   
   domainClusterConstraintsEnabled OBJECT-TYPE
      SYNTAX      INTEGER
      MAX-ACCESS  read-only
      STATUS      current
      DESCRIPTION "Retrieves the attribute indicating whether strict cluster constraints are enforced or not for this domain."
      ::= { domainEntry 56  }
   
   
   domainConsoleEnabled OBJECT-TYPE
      SYNTAX      INTEGER
      MAX-ACCESS  read-only
      STATUS      current
      DESCRIPTION "Indicates whether the WLS console should be auto-deployed for this domain."
      ::= { domainEntry 57  }
   
   
   domainInternalAppsDeployOnDemandEnabled OBJECT-TYPE
      SYNTAX      OCTET STRING
      MAX-ACCESS  read-only
      STATUS      current
      DESCRIPTION "Specifies whether internal applications such as the console, uddi, wlstestclient, and uddiexplorer are deployed on demand (first access) instead of during server startup."
      ::= { domainEntry 58  }
   
   
   domainDomainVersion OBJECT-TYPE
      SYNTAX      OCTET STRING
      MAX-ACCESS  read-only
      STATUS      current
      DESCRIPTION "Defines the common version of all servers in a domain. In a domain containing servers that are not all at the same release version, this attribute is used to determine the feature level that servers will assume.  The value must be less than or equal to the version of any managed server in the domain.  If this value is not equal to the version of the release version of the admin server, then the admin server will not be allowed to make modifications to the configuration."
      ::= { domainEntry 59  }
   
   
   domainConfigBackupEnabled OBJECT-TYPE
      SYNTAX      OCTET STRING
      MAX-ACCESS  read-only
      STATUS      current
      DESCRIPTION "If true, then backups of the configuration will be made during server boot."
      ::= { domainEntry 60  }
   
   
   domainConsoleExtensionDirectory OBJECT-TYPE
      SYNTAX      OCTET STRING
      MAX-ACCESS  read-only
      STATUS      current
      DESCRIPTION "Returns the directory path that console extensions are loaded from."
      ::= { domainEntry 61  }
   
   
   domainConfigurationAuditType OBJECT-TYPE
      SYNTAX      OCTET STRING
      MAX-ACCESS  read-only
      STATUS      current
      DESCRIPTION "Returns the criteria used for auditing configuration events  (configuration changes and other operations):  CONFIG_CHANGE_NONE Configuration events will neither be written to the server log or directed to the Security Audit Framework. CONFIG_CHANGE_LOG Configuration events will be written to the server log. CONFIG_CHANGE_AUDITConfiguration events will be directed to the Security Audit Framework. CONFIG_CHANGE_LOG_AND_AUDIT Configuration events will be written to the server log and directed to the Security Audit Framework."
      ::= { domainEntry 62  }
   
   
   domainAdminServerName OBJECT-TYPE
      SYNTAX      OCTET STRING
      MAX-ACCESS  read-only
      STATUS      current
      DESCRIPTION ""
      ::= { domainEntry 63  }
   
   
   domainAdministrationProtocol OBJECT-TYPE
      SYNTAX      OCTET STRING
      MAX-ACCESS  read-only
      STATUS      current
      DESCRIPTION "The default protocol for communicating through the administration port or administration channels. (Requires you to enable the administration port or to create an administration channel.)  If requests through the administration port or an administration channel do not specify a protocol, WebLogic Server uses the protocol specified here."
      ::= { domainEntry 64  }
   
   
   domainProductionModeEnabled OBJECT-TYPE
      SYNTAX      OCTET STRING
      MAX-ACCESS  read-only
      STATUS      current
      DESCRIPTION "Specifies whether all servers in this domain run in production mode. You can configure servers in your domain to start in one of two modes, development or production. You use development mode while you are developing your applications. Development mode uses a relaxed security configuration and enables you to auto-deploy applications. You use production mode when your application is running in its final form. A production domain uses full security and may use clusters or other advanced features.  The runtime mode is a domain-wide setting. As each Managed Server starts, it refers to the mode of the Administration Server to determine its runtime mode. If you configure the domain to run in production mode, the Administration Server saves this setting to the domains configuration document."
      ::= { domainEntry 65  }
   
   
   ejbComponentTable OBJECT-TYPE
      SYNTAX      SEQUENCE OF EjbComponentEntry
      MAX-ACCESS  not-accessible
      STATUS      current
      DESCRIPTION "Generated SNMP Table."
      ::= { wls 540  }
      
   
   ejbComponentEntry OBJECT-TYPE
      SYNTAX      EjbComponentEntry
      MAX-ACCESS  not-accessible
      STATUS      current
      DESCRIPTION "Entry of ejbComponentTable"
      INDEX { ejbComponentIndex}
      ::= { ejbComponentTable 1 }
      
   EjbComponentEntry ::=
      SEQUENCE
      {
         ejbComponentIndex    DisplayString (SIZE (1..16)),
         ejbComponentObjectName DisplayString (SIZE (1..256)),
         ejbComponentType     DisplayString (SIZE (1..64)),
         ejbComponentName     DisplayString (SIZE (1..64)),
         ejbComponentParent   DisplayString (SIZE (1..256)),
         ejbComponentJavaCompiler DisplayString (SIZE (1..32)),
         ejbComponentJavaCompilerPreClassPath DisplayString (SIZE (1..256)),
         ejbComponentJavaCompilerPostClassPath DisplayString (SIZE (1..256)),
         ejbComponentExtraRmicOptions DisplayString (SIZE (1..256)),
         ejbComponentKeepGenerated INTEGER
                     {
                        true(1),
                        false(2)
                     }
         ,
         ejbComponentTmpPath  DisplayString (SIZE (1..1024)),
         ejbComponentApplication DisplayString (SIZE (1..256)),
         ejbComponentURI      DisplayString (SIZE (1..256))
      }
      
   
   ejbComponentIndex OBJECT-TYPE
      SYNTAX      DisplayString (SIZE (1..16))
      MAX-ACCESS  read-only
      STATUS      current
      DESCRIPTION "Unique value directed from ObjectName which is used as table index"
      ::= { ejbComponentEntry 1  }
   
   
   ejbComponentObjectName OBJECT-TYPE
      SYNTAX      DisplayString (SIZE (1..256))
      MAX-ACCESS  read-only
      STATUS      current
      DESCRIPTION "JMX-standard MBean name"
      ::= { ejbComponentEntry 5  }
   
   
   ejbComponentType OBJECT-TYPE
      SYNTAX      DisplayString (SIZE (1..64))
      MAX-ACCESS  read-only
      STATUS      current
      DESCRIPTION "BEA-proprietary MBean type"
      ::= { ejbComponentEntry 10  }
   
   
   ejbComponentName OBJECT-TYPE
      SYNTAX      DisplayString (SIZE (1..64))
      MAX-ACCESS  read-only
      STATUS      current
      DESCRIPTION "BEA-proprietary MBean name"
      ::= { ejbComponentEntry 15  }
   
   
   ejbComponentParent OBJECT-TYPE
      SYNTAX      DisplayString (SIZE (1..256))
      MAX-ACCESS  read-only
      STATUS      current
      DESCRIPTION "BEA-proprietary Parent object's identification, with syntax
      <type>:<name>"
      ::= { ejbComponentEntry 20  }
   
   
   ejbComponentJavaCompiler OBJECT-TYPE
      SYNTAX      DisplayString (SIZE (1..32))
      MAX-ACCESS  read-only
      STATUS      current
      DESCRIPTION "Return the path to the Java compiler to use to compile EJB's"
      ::= { ejbComponentEntry 25  }
   
   
   ejbComponentJavaCompilerPreClassPath OBJECT-TYPE
      SYNTAX      DisplayString (SIZE (1..256))
      MAX-ACCESS  read-only
      STATUS      current
      DESCRIPTION "Return the options to prepend to the Java compiler classpath for when
      we need to compile Java code."
      ::= { ejbComponentEntry 30  }
   
   
   ejbComponentJavaCompilerPostClassPath OBJECT-TYPE
      SYNTAX      DisplayString (SIZE (1..256))
      MAX-ACCESS  read-only
      STATUS      current
      DESCRIPTION "Return the options to append to the Java compiler classpath for when we
      need to compile Java code."
      ::= { ejbComponentEntry 35  }
   
   
   ejbComponentExtraRmicOptions OBJECT-TYPE
      SYNTAX      DisplayString (SIZE (1..256))
      MAX-ACCESS  read-only
      STATUS      current
      DESCRIPTION "Return the extra options passed to rmic during server-side
      generation.."
      ::= { ejbComponentEntry 40  }
   
   
   ejbComponentKeepGenerated OBJECT-TYPE
      SYNTAX      INTEGER
                  {
                     true(1),
                     false(2)
                  }
      
      MAX-ACCESS  read-only
      STATUS      current
      DESCRIPTION "A boolean value (true Or false). Return true if ejbc should keep its generated source files,
      false if it should delete them after compiling them."
      ::= { ejbComponentEntry 45  }
   
   
   ejbComponentTmpPath OBJECT-TYPE
      SYNTAX      DisplayString (SIZE (1..1024))
      MAX-ACCESS  read-only
      STATUS      current
      DESCRIPTION "Return the temporary directory where generated files are stored by ejbc."
      ::= { ejbComponentEntry 50  }
   
   
   ejbComponentApplication OBJECT-TYPE
      SYNTAX      DisplayString (SIZE (1..256))
      MAX-ACCESS  read-only
      STATUS      current
      DESCRIPTION "Return the application this component is a part of. 
      This is guaranteed to never be null."
      ::= { ejbComponentEntry 60  }
   
   
   ejbComponentURI OBJECT-TYPE
      SYNTAX      DisplayString (SIZE (1..256))
      MAX-ACCESS  read-only
      STATUS      current
      DESCRIPTION "Return a URI pointing to the application component, usually on the Admin Server."
      ::= { ejbComponentEntry 65  }
   
   
   ejbContainerTable OBJECT-TYPE
      SYNTAX      SEQUENCE OF EjbContainerEntry
      MAX-ACCESS  not-accessible
      STATUS      current
      DESCRIPTION "This table represents a ejbContainer in the domain."
      ::= { wls 545  }
      
   
   ejbContainerEntry OBJECT-TYPE
      SYNTAX      EjbContainerEntry
      MAX-ACCESS  not-accessible
      STATUS      current
      DESCRIPTION "Entry of ejbContainerTable"
      INDEX { ejbContainerIndex}
      ::= { ejbContainerTable 1 }
      
   EjbContainerEntry ::=
      SEQUENCE
      {
         ejbContainerIndex    DisplayString (SIZE (1..16)),
         ejbContainerObjectName DisplayString (SIZE (1..256)),
         ejbContainerType     DisplayString (SIZE (1..64)),
         ejbContainerName     DisplayString (SIZE (1..64)),
         ejbContainerParent   DisplayString (SIZE (1..256)),
         ejbContainerVerboseEJBDeploymentEnabled DisplayString (SIZE (1..256)),
         ejbContainerExtraRmicOptions DisplayString (SIZE (1..256)),
         ejbContainerForceGeneration DisplayString (SIZE (1..256)),
         ejbContainerJavaCompiler DisplayString (SIZE (1..256)),
         ejbContainerJavaCompilerPostClassPath DisplayString (SIZE (1..256)),
         ejbContainerJavaCompilerPreClassPath DisplayString (SIZE (1..256)),
         ejbContainerKeepGenerated DisplayString (SIZE (1..256)),
         ejbContainerTmpPath  DisplayString (SIZE (1..256)),
         ejbContainerExtraEjbcOptions DisplayString
      }
      
   
   ejbContainerIndex OBJECT-TYPE
      SYNTAX      DisplayString (SIZE (1..16))
      MAX-ACCESS  read-only
      STATUS      current
      DESCRIPTION "Unique value directed from ObjectName which is used as table index"
      ::= { ejbContainerEntry 1  }
   
   
   ejbContainerObjectName OBJECT-TYPE
      SYNTAX      DisplayString (SIZE (1..256))
      MAX-ACCESS  read-only
      STATUS      current
      DESCRIPTION "JMX-standard MBean name"
      ::= { ejbContainerEntry 5  }
   
   
   ejbContainerType OBJECT-TYPE
      SYNTAX      DisplayString (SIZE (1..64))
      MAX-ACCESS  read-only
      STATUS      current
      DESCRIPTION "BEA-proprietary MBean type"
      ::= { ejbContainerEntry 10  }
   
   
   ejbContainerName OBJECT-TYPE
      SYNTAX      DisplayString (SIZE (1..64))
      MAX-ACCESS  read-only
      STATUS      current
      DESCRIPTION "BEA-proprietary MBean name"
      ::= { ejbContainerEntry 15  }
   
   
   ejbContainerParent OBJECT-TYPE
      SYNTAX      DisplayString (SIZE (1..256))
      MAX-ACCESS  read-only
      STATUS      current
      DESCRIPTION "BEA-proprietary Parent object's identification, with syntax
      <type>:<name>"
      ::= { ejbContainerEntry 20  }
   
   
   ejbContainerVerboseEJBDeploymentEnabled OBJECT-TYPE
      SYNTAX      DisplayString (SIZE (1..256))
      MAX-ACCESS  read-only
      STATUS      current
      DESCRIPTION "Returns true if verbose deployment of EJB's is enabled."
      ::= { ejbContainerEntry 25  }
   
   
   ejbContainerExtraRmicOptions OBJECT-TYPE
      SYNTAX      DisplayString (SIZE (1..256))
      MAX-ACCESS  read-only
      STATUS      current
      DESCRIPTION "Return the extra options passed to rmic during server-side
      generation."
      ::= { ejbContainerEntry 30  }
   
   
   ejbContainerForceGeneration OBJECT-TYPE
      SYNTAX      DisplayString (SIZE (1..256))
      MAX-ACCESS  read-only
      STATUS      current
      DESCRIPTION "Return true if ejbc should force regeneration of wrapper classes,
      false if it should regenerate the files only if it determines
      it needs to do so."
      ::= { ejbContainerEntry 35  }
   
   
   ejbContainerJavaCompiler OBJECT-TYPE
      SYNTAX      DisplayString (SIZE (1..256))
      MAX-ACCESS  read-only
      STATUS      current
      DESCRIPTION "Return the path to the Java compiler to use to compile EJB's
      (e.g. sj or javac)."
      ::= { ejbContainerEntry 40  }
   
   
   ejbContainerJavaCompilerPostClassPath OBJECT-TYPE
      SYNTAX      DisplayString (SIZE (1..256))
      MAX-ACCESS  read-only
      STATUS      current
      DESCRIPTION "Return the options to append to the Java compiler classpath for when we
      need to compile Java code."
      ::= { ejbContainerEntry 45  }
   
   
   ejbContainerJavaCompilerPreClassPath OBJECT-TYPE
      SYNTAX      DisplayString (SIZE (1..256))
      MAX-ACCESS  read-only
      STATUS      current
      DESCRIPTION "Return the options to prepend to the Java compiler classpath for when
      we need to compile Java code."
      ::= { ejbContainerEntry 50  }
   
   
   ejbContainerKeepGenerated OBJECT-TYPE
      SYNTAX      DisplayString (SIZE (1..256))
      MAX-ACCESS  read-only
      STATUS      current
      DESCRIPTION "Return the options to prepend to the Java compiler classpath for when
      we need to compile Java code."
      ::= { ejbContainerEntry 55  }
   
   
   ejbContainerTmpPath OBJECT-TYPE
      SYNTAX      DisplayString (SIZE (1..256))
      MAX-ACCESS  read-only
      STATUS      current
      DESCRIPTION "Return the temporary directory where generated files are stored
      by ejbc."
      ::= { ejbContainerEntry 60  }
   
   
   ejbContainerExtraEjbcOptions OBJECT-TYPE
      SYNTAX      DisplayString
      MAX-ACCESS  read-only
      STATUS      current
      DESCRIPTION "Returns the extra options passed to ejbc during the dynamic ejbc of a jar file."
      ::= { ejbContainerEntry 61  }
   
   
   executeQueueTable OBJECT-TYPE
      SYNTAX      SEQUENCE OF ExecuteQueueEntry
      MAX-ACCESS  not-accessible
      STATUS      current
      DESCRIPTION "Generated SNMP Table."
      ::= { wls 550  }
      
   
   executeQueueEntry OBJECT-TYPE
      SYNTAX      ExecuteQueueEntry
      MAX-ACCESS  not-accessible
      STATUS      current
      DESCRIPTION "Entry of executeQueueTable"
      INDEX { executeQueueIndex}
      ::= { executeQueueTable 1 }
      
   ExecuteQueueEntry ::=
      SEQUENCE
      {
         executeQueueIndex    DisplayString (SIZE (1..16)),
         executeQueueObjectName DisplayString (SIZE (1..256)),
         executeQueueType     DisplayString (SIZE (1..64)),
         executeQueueName     DisplayString (SIZE (1..64)),
         executeQueueParent   DisplayString (SIZE (1..256)),
         executeQueueThreadCount INTEGER,
         executeQueueThreadsMaximum INTEGER,
         executeQueueQueueLengthThresholdPercent INTEGER,
         executeQueueThreadsIncrease INTEGER,
         executeQueueThreadsMinimum INTEGER,
         executeQueueQueueLength INTEGER
      }
      
   
   executeQueueIndex OBJECT-TYPE
      SYNTAX      DisplayString (SIZE (1..16))
      MAX-ACCESS  read-only
      STATUS      current
      DESCRIPTION "Unique value directed from ObjectName which is used as table index"
      ::= { executeQueueEntry 1  }
   
   
   executeQueueObjectName OBJECT-TYPE
      SYNTAX      DisplayString (SIZE (1..256))
      MAX-ACCESS  read-only
      STATUS      current
      DESCRIPTION "JMX-standard MBean name"
      ::= { executeQueueEntry 5  }
   
   
   executeQueueType OBJECT-TYPE
      SYNTAX      DisplayString (SIZE (1..64))
      MAX-ACCESS  read-only
      STATUS      current
      DESCRIPTION "BEA-proprietary MBean type"
      ::= { executeQueueEntry 10  }
   
   
   executeQueueName OBJECT-TYPE
      SYNTAX      DisplayString (SIZE (1..64))
      MAX-ACCESS  read-only
      STATUS      current
      DESCRIPTION "BEA-proprietary MBean name"
      ::= { executeQueueEntry 15  }
   
   
   executeQueueParent OBJECT-TYPE
      SYNTAX      DisplayString (SIZE (1..256))
      MAX-ACCESS  read-only
      STATUS      current
      DESCRIPTION "BEA-proprietary Parent object's identification, with syntax
      <type>:<name>"
      ::= { executeQueueEntry 20  }
   
   
   executeQueueThreadCount OBJECT-TYPE
      SYNTAX      INTEGER
      MAX-ACCESS  read-only
      STATUS      current
      DESCRIPTION "The number of threads assigned to this queue."
      ::= { executeQueueEntry 25  }
   
   
   executeQueueThreadsMaximum OBJECT-TYPE
      SYNTAX      INTEGER
      MAX-ACCESS  read-only
      STATUS      current
      DESCRIPTION "Returns the maximum number of threads in the pool."
      ::= { executeQueueEntry 26  }
   
   
   executeQueueQueueLengthThresholdPercent OBJECT-TYPE
      SYNTAX      INTEGER
      MAX-ACCESS  read-only
      STATUS      current
      DESCRIPTION "The percentage of the Queue Length size that can be reached before this server indicates an overflow condition for the queue. If the overflow condition is reached and the current thread count has not reached the ThreadsMaximum value, then ThreadsIncrease number of threads are added."
      ::= { executeQueueEntry 27  }
   
   
   executeQueueThreadsIncrease OBJECT-TYPE
      SYNTAX      INTEGER
      MAX-ACCESS  read-only
      STATUS      current
      DESCRIPTION "Specifies the number of threads to increase the queue length when the queue length theshold is reached. This threshold is determined by the QueueLengthThresholdPercent value.  The following consideration applies to the dynamic nature of ThreadsMaximum and ThreadsIncrease attributes. If any of these attributes change during runtime, the changed value comes into effect when the next request is submitted to the execute queue and the scheduler decides to increase threads depending on the queue threshold conditions."
      ::= { executeQueueEntry 28  }
   
   
   executeQueueThreadsMinimum OBJECT-TYPE
      SYNTAX      INTEGER
      MAX-ACCESS  read-only
      STATUS      current
      DESCRIPTION "The minimum number of threads that WebLogic Server will maintain in the queue."
      ::= { executeQueueEntry 29  }
   
   
   executeQueueQueueLength OBJECT-TYPE
      SYNTAX      INTEGER
      MAX-ACCESS  read-only
      STATUS      current
      DESCRIPTION "The maximum number of simultaneous requests that this server can hold in the queue."
      ::= { executeQueueEntry 30  }
   
   
   foreignJMSConnectionFactoryTable OBJECT-TYPE
      SYNTAX      SEQUENCE OF ForeignJMSConnectionFactoryEntry
      MAX-ACCESS  not-accessible
      STATUS      current
      DESCRIPTION "Generated SNMP Table."
      ::= { wls 551  }
      
   
   foreignJMSConnectionFactoryEntry OBJECT-TYPE
      SYNTAX      ForeignJMSConnectionFactoryEntry
      MAX-ACCESS  not-accessible
      STATUS      current
      DESCRIPTION "Entry of foreignJMSConnectionFactoryTable"
      INDEX { foreignJMSConnectionFactoryIndex}
      ::= { foreignJMSConnectionFactoryTable 1 }
      
   ForeignJMSConnectionFactoryEntry ::=
      SEQUENCE
      {
         foreignJMSConnectionFactoryIndex DisplayString (SIZE (1..16)),
         foreignJMSConnectionFactoryObjectName DisplayString (SIZE (1..256)),
         foreignJMSConnectionFactoryType DisplayString (SIZE (1..64)),
         foreignJMSConnectionFactoryName DisplayString (SIZE (1..64)),
         foreignJMSConnectionFactoryParent DisplayString (SIZE (1..256)),
         foreignJMSConnectionFactoryLocalJNDIName DisplayString,
         foreignJMCConnectionFactoryRemoteJNDIName DisplayString,
         foreignJMSConnectionFactoryUsername DisplayString
      }
      
   
   foreignJMSConnectionFactoryIndex OBJECT-TYPE
      SYNTAX      DisplayString (SIZE (1..16))
      MAX-ACCESS  read-only
      STATUS      current
      DESCRIPTION "Unique value directed from ObjectName which is used as table index"
      ::= { foreignJMSConnectionFactoryEntry 1  }
   
   
   foreignJMSConnectionFactoryObjectName OBJECT-TYPE
      SYNTAX      DisplayString (SIZE (1..256))
      MAX-ACCESS  read-only
      STATUS      current
      DESCRIPTION "JMX-standard MBean name"
      ::= { foreignJMSConnectionFactoryEntry 5  }
   
   
   foreignJMSConnectionFactoryType OBJECT-TYPE
      SYNTAX      DisplayString (SIZE (1..64))
      MAX-ACCESS  read-only
      STATUS      current
      DESCRIPTION "BEA-proprietary MBean type"
      ::= { foreignJMSConnectionFactoryEntry 10  }
   
   
   foreignJMSConnectionFactoryName OBJECT-TYPE
      SYNTAX      DisplayString (SIZE (1..64))
      MAX-ACCESS  read-only
      STATUS      current
      DESCRIPTION "BEA-proprietary MBean name"
      ::= { foreignJMSConnectionFactoryEntry 15  }
   
   
   foreignJMSConnectionFactoryParent OBJECT-TYPE
      SYNTAX      DisplayString (SIZE (1..256))
      MAX-ACCESS  read-only
      STATUS      current
      DESCRIPTION "BEA-proprietary Parent object's identification, with syntax
      <type>:<name>"
      ::= { foreignJMSConnectionFactoryEntry 20  }
   
   
   foreignJMSConnectionFactoryLocalJNDIName OBJECT-TYPE
      SYNTAX      DisplayString
      MAX-ACCESS  read-only
      STATUS      current
      DESCRIPTION "Generated Object."
      ::= { foreignJMSConnectionFactoryEntry 21  }
   
   
   foreignJMCConnectionFactoryRemoteJNDIName OBJECT-TYPE
      SYNTAX      DisplayString
      MAX-ACCESS  read-only
      STATUS      current
      DESCRIPTION "Generated Object."
      ::= { foreignJMSConnectionFactoryEntry 22  }
   
   
   foreignJMSConnectionFactoryUsername OBJECT-TYPE
      SYNTAX      DisplayString
      MAX-ACCESS  read-only
      STATUS      current
      DESCRIPTION "Generated Object."
      ::= { foreignJMSConnectionFactoryEntry 23  }
   
   
   foreignJMSDestinationTable OBJECT-TYPE
      SYNTAX      SEQUENCE OF ForeignJMSDestinationEntry
      MAX-ACCESS  not-accessible
      STATUS      current
      DESCRIPTION "Generated SNMP Table."
      ::= { wls 552  }
      
   
   foreignJMSDestinationEntry OBJECT-TYPE
      SYNTAX      ForeignJMSDestinationEntry
      MAX-ACCESS  not-accessible
      STATUS      current
      DESCRIPTION "Entry of foreignJMSDestinationTable"
      INDEX { foreignJMSDestinationIndex}
      ::= { foreignJMSDestinationTable 1 }
      
   ForeignJMSDestinationEntry ::=
      SEQUENCE
      {
         foreignJMSDestinationIndex DisplayString (SIZE (1..16)),
         foreignJMSDestinationObjectName DisplayString (SIZE (1..256)),
         foreignJMSDestinationType DisplayString (SIZE (1..64)),
         foreignJMSDestinationName DisplayString (SIZE (1..64)),
         foreignJMSDestinationParent DisplayString (SIZE (1..256)),
         foreignJMSDestinationLocalJNDIName DisplayString,
         foreignJMSDestinationRemoteJNDIName DisplayString
      }
      
   
   foreignJMSDestinationIndex OBJECT-TYPE
      SYNTAX      DisplayString (SIZE (1..16))
      MAX-ACCESS  read-only
      STATUS      current
      DESCRIPTION "Unique value directed from ObjectName which is used as table index"
      ::= { foreignJMSDestinationEntry 1  }
   
   
   foreignJMSDestinationObjectName OBJECT-TYPE
      SYNTAX      DisplayString (SIZE (1..256))
      MAX-ACCESS  read-only
      STATUS      current
      DESCRIPTION "JMX-standard MBean name"
      ::= { foreignJMSDestinationEntry 5  }
   
   
   foreignJMSDestinationType OBJECT-TYPE
      SYNTAX      DisplayString (SIZE (1..64))
      MAX-ACCESS  read-only
      STATUS      current
      DESCRIPTION "BEA-proprietary MBean type"
      ::= { foreignJMSDestinationEntry 10  }
   
   
   foreignJMSDestinationName OBJECT-TYPE
      SYNTAX      DisplayString (SIZE (1..64))
      MAX-ACCESS  read-only
      STATUS      current
      DESCRIPTION "BEA-proprietary MBean name"
      ::= { foreignJMSDestinationEntry 15  }
   
   
   foreignJMSDestinationParent OBJECT-TYPE
      SYNTAX      DisplayString (SIZE (1..256))
      MAX-ACCESS  read-only
      STATUS      current
      DESCRIPTION "BEA-proprietary Parent object's identification, with syntax
      <type>:<name>"
      ::= { foreignJMSDestinationEntry 20  }
   
   
   foreignJMSDestinationLocalJNDIName OBJECT-TYPE
      SYNTAX      DisplayString
      MAX-ACCESS  read-only
      STATUS      current
      DESCRIPTION "Generated Object."
      ::= { foreignJMSDestinationEntry 21  }
   
   
   foreignJMSDestinationRemoteJNDIName OBJECT-TYPE
      SYNTAX      DisplayString
      MAX-ACCESS  read-only
      STATUS      current
      DESCRIPTION "Generated Object."
      ::= { foreignJMSDestinationEntry 22  }
   
   
   foreignJMSServerTable OBJECT-TYPE
      SYNTAX      SEQUENCE OF ForeignJMSServerEntry
      MAX-ACCESS  not-accessible
      STATUS      current
      DESCRIPTION "Generated SNMP Table."
      ::= { wls 553  }
      
   
   foreignJMSServerEntry OBJECT-TYPE
      SYNTAX      ForeignJMSServerEntry
      MAX-ACCESS  not-accessible
      STATUS      current
      DESCRIPTION "Entry of foreignJMSServerTable"
      INDEX { foreignJMSServerIndex}
      ::= { foreignJMSServerTable 1 }
      
   ForeignJMSServerEntry ::=
      SEQUENCE
      {
         foreignJMSServerIndex DisplayString (SIZE (1..16)),
         foreignJMSServerObjectName DisplayString (SIZE (1..256)),
         foreignJMSServerType DisplayString (SIZE (1..64)),
         foreignJMSServerName DisplayString (SIZE (1..64)),
         foreignJMSServerParent DisplayString (SIZE (1..256)),
         foreignJMSServerConnectionURL DisplayString,
         foreignJMSServerInitialContextFactory DisplayString
      }
      
   
   foreignJMSServerIndex OBJECT-TYPE
      SYNTAX      DisplayString (SIZE (1..16))
      MAX-ACCESS  read-only
      STATUS      current
      DESCRIPTION "Unique value directed from ObjectName which is used as table index"
      ::= { foreignJMSServerEntry 1  }
   
   
   foreignJMSServerObjectName OBJECT-TYPE
      SYNTAX      DisplayString (SIZE (1..256))
      MAX-ACCESS  read-only
      STATUS      current
      DESCRIPTION "JMX-standard MBean name"
      ::= { foreignJMSServerEntry 5  }
   
   
   foreignJMSServerType OBJECT-TYPE
      SYNTAX      DisplayString (SIZE (1..64))
      MAX-ACCESS  read-only
      STATUS      current
      DESCRIPTION "BEA-proprietary MBean type"
      ::= { foreignJMSServerEntry 10  }
   
   
   foreignJMSServerName OBJECT-TYPE
      SYNTAX      DisplayString (SIZE (1..64))
      MAX-ACCESS  read-only
      STATUS      current
      DESCRIPTION "BEA-proprietary MBean name"
      ::= { foreignJMSServerEntry 15  }
   
   
   foreignJMSServerParent OBJECT-TYPE
      SYNTAX      DisplayString (SIZE (1..256))
      MAX-ACCESS  read-only
      STATUS      current
      DESCRIPTION "BEA-proprietary Parent object's identification, with syntax
      <type>:<name>"
      ::= { foreignJMSServerEntry 20  }
   
   
   foreignJMSServerConnectionURL OBJECT-TYPE
      SYNTAX      DisplayString
      MAX-ACCESS  read-only
      STATUS      current
      DESCRIPTION "Generated Object."
      ::= { foreignJMSServerEntry 21  }
   
   
   foreignJMSServerInitialContextFactory OBJECT-TYPE
      SYNTAX      DisplayString
      MAX-ACCESS  read-only
      STATUS      current
      DESCRIPTION "Generated Object."
      ::= { foreignJMSServerEntry 22  }
   
   
   iiopTable OBJECT-TYPE
      SYNTAX      SEQUENCE OF IiopEntry
      MAX-ACCESS  not-accessible
      STATUS      current
      DESCRIPTION "This table represents a iiop in the domain."
      ::= { wls 555  }
      
   
   iiopEntry OBJECT-TYPE
      SYNTAX      IiopEntry
      MAX-ACCESS  not-accessible
      STATUS      current
      DESCRIPTION "Entry of iiopTable"
      INDEX { iiopIndex}
      ::= { iiopTable 1 }
      
   IiopEntry ::=
      SEQUENCE
      {
         iiopIndex            DisplayString (SIZE (1..16)),
         iiopObjectName       DisplayString (SIZE (1..256)),
         iiopType             DisplayString (SIZE (1..64)),
         iiopName             DisplayString (SIZE (1..64)),
         iiopParent           DisplayString (SIZE (1..256)),
         iiopCompleteMessageTimeout INTEGER,
         iiopIdleConnectionTimeout INTEGER,
         iiopMaxMessageSize   INTEGER,
         iiopDefaultCharCodeset DisplayString,
         iiopDefaultMinorVersion INTEGER,
         iiopDefaultWideCharCodeset DisplayString,
         iiopTxMechanism      DisplayString,
         iiopUseStatefulAuthentication OCTET STRING,
         iiopUseJavaSerialization OCTET STRING,
         iiopUseFullRepositoryIdList OCTET STRING,
         iiopEnableIORServlet OCTET STRING,
         iiopSystemSecurity   OCTET STRING,
         iiopUseSerialFormatVersion2 OCTET STRING
      }
      
   
   iiopIndex OBJECT-TYPE
      SYNTAX      DisplayString (SIZE (1..16))
      MAX-ACCESS  read-only
      STATUS      current
      DESCRIPTION "Unique value directed from ObjectName which is used as table index"
      ::= { iiopEntry 1  }
   
   
   iiopObjectName OBJECT-TYPE
      SYNTAX      DisplayString (SIZE (1..256))
      MAX-ACCESS  read-only
      STATUS      current
      DESCRIPTION "JMX-standard MBean name"
      ::= { iiopEntry 5  }
   
   
   iiopType OBJECT-TYPE
      SYNTAX      DisplayString (SIZE (1..64))
      MAX-ACCESS  read-only
      STATUS      current
      DESCRIPTION "BEA-proprietary MBean type"
      ::= { iiopEntry 10  }
   
   
   iiopName OBJECT-TYPE
      SYNTAX      DisplayString (SIZE (1..64))
      MAX-ACCESS  read-only
      STATUS      current
      DESCRIPTION "BEA-proprietary MBean name"
      ::= { iiopEntry 15  }
   
   
   iiopParent OBJECT-TYPE
      SYNTAX      DisplayString (SIZE (1..256))
      MAX-ACCESS  read-only
      STATUS      current
      DESCRIPTION "BEA-proprietary Parent object's identification, with syntax
      <type>:<name>"
      ::= { iiopEntry 20  }
   
   
   iiopCompleteMessageTimeout OBJECT-TYPE
      SYNTAX      INTEGER
      MAX-ACCESS  read-only
      STATUS      current
      DESCRIPTION "Specify the maximum number of seconds spent
      * waiting for a complete IIOP message to be received.
      * This attribute helps guard against denial of
      * service attacks in which a caller indicates that
      * they will be sending a message of a certain size
      * which they never finish sending."
      ::= { iiopEntry 25  }
   
   
   iiopIdleConnectionTimeout OBJECT-TYPE
      SYNTAX      INTEGER
      MAX-ACCESS  read-only
      STATUS      current
      DESCRIPTION "Specify the maximum number of seconds an IIOP connection is
      * allowed to be idle before it is closed by the server. This
      * attribute helps guard against server deadlock through too many
      * open connections."
      ::= { iiopEntry 30  }
   
   
   iiopMaxMessageSize OBJECT-TYPE
      SYNTAX      INTEGER
      MAX-ACCESS  read-only
      STATUS      current
      DESCRIPTION "Specify the maximum IIOP message size allowable in a message header.
      * This attribute attempts to prevent a denial of service attack whereby
      * a caller attempts to force the server to allocate more memory than
      * is available thereby keeping the server from responding quickly to
      * other requests."
      ::= { iiopEntry 35  }
   
   
   iiopDefaultCharCodeset OBJECT-TYPE
      SYNTAX      DisplayString
      MAX-ACCESS  read-only
      STATUS      current
      DESCRIPTION "Specify what codeset should be used for the default native character codeset."
      ::= { iiopEntry 36  }
   
   
   iiopDefaultMinorVersion OBJECT-TYPE
      SYNTAX      INTEGER
      MAX-ACCESS  read-only
      STATUS      current
      DESCRIPTION "Specify the default minor GIOP version for IIOP messages."
      ::= { iiopEntry 37  }
   
   
   iiopDefaultWideCharCodeset OBJECT-TYPE
      SYNTAX      DisplayString
      MAX-ACCESS  read-only
      STATUS      current
      DESCRIPTION "Specify what codeset should be used for the default native wide character codeset."
      ::= { iiopEntry 38  }
   
   
   iiopTxMechanism OBJECT-TYPE
      SYNTAX      DisplayString
      MAX-ACCESS  read-only
      STATUS      current
      DESCRIPTION "Specify whether IIOP should use the WebLogic-specific JTA to propagate transactions or the OMG-specified OTS."
      ::= { iiopEntry 39  }
   
   
   iiopUseStatefulAuthentication OBJECT-TYPE
      SYNTAX      OCTET STRING
      MAX-ACCESS  read-only
      STATUS      current
      DESCRIPTION "Specify whether to advertise RMI objects and EJBs as supporting stateful CSIv2. Stateful CSIv2 is more efficient than stateless, requiring only a single authentication step for each remote principal. Stateless CSIv2 requires per-request authentication. Stateful CSIv2 is not required by J2EE 1.3 and so some ORBs do not support it. Stateful CSIv2 is enabled by default. This property can be changed at the object-level by changing the object's &lt;stateful-authentication&gt; runtime descriptor property."
      ::= { iiopEntry 40  }
   
   
   iiopUseJavaSerialization OBJECT-TYPE
      SYNTAX      OCTET STRING
      MAX-ACCESS  read-only
      STATUS      current
      DESCRIPTION "Specity whether to use java serialization for marshalling objects. Setting this property improves performance when marshalling objects with very large object graphs."
      ::= { iiopEntry 41  }
   
   
   iiopUseFullRepositoryIdList OBJECT-TYPE
      SYNTAX      OCTET STRING
      MAX-ACCESS  read-only
      STATUS      current
      DESCRIPTION "Specify whether to use full Repository ID lists when sending value type information for custom-marshaled types. Full Repository ID lists allow C++ ORBS to truncate values to base types. For RMI-IIOP and Java ORBs doing this merely increases transmission overhead. JDK ORBs are known to have problems with these so setting this will prevent JDK ORB access from working."
      ::= { iiopEntry 42  }
   
   
   iiopEnableIORServlet OBJECT-TYPE
      SYNTAX      OCTET STRING
      MAX-ACCESS  read-only
      STATUS      current
      DESCRIPTION "Enable getior servlet used to publish COS Naming Service IORs"
      ::= { iiopEntry 43  }
   
   
   iiopSystemSecurity OBJECT-TYPE
      SYNTAX      OCTET STRING
      MAX-ACCESS  read-only
      STATUS      current
      DESCRIPTION "Specify the value System Security. The following variables are affected. clientCertAuthentication, clientAuthentication, identityAssertion confidentiality, integrity. The value set in this MBean would only be picked up if the value set in RTD.xml is 'config'."
      ::= { iiopEntry 44  }
   
   
   iiopUseSerialFormatVersion2 OBJECT-TYPE
      SYNTAX      OCTET STRING
      MAX-ACCESS  read-only
      STATUS      current
      DESCRIPTION "Specify whether to advertise RMI objects and EJBs as supporting RMI-IIOP serial format version 2 for custom marshaled objects."
      ::= { iiopEntry 45  }
   
   
   jdbcConnectionPoolTable OBJECT-TYPE
      SYNTAX      SEQUENCE OF JdbcConnectionPoolEntry
      MAX-ACCESS  not-accessible
      STATUS      current
      DESCRIPTION "This table defines a JDBC connection pool."
      ::= { wls 560  }
      
   
   jdbcConnectionPoolEntry OBJECT-TYPE
      SYNTAX      JdbcConnectionPoolEntry
      MAX-ACCESS  not-accessible
      STATUS      current
      DESCRIPTION "Entry of jdbcConnectionPoolTable"
      INDEX { jdbcConnectionPoolIndex}
      ::= { jdbcConnectionPoolTable 1 }
      
   JdbcConnectionPoolEntry ::=
      SEQUENCE
      {
         jdbcConnectionPoolIndex DisplayString (SIZE (1..16)),
         jdbcConnectionPoolObjectName DisplayString (SIZE (1..256)),
         jdbcConnectionPoolType DisplayString (SIZE (1..64)),
         jdbcConnectionPoolName DisplayString (SIZE (1..64)),
         jdbcConnectionPoolParent DisplayString (SIZE (1..256)),
         jdbcConnectionPoolACLName DisplayString (SIZE (1..32)),
         jdbcConnectionPoolURL DisplayString (SIZE (1..256)),
         jdbcConnectionPoolDriverName DisplayString (SIZE (1..256)),
         jdbcConnectionPoolProperties DisplayString (SIZE (1..2048)),
         jdbcConnectionPoolLoginDelaySeconds INTEGER,
         jdbcConnectionPoolInitialCapacity INTEGER,
         jdbcConnectionPoolMaxCapacity INTEGER,
         jdbcConnectionPoolCapacityIncrement INTEGER,
         jdbcConnectionPoolShrinkingEnabled INTEGER
                     {
                        true(1),
                        false(2)
                     }
         ,
         jdbcConnectionPoolShrinkPeriodMinutes INTEGER,
         jdbcConnectionPoolTestConnectionsOnReserve INTEGER
                     {
                        true(1),
                        false(2)
                     }
         ,
         jdbcConnectionPoolTestConnectionsOnRelease INTEGER
                     {
                        true(1),
                        false(2)
                     }
         ,
         jdbcConnectionPoolSupportsLocalTransaction INTEGER
                     {
                        true(1),
                        false(2)
                     }
         ,
         jdbcConnectionPoolRefreshMinutes INTEGER,
         jdbcConnectionPoolTargets DisplayString (SIZE (1..2048)),
         jdbcConnectionPoolConnectionCreationRetryFrequencySeconds INTEGER,
         jdbcConnectionPoolConnectionReserveTimeoutSeconds INTEGER,
         jdbcConnectionPoolHighestNumUnavailable INTEGER,
         jdbcConnectionPoolHighestNumWaiters INTEGER,
         jdbcConnectionPoolInactiveConnectionTimeoutSeconds INTEGER,
         jdbcConnectionPoolTestTableName DisplayString,
         jdbcConnectionPoolKeepLogicalConnOpenOnRelease INTEGER,
         jdbcConnectionPoolKeepXAConnTillTxComplete INTEGER,
         jdbcConnectionPoolNewXAConnForCommit INTEGER,
         jdbcConnectionPoolShrinkFrequencySeconds INTEGER,
         jdbcConnectionPoolStatementCacheSize INTEGER,
         jdbcConnectionPoolStatementCacheType DisplayString,
         jdbcConnectionPoolTestConnectionsOnCreate INTEGER,
         jdbcConnectionPoolTestFrequencySeconds INTEGER,
         jdbcConnectionPoolXAEndOnlyOnce INTEGER,
         jdbcConnectionPoolConnLeakProfilingEnabled INTEGER
      }
      
   
   jdbcConnectionPoolIndex OBJECT-TYPE
      SYNTAX      DisplayString (SIZE (1..16))
      MAX-ACCESS  read-only
      STATUS      current
      DESCRIPTION "Unique value directed from ObjectName which is used as table index"
      ::= { jdbcConnectionPoolEntry 1  }
   
   
   jdbcConnectionPoolObjectName OBJECT-TYPE
      SYNTAX      DisplayString (SIZE (1..256))
      MAX-ACCESS  read-only
      STATUS      current
      DESCRIPTION "JMX-standard MBean name"
      ::= { jdbcConnectionPoolEntry 5  }
   
   
   jdbcConnectionPoolType OBJECT-TYPE
      SYNTAX      DisplayString (SIZE (1..64))
      MAX-ACCESS  read-only
      STATUS      current
      DESCRIPTION "BEA-proprietary MBean type"
      ::= { jdbcConnectionPoolEntry 10  }
   
   
   jdbcConnectionPoolName OBJECT-TYPE
      SYNTAX      DisplayString (SIZE (1..64))
      MAX-ACCESS  read-only
      STATUS      current
      DESCRIPTION "BEA-proprietary MBean name"
      ::= { jdbcConnectionPoolEntry 15  }
   
   
   jdbcConnectionPoolParent OBJECT-TYPE
      SYNTAX      DisplayString (SIZE (1..256))
      MAX-ACCESS  read-only
      STATUS      current
      DESCRIPTION "BEA-proprietary Parent object's identification, with syntax
      <type>:<name>"
      ::= { jdbcConnectionPoolEntry 20  }
   
   
   jdbcConnectionPoolACLName OBJECT-TYPE
      SYNTAX      DisplayString (SIZE (1..32))
      MAX-ACCESS  read-only
      STATUS      current
      DESCRIPTION "JDBC Connection ACL Name."
      ::= { jdbcConnectionPoolEntry 25  }
   
   
   jdbcConnectionPoolURL OBJECT-TYPE
      SYNTAX      DisplayString (SIZE (1..256))
      MAX-ACCESS  read-only
      STATUS      current
      DESCRIPTION "The database connection URL."
      ::= { jdbcConnectionPoolEntry 30  }
   
   
   jdbcConnectionPoolDriverName OBJECT-TYPE
      SYNTAX      DisplayString (SIZE (1..256))
      MAX-ACCESS  read-only
      STATUS      current
      DESCRIPTION "The JDBC driver class name."
      ::= { jdbcConnectionPoolEntry 35  }
   
   
   jdbcConnectionPoolProperties OBJECT-TYPE
      SYNTAX      DisplayString (SIZE (1..2048))
      MAX-ACCESS  read-only
      STATUS      current
      DESCRIPTION "The list of properties passed to the the driver."
      ::= { jdbcConnectionPoolEntry 40  }
   
   
   jdbcConnectionPoolLoginDelaySeconds OBJECT-TYPE
      SYNTAX      INTEGER
      MAX-ACCESS  read-only
      STATUS      current
      DESCRIPTION "The number of second to delay between logins when creating the pool."
      ::= { jdbcConnectionPoolEntry 45  }
   
   
   jdbcConnectionPoolInitialCapacity OBJECT-TYPE
      SYNTAX      INTEGER
      MAX-ACCESS  read-only
      STATUS      current
      DESCRIPTION "The initial number of connections."
      ::= { jdbcConnectionPoolEntry 50  }
   
   
   jdbcConnectionPoolMaxCapacity OBJECT-TYPE
      SYNTAX      INTEGER
      MAX-ACCESS  read-only
      STATUS      current
      DESCRIPTION "The maximum number of connections."
      ::= { jdbcConnectionPoolEntry 55  }
   
   
   jdbcConnectionPoolCapacityIncrement OBJECT-TYPE
      SYNTAX      INTEGER
      MAX-ACCESS  read-only
      STATUS      current
      DESCRIPTION "The increment by which the pool capacity is expanded."
      ::= { jdbcConnectionPoolEntry 60  }
   
   
   jdbcConnectionPoolShrinkingEnabled OBJECT-TYPE
      SYNTAX      INTEGER
                  {
                     true(1),
                     false(2)
                  }
      
      MAX-ACCESS  read-only
      STATUS      current
      DESCRIPTION "A boolean value (true Or false). Set to <code>true</code> to enable pool shrinking."
      ::= { jdbcConnectionPoolEntry 65  }
   
   
   jdbcConnectionPoolShrinkPeriodMinutes OBJECT-TYPE
      SYNTAX      INTEGER
      MAX-ACCESS  read-only
      STATUS      current
      DESCRIPTION "Shrink period for the pool in minutes."
      ::= { jdbcConnectionPoolEntry 70  }
   
   
   jdbcConnectionPoolTestConnectionsOnReserve OBJECT-TYPE
      SYNTAX      INTEGER
                  {
                     true(1),
                     false(2)
                  }
      
      MAX-ACCESS  read-only
      STATUS      current
      DESCRIPTION "Specifies if test connections on reserve enabled."
      ::= { jdbcConnectionPoolEntry 80  }
   
   
   jdbcConnectionPoolTestConnectionsOnRelease OBJECT-TYPE
      SYNTAX      INTEGER
                  {
                     true(1),
                     false(2)
                  }
      
      MAX-ACCESS  read-only
      STATUS      current
      DESCRIPTION "Specifies if test connections on release enabled."
      ::= { jdbcConnectionPoolEntry 85  }
   
   
   jdbcConnectionPoolSupportsLocalTransaction OBJECT-TYPE
      SYNTAX      INTEGER
                  {
                     true(1),
                     false(2)
                  }
      
      MAX-ACCESS  read-only
      STATUS      current
      DESCRIPTION "A boolean value (true Or false). This property applies to XA connection pools only, and is ignored
      for non-XA driver."
      ::= { jdbcConnectionPoolEntry 90  }
   
   
   jdbcConnectionPoolRefreshMinutes OBJECT-TYPE
      SYNTAX      INTEGER
      MAX-ACCESS  read-only
      STATUS      current
      DESCRIPTION "Connection pool refresh minutes."
      ::= { jdbcConnectionPoolEntry 95  }
   
   
   jdbcConnectionPoolTargets OBJECT-TYPE
      SYNTAX      DisplayString (SIZE (1..2048))
      MAX-ACCESS  read-only
      STATUS      current
      DESCRIPTION "Targets on which these jdbc Connection pools are deployed."
      ::= { jdbcConnectionPoolEntry 100  }
   
   
   jdbcConnectionPoolConnectionCreationRetryFrequencySeconds OBJECT-TYPE
      SYNTAX      INTEGER
      MAX-ACCESS  read-only
      STATUS      current
      DESCRIPTION "Gets the connectionCreationRetryFrequencySeconds attribute of the JDBCConnectionPoolMBean object"
      ::= { jdbcConnectionPoolEntry 101  }
   
   
   jdbcConnectionPoolConnectionReserveTimeoutSeconds OBJECT-TYPE
      SYNTAX      INTEGER
      MAX-ACCESS  read-only
      STATUS      current
      DESCRIPTION "The number of seconds after which a call to reserve a connection from the pool"
      ::= { jdbcConnectionPoolEntry 102  }
   
   
   jdbcConnectionPoolHighestNumUnavailable OBJECT-TYPE
      SYNTAX      INTEGER
      MAX-ACCESS  read-only
      STATUS      current
      DESCRIPTION "Gets the highestNumUnavailable attribute of the JDBCConnectionPoolMBean object"
      ::= { jdbcConnectionPoolEntry 103  }
   
   
   jdbcConnectionPoolHighestNumWaiters OBJECT-TYPE
      SYNTAX      INTEGER
      MAX-ACCESS  read-only
      STATUS      current
      DESCRIPTION "Gets the highestNumWaiters attribute of the JDBCConnectionPoolMBean object"
      ::= { jdbcConnectionPoolEntry 104  }
   
   
   jdbcConnectionPoolInactiveConnectionTimeoutSeconds OBJECT-TYPE
      SYNTAX      INTEGER
      MAX-ACCESS  read-only
      STATUS      current
      DESCRIPTION "Gets the inactiveConnectionTimeoutSeconds attribute of the JDBCConnectionPoolMBean object"
      ::= { jdbcConnectionPoolEntry 105  }
   
   
   jdbcConnectionPoolTestTableName OBJECT-TYPE
      SYNTAX      DisplayString
      MAX-ACCESS  read-only
      STATUS      current
      DESCRIPTION "The name of the table used when testing a physical database connection."
      ::= { jdbcConnectionPoolEntry 106  }
   
   
   jdbcConnectionPoolKeepLogicalConnOpenOnRelease OBJECT-TYPE
      SYNTAX      INTEGER
      MAX-ACCESS  read-only
      STATUS      current
      DESCRIPTION "if the logical JDBC connection is kept open when the physical XA connection is returned to the XA connection pool."
      ::= { jdbcConnectionPoolEntry 107  }
   
   
   jdbcConnectionPoolKeepXAConnTillTxComplete OBJECT-TYPE
      SYNTAX      INTEGER
      MAX-ACCESS  read-only
      STATUS      current
      DESCRIPTION "if the XA connection pool associates the same XA connection with the distributed transaction until the transaction completes."
      ::= { jdbcConnectionPoolEntry 108  }
   
   
   jdbcConnectionPoolNewXAConnForCommit OBJECT-TYPE
      SYNTAX      INTEGER
      MAX-ACCESS  read-only
      STATUS      current
      DESCRIPTION "if a dedicated XA connection is used for commit/rollback processing of a particular distributed transaction."
      ::= { jdbcConnectionPoolEntry 109  }
   
   
   jdbcConnectionPoolShrinkFrequencySeconds OBJECT-TYPE
      SYNTAX      INTEGER
      MAX-ACCESS  read-only
      STATUS      current
      DESCRIPTION "Number of seconds to wait before shrinking a connection pool that has incrementally increased to meet demand."
      ::= { jdbcConnectionPoolEntry 110  }
   
   
   jdbcConnectionPoolStatementCacheSize OBJECT-TYPE
      SYNTAX      INTEGER
      MAX-ACCESS  read-only
      STATUS      current
      DESCRIPTION "Generated Object."
      ::= { jdbcConnectionPoolEntry 111  }
   
   
   jdbcConnectionPoolStatementCacheType OBJECT-TYPE
      SYNTAX      DisplayString
      MAX-ACCESS  read-only
      STATUS      current
      DESCRIPTION "Generated Object."
      ::= { jdbcConnectionPoolEntry 112  }
   
   
   jdbcConnectionPoolTestConnectionsOnCreate OBJECT-TYPE
      SYNTAX      INTEGER
      MAX-ACCESS  read-only
      STATUS      current
      DESCRIPTION "Generated Object."
      ::= { jdbcConnectionPoolEntry 113  }
   
   
   jdbcConnectionPoolTestFrequencySeconds OBJECT-TYPE
      SYNTAX      INTEGER
      MAX-ACCESS  read-only
      STATUS      current
      DESCRIPTION "Generated Object."
      ::= { jdbcConnectionPoolEntry 114  }
   
   
   jdbcConnectionPoolXAEndOnlyOnce OBJECT-TYPE
      SYNTAX      INTEGER
      MAX-ACCESS  read-only
      STATUS      current
      DESCRIPTION "Generated Object."
      ::= { jdbcConnectionPoolEntry 115  }
   
   
   jdbcConnectionPoolConnLeakProfilingEnabled OBJECT-TYPE
      SYNTAX      INTEGER
      MAX-ACCESS  read-only
      STATUS      current
      DESCRIPTION "Generated Object."
      ::= { jdbcConnectionPoolEntry 116  }
   
   
   jdbcDataSourceTable OBJECT-TYPE
      SYNTAX      SEQUENCE OF JdbcDataSourceEntry
      MAX-ACCESS  not-accessible
      STATUS      current
      DESCRIPTION "This table defines a JDBC connection pool."
      ::= { wls 570  }
      
   
   jdbcDataSourceEntry OBJECT-TYPE
      SYNTAX      JdbcDataSourceEntry
      MAX-ACCESS  not-accessible
      STATUS      current
      DESCRIPTION "Entry of jdbcDataSourceTable"
      INDEX { jdbcDataSourceIndex}
      ::= { jdbcDataSourceTable 1 }
      
   JdbcDataSourceEntry ::=
      SEQUENCE
      {
         jdbcDataSourceIndex  DisplayString (SIZE (1..16)),
         jdbcDataSourceObjectName DisplayString (SIZE (1..256)),
         jdbcDataSourceType   DisplayString (SIZE (1..64)),
         jdbcDataSourceName   DisplayString (SIZE (1..64)),
         jdbcDataSourceParent DisplayString (SIZE (1..256)),
         jdbcDataSourceJNDIName DisplayString (SIZE (1..256)),
         jdbcDataSourcePoolName DisplayString (SIZE (1..64)),
         jdbcDataSourceTargets DisplayString (SIZE (1..2048)),
         jdbcDataSourceRowPrefetchEnabled INTEGER
                     {
                        true(1),
                        false(2)
                     }
         ,
         jdbcDataSourceRowPrefetchSize INTEGER,
         jdbcDataSourceStreamChunkSize INTEGER
      }
      
   
   jdbcDataSourceIndex OBJECT-TYPE
      SYNTAX      DisplayString (SIZE (1..16))
      MAX-ACCESS  read-only
      STATUS      current
      DESCRIPTION "Unique value directed from ObjectName which is used as table index"
      ::= { jdbcDataSourceEntry 1  }
   
   
   jdbcDataSourceObjectName OBJECT-TYPE
      SYNTAX      DisplayString (SIZE (1..256))
      MAX-ACCESS  read-only
      STATUS      current
      DESCRIPTION "JMX-standard MBean name"
      ::= { jdbcDataSourceEntry 5  }
   
   
   jdbcDataSourceType OBJECT-TYPE
      SYNTAX      DisplayString (SIZE (1..64))
      MAX-ACCESS  read-only
      STATUS      current
      DESCRIPTION "BEA-proprietary MBean type"
      ::= { jdbcDataSourceEntry 10  }
   
   
   jdbcDataSourceName OBJECT-TYPE
      SYNTAX      DisplayString (SIZE (1..64))
      MAX-ACCESS  read-only
      STATUS      current
      DESCRIPTION "BEA-proprietary MBean name"
      ::= { jdbcDataSourceEntry 15  }
   
   
   jdbcDataSourceParent OBJECT-TYPE
      SYNTAX      DisplayString (SIZE (1..256))
      MAX-ACCESS  read-only
      STATUS      current
      DESCRIPTION "BEA-proprietary Parent object's identification, with syntax
      <type>:<name>"
      ::= { jdbcDataSourceEntry 20  }
   
   
   jdbcDataSourceJNDIName OBJECT-TYPE
      SYNTAX      DisplayString (SIZE (1..256))
      MAX-ACCESS  read-only
      STATUS      current
      DESCRIPTION ""
      ::= { jdbcDataSourceEntry 25  }
   
   
   jdbcDataSourcePoolName OBJECT-TYPE
      SYNTAX      DisplayString (SIZE (1..64))
      MAX-ACCESS  read-only
      STATUS      current
      DESCRIPTION ""
      ::= { jdbcDataSourceEntry 30  }
   
   
   jdbcDataSourceTargets OBJECT-TYPE
      SYNTAX      DisplayString (SIZE (1..2048))
      MAX-ACCESS  read-only
      STATUS      current
      DESCRIPTION "targets on which this deployment is deployed."
      ::= { jdbcDataSourceEntry 35  }
   
   
   jdbcDataSourceRowPrefetchEnabled OBJECT-TYPE
      SYNTAX      INTEGER
                  {
                     true(1),
                     false(2)
                  }
      
      MAX-ACCESS  read-only
      STATUS      current
      DESCRIPTION "is row caching enabled."
      ::= { jdbcDataSourceEntry 40  }
   
   
   jdbcDataSourceRowPrefetchSize OBJECT-TYPE
      SYNTAX      INTEGER
      MAX-ACCESS  read-only
      STATUS      current
      DESCRIPTION "Number of rows to prefetch between client and WebLogic Server when not in the same JVM."
      ::= { jdbcDataSourceEntry 45  }
   
   
   jdbcDataSourceStreamChunkSize OBJECT-TYPE
      SYNTAX      INTEGER
      MAX-ACCESS  read-only
      STATUS      current
      DESCRIPTION "Streaming datatypes (e.g. blob/clob) will be pulled in StreamChunkSize sized chunks 
      from the WebLogic Server to the client as needed."
      ::= { jdbcDataSourceEntry 50  }
   
   
   jdbcDataSourceFactoryTable OBJECT-TYPE
      SYNTAX      SEQUENCE OF JdbcDataSourceFactoryEntry
      MAX-ACCESS  not-accessible
      STATUS      current
      DESCRIPTION "This table represents a jdbcDataSourceFactory in the domain."
      ::= { wls 575  }
      
   
   jdbcDataSourceFactoryEntry OBJECT-TYPE
      SYNTAX      JdbcDataSourceFactoryEntry
      MAX-ACCESS  not-accessible
      STATUS      current
      DESCRIPTION "Entry of jdbcDataSourceFactoryTable"
      INDEX { jdbcDataSourceFactoryIndex}
      ::= { jdbcDataSourceFactoryTable 1 }
      
   JdbcDataSourceFactoryEntry ::=
      SEQUENCE
      {
         jdbcDataSourceFactoryIndex DisplayString (SIZE (1..16)),
         jdbcDataSourceFactoryObjectName DisplayString (SIZE (1..256)),
         jdbcDataSourceFactoryType DisplayString (SIZE (1..64)),
         jdbcDataSourceFactoryName DisplayString (SIZE (1..64)),
         jdbcDataSourceFactoryParent DisplayString (SIZE (1..256)),
         jdbcDataSourceFactoryDriverClassName DisplayString (SIZE (1..256)),
         jdbcDataSourceFactoryFactoryName DisplayString (SIZE (1..256)),
         jdbcDataSourceFactoryURL DisplayString (SIZE (1..256)),
         jdbcDataSourceFactoryUserName DisplayString (SIZE (1..256))
      }
      
   
   jdbcDataSourceFactoryIndex OBJECT-TYPE
      SYNTAX      DisplayString (SIZE (1..16))
      MAX-ACCESS  read-only
      STATUS      current
      DESCRIPTION "Unique value directed from ObjectName which is used as table index"
      ::= { jdbcDataSourceFactoryEntry 1  }
   
   
   jdbcDataSourceFactoryObjectName OBJECT-TYPE
      SYNTAX      DisplayString (SIZE (1..256))
      MAX-ACCESS  read-only
      STATUS      current
      DESCRIPTION "JMX-standard MBean name"
      ::= { jdbcDataSourceFactoryEntry 5  }
   
   
   jdbcDataSourceFactoryType OBJECT-TYPE
      SYNTAX      DisplayString (SIZE (1..64))
      MAX-ACCESS  read-only
      STATUS      current
      DESCRIPTION "BEA-proprietary MBean type"
      ::= { jdbcDataSourceFactoryEntry 10  }
   
   
   jdbcDataSourceFactoryName OBJECT-TYPE
      SYNTAX      DisplayString (SIZE (1..64))
      MAX-ACCESS  read-only
      STATUS      current
      DESCRIPTION "BEA-proprietary MBean name"
      ::= { jdbcDataSourceFactoryEntry 15  }
   
   
   jdbcDataSourceFactoryParent OBJECT-TYPE
      SYNTAX      DisplayString (SIZE (1..256))
      MAX-ACCESS  read-only
      STATUS      current
      DESCRIPTION "BEA-proprietary Parent object's identification, with syntax
      <type>:<name>"
      ::= { jdbcDataSourceFactoryEntry 20  }
   
   
   jdbcDataSourceFactoryDriverClassName OBJECT-TYPE
      SYNTAX      DisplayString (SIZE (1..256))
      MAX-ACCESS  read-only
      STATUS      current
      DESCRIPTION "The name of the driver. This may be overridden by
      * driver-name in the descriptor."
      ::= { jdbcDataSourceFactoryEntry 25  }
   
   
   jdbcDataSourceFactoryFactoryName OBJECT-TYPE
      SYNTAX      DisplayString (SIZE (1..256))
      MAX-ACCESS  read-only
      STATUS      current
      DESCRIPTION "The name of this data source factory. This is referenced
      * from the connection-factory element in weblogic-application.xml."
      ::= { jdbcDataSourceFactoryEntry 30  }
   
   
   jdbcDataSourceFactoryURL OBJECT-TYPE
      SYNTAX      DisplayString (SIZE (1..256))
      MAX-ACCESS  read-only
      STATUS      current
      DESCRIPTION "The connection URL. This may be overridden by url in the descriptor."
      ::= { jdbcDataSourceFactoryEntry 35  }
   
   
   jdbcDataSourceFactoryUserName OBJECT-TYPE
      SYNTAX      DisplayString (SIZE (1..256))
      MAX-ACCESS  read-only
      STATUS      current
      DESCRIPTION "The database user name. This may be overridden by
      * user-name in the descriptor."
      ::= { jdbcDataSourceFactoryEntry 40  }
   
   
   jdbcMultiPoolTable OBJECT-TYPE
      SYNTAX      SEQUENCE OF JdbcMultiPoolEntry
      MAX-ACCESS  not-accessible
      STATUS      current
      DESCRIPTION "This table is use to defines a 
      <b>JDBC meta pool</b>."
      ::= { wls 580  }
      
   
   jdbcMultiPoolEntry OBJECT-TYPE
      SYNTAX      JdbcMultiPoolEntry
      MAX-ACCESS  not-accessible
      STATUS      current
      DESCRIPTION "Entry of jdbcMultiPoolTable"
      INDEX { jdbcMultiPoolIndex}
      ::= { jdbcMultiPoolTable 1 }
      
   JdbcMultiPoolEntry ::=
      SEQUENCE
      {
         jdbcMultiPoolIndex   DisplayString (SIZE (1..16)),
         jdbcMultiPoolObjectName DisplayString (SIZE (1..256)),
         jdbcMultiPoolType    DisplayString (SIZE (1..64)),
         jdbcMultiPoolName    DisplayString (SIZE (1..64)),
         jdbcMultiPoolParent  DisplayString (SIZE (1..256)),
         jdbcMultiPoolACLName DisplayString (SIZE (1..32)),
         jdbcMultiPoolPoolList DisplayString (SIZE (1..2048)),
         jdbcMultiPoolLoadBalance INTEGER
                     {
                        true(1),
                        false(2)
                     }
         ,
         jdbcMultiPoolHighAvail INTEGER
                     {
                        true(1),
                        false(2)
                     }
         ,
         jdbcMultiPoolTargets DisplayString (SIZE (1..2048))
      }
      
   
   jdbcMultiPoolIndex OBJECT-TYPE
      SYNTAX      DisplayString (SIZE (1..16))
      MAX-ACCESS  read-only
      STATUS      current
      DESCRIPTION "Unique value directed from ObjectName which is used as table index"
      ::= { jdbcMultiPoolEntry 1  }
   
   
   jdbcMultiPoolObjectName OBJECT-TYPE
      SYNTAX      DisplayString (SIZE (1..256))
      MAX-ACCESS  read-only
      STATUS      current
      DESCRIPTION "JMX-standard MBean name"
      ::= { jdbcMultiPoolEntry 5  }
   
   
   jdbcMultiPoolType OBJECT-TYPE
      SYNTAX      DisplayString (SIZE (1..64))
      MAX-ACCESS  read-only
      STATUS      current
      DESCRIPTION "BEA-proprietary MBean type"
      ::= { jdbcMultiPoolEntry 10  }
   
   
   jdbcMultiPoolName OBJECT-TYPE
      SYNTAX      DisplayString (SIZE (1..64))
      MAX-ACCESS  read-only
      STATUS      current
      DESCRIPTION "BEA-proprietary MBean name"
      ::= { jdbcMultiPoolEntry 15  }
   
   
   jdbcMultiPoolParent OBJECT-TYPE
      SYNTAX      DisplayString (SIZE (1..256))
      MAX-ACCESS  read-only
      STATUS      current
      DESCRIPTION "BEA-proprietary Parent object's identification, with syntax
      <type>:<name>"
      ::= { jdbcMultiPoolEntry 20  }
   
   
   jdbcMultiPoolACLName OBJECT-TYPE
      SYNTAX      DisplayString (SIZE (1..32))
      MAX-ACCESS  read-only
      STATUS      current
      DESCRIPTION "jdbcMultiPool the ACL list for this meta pool"
      ::= { jdbcMultiPoolEntry 25  }
   
   
   jdbcMultiPoolPoolList OBJECT-TYPE
      SYNTAX      DisplayString (SIZE (1..2048))
      MAX-ACCESS  read-only
      STATUS      current
      DESCRIPTION "retrieves the list of connection pools in the meta pool"
      ::= { jdbcMultiPoolEntry 30  }
   
   
   jdbcMultiPoolLoadBalance OBJECT-TYPE
      SYNTAX      INTEGER
                  {
                     true(1),
                     false(2)
                  }
      
      MAX-ACCESS  read-only
      STATUS      current
      DESCRIPTION "A boolean value (true Or false). finds out whether load balancing is used in this meta pool."
      ::= { jdbcMultiPoolEntry 35  }
   
   
   jdbcMultiPoolHighAvail OBJECT-TYPE
      SYNTAX      INTEGER
                  {
                     true(1),
                     false(2)
                  }
      
      MAX-ACCESS  read-only
      STATUS      current
      DESCRIPTION "A boolean value (true Or false). finds out whether high availability is used in this meta pool"
      ::= { jdbcMultiPoolEntry 40  }
   
   
   jdbcMultiPoolTargets OBJECT-TYPE
      SYNTAX      DisplayString (SIZE (1..2048))
      MAX-ACCESS  read-only
      STATUS      current
      DESCRIPTION "targets on which this deployment is deployed."
      ::= { jdbcMultiPoolEntry 45  }
   
   
   jdbcTxDataSourceTable OBJECT-TYPE
      SYNTAX      SEQUENCE OF JdbcTxDataSourceEntry
      MAX-ACCESS  not-accessible
      STATUS      current
      DESCRIPTION "This table is used to defines a JDBC meta pool."
      ::= { wls 590  }
      
   
   jdbcTxDataSourceEntry OBJECT-TYPE
      SYNTAX      JdbcTxDataSourceEntry
      MAX-ACCESS  not-accessible
      STATUS      current
      DESCRIPTION "Entry of jdbcTxDataSourceTable"
      INDEX { jdbcTxDataSourceIndex}
      ::= { jdbcTxDataSourceTable 1 }
      
   JdbcTxDataSourceEntry ::=
      SEQUENCE
      {
         jdbcTxDataSourceIndex DisplayString (SIZE (1..16)),
         jdbcTxDataSourceObjectName DisplayString (SIZE (1..256)),
         jdbcTxDataSourceType DisplayString (SIZE (1..64)),
         jdbcTxDataSourceName DisplayString (SIZE (1..64)),
         jdbcTxDataSourceParent DisplayString (SIZE (1..256)),
         jdbcTxDataSourceJNDIName DisplayString (SIZE (1..256)),
         jdbcTxDataSourcePoolName DisplayString (SIZE (1..64)),
         jdbcTxDataSourceEnableTwoPhaseCommit INTEGER
                     {
                        true(1),
                        false(2)
                     }
         ,
         jdbcTxDataSourceTargets DisplayString (SIZE (1..2048)),
         jdbcTxDataSourceRowPrefetchEnabled INTEGER
                     {
                        true(1),
                        false(2)
                     }
         ,
         jdbcTxDataSourceRowPrefetchSize INTEGER,
         jdbcTxDataSourceStreamChunkSize INTEGER
      }
      
   
   jdbcTxDataSourceIndex OBJECT-TYPE
      SYNTAX      DisplayString (SIZE (1..16))
      MAX-ACCESS  read-only
      STATUS      current
      DESCRIPTION "Unique value directed from ObjectName which is used as table index"
      ::= { jdbcTxDataSourceEntry 1  }
   
   
   jdbcTxDataSourceObjectName OBJECT-TYPE
      SYNTAX      DisplayString (SIZE (1..256))
      MAX-ACCESS  read-only
      STATUS      current
      DESCRIPTION "JMX-standard MBean name"
      ::= { jdbcTxDataSourceEntry 5  }
   
   
   jdbcTxDataSourceType OBJECT-TYPE
      SYNTAX      DisplayString (SIZE (1..64))
      MAX-ACCESS  read-only
      STATUS      current
      DESCRIPTION "BEA-proprietary MBean type"
      ::= { jdbcTxDataSourceEntry 10  }
   
   
   jdbcTxDataSourceName OBJECT-TYPE
      SYNTAX      DisplayString (SIZE (1..64))
      MAX-ACCESS  read-only
      STATUS      current
      DESCRIPTION "BEA-proprietary MBean name"
      ::= { jdbcTxDataSourceEntry 15  }
   
   
   jdbcTxDataSourceParent OBJECT-TYPE
      SYNTAX      DisplayString (SIZE (1..256))
      MAX-ACCESS  read-only
      STATUS      current
      DESCRIPTION "BEA-proprietary Parent object's identification, with syntax
      <type>:<name>"
      ::= { jdbcTxDataSourceEntry 20  }
   
   
   jdbcTxDataSourceJNDIName OBJECT-TYPE
      SYNTAX      DisplayString (SIZE (1..256))
      MAX-ACCESS  read-only
      STATUS      current
      DESCRIPTION "The JNDI path to where this TxDataSource is bound. Applications that look up the JNDI path 
      will get a <CODE>javax.sql.DataSource</CODE> instance that correspond to this TxDataSource."
      ::= { jdbcTxDataSourceEntry 25  }
   
   
   jdbcTxDataSourcePoolName OBJECT-TYPE
      SYNTAX      DisplayString (SIZE (1..64))
      MAX-ACCESS  read-only
      STATUS      current
      DESCRIPTION "The name of the JDBC connection pool that is associated with this TxDataSource"
      ::= { jdbcTxDataSourceEntry 30  }
   
   
   jdbcTxDataSourceEnableTwoPhaseCommit OBJECT-TYPE
      SYNTAX      INTEGER
                  {
                     true(1),
                     false(2)
                  }
      
      MAX-ACCESS  read-only
      STATUS      current
      DESCRIPTION "Specifies whether this TxDataSource is enabled to participate in distributed 
      transaction if this TxDataSource is associated with a non-XA connection pool, 
      and if more than one resources participate in the distributed transaction."
      ::= { jdbcTxDataSourceEntry 35  }
   
   
   jdbcTxDataSourceTargets OBJECT-TYPE
      SYNTAX      DisplayString (SIZE (1..2048))
      MAX-ACCESS  read-only
      STATUS      current
      DESCRIPTION "The targets where this jdbc data source is deployed."
      ::= { jdbcTxDataSourceEntry 40  }
   
   
   jdbcTxDataSourceRowPrefetchEnabled OBJECT-TYPE
      SYNTAX      INTEGER
                  {
                     true(1),
                     false(2)
                  }
      
      MAX-ACCESS  read-only
      STATUS      current
      DESCRIPTION "Whether to enable row prefetching between client and WebLogic Server for each ResultSet.  
      The WebLogic Server will ignore this setting and not use row prefetching when the client 
      and WebLogic Server are in the same JVM."
      ::= { jdbcTxDataSourceEntry 45  }
   
   
   jdbcTxDataSourceRowPrefetchSize OBJECT-TYPE
      SYNTAX      INTEGER
      MAX-ACCESS  read-only
      STATUS      current
      DESCRIPTION "Number of rows to prefetch between client and WebLogic Server when not in the same JVM."
      ::= { jdbcTxDataSourceEntry 50  }
   
   
   jdbcTxDataSourceStreamChunkSize OBJECT-TYPE
      SYNTAX      INTEGER
      MAX-ACCESS  read-only
      STATUS      current
      DESCRIPTION "Streaming datatypes (e.g. blob/clob) will be pulled in StreamChunkSize sized chunks 
      from the WebLogic Server to the client as needed."
      ::= { jdbcTxDataSourceEntry 55  }
   
   
   jmsBridgeDestinationTable OBJECT-TYPE
      SYNTAX      SEQUENCE OF JmsBridgeDestinationEntry
      MAX-ACCESS  not-accessible
      STATUS      current
      DESCRIPTION "This table is use to defines a 
      <b>JDBC meta pool</b>."
      ::= { wls 595  }
      
   
   jmsBridgeDestinationEntry OBJECT-TYPE
      SYNTAX      JmsBridgeDestinationEntry
      MAX-ACCESS  not-accessible
      STATUS      current
      DESCRIPTION "Entry of jmsBridgeDestinationTable"
      INDEX { jmsBridgeDestinationIndex}
      ::= { jmsBridgeDestinationTable 1 }
      
   JmsBridgeDestinationEntry ::=
      SEQUENCE
      {
         jmsBridgeDestinationIndex DisplayString (SIZE (1..16)),
         jmsBridgeDestinationObjectName DisplayString (SIZE (1..256)),
         jmsBridgeDestinationType DisplayString (SIZE (1..64)),
         jmsBridgeDestinationName DisplayString (SIZE (1..64)),
         jmsBridgeDestinationParent DisplayString (SIZE (1..256)),
         jmsBridgeDestinationConnectionFactoryJNDIName DisplayString (SIZE (1..32)),
         jmsBridgeDestinationConnectionURL DisplayString (SIZE (1..2048)),
         jmsBridgeDestinationDestinationJNDIName DisplayString (SIZE (1..2048)),
         jmsBridgeDestinationDestinationType DisplayString (SIZE (1..2048)),
         jmsBridgeDestinationInitialContextFactory DisplayString (SIZE (1..2048)),
         jmsBridgeDestinationAdapterJNDIName OCTET STRING,
         jmsBridgeDestinationClasspath OCTET STRING,
         jmsBridgeDestinationUserName OCTET STRING
      }
      
   
   jmsBridgeDestinationIndex OBJECT-TYPE
      SYNTAX      DisplayString (SIZE (1..16))
      MAX-ACCESS  read-only
      STATUS      current
      DESCRIPTION "Unique value directed from ObjectName which is used as table index"
      ::= { jmsBridgeDestinationEntry 1  }
   
   
   jmsBridgeDestinationObjectName OBJECT-TYPE
      SYNTAX      DisplayString (SIZE (1..256))
      MAX-ACCESS  read-only
      STATUS      current
      DESCRIPTION "JMX-standard MBean name"
      ::= { jmsBridgeDestinationEntry 5  }
   
   
   jmsBridgeDestinationType OBJECT-TYPE
      SYNTAX      DisplayString (SIZE (1..64))
      MAX-ACCESS  read-only
      STATUS      current
      DESCRIPTION "BEA-proprietary MBean type"
      ::= { jmsBridgeDestinationEntry 10  }
   
   
   jmsBridgeDestinationName OBJECT-TYPE
      SYNTAX      DisplayString (SIZE (1..64))
      MAX-ACCESS  read-only
      STATUS      current
      DESCRIPTION "BEA-proprietary MBean name"
      ::= { jmsBridgeDestinationEntry 15  }
   
   
   jmsBridgeDestinationParent OBJECT-TYPE
      SYNTAX      DisplayString (SIZE (1..256))
      MAX-ACCESS  read-only
      STATUS      current
      DESCRIPTION "BEA-proprietary Parent object's identification, with syntax
      <type>:<name>"
      ::= { jmsBridgeDestinationEntry 20  }
   
   
   jmsBridgeDestinationConnectionFactoryJNDIName OBJECT-TYPE
      SYNTAX      DisplayString (SIZE (1..32))
      MAX-ACCESS  read-only
      STATUS      current
      DESCRIPTION "Defines the connection factory's JNDI name for a JMS bridge destination.
      * This attribute is only applicable to JMS destinations."
      ::= { jmsBridgeDestinationEntry 25  }
   
   
   jmsBridgeDestinationConnectionURL OBJECT-TYPE
      SYNTAX      DisplayString (SIZE (1..2048))
      MAX-ACCESS  read-only
      STATUS      current
      DESCRIPTION "Defines the connection URL for a JMS bridge destination.
      * This attribute is only applicable to JMS destinations"
      ::= { jmsBridgeDestinationEntry 30  }
   
   
   jmsBridgeDestinationDestinationJNDIName OBJECT-TYPE
      SYNTAX      DisplayString (SIZE (1..2048))
      MAX-ACCESS  read-only
      STATUS      current
      DESCRIPTION "Defines the destination JNDI name (Queue or Topic) for a JMS bridge destination.
      * This attribute is only applicable to JMS destinations."
      ::= { jmsBridgeDestinationEntry 35  }
   
   
   jmsBridgeDestinationDestinationType OBJECT-TYPE
      SYNTAX      DisplayString (SIZE (1..2048))
      MAX-ACCESS  read-only
      STATUS      current
      DESCRIPTION "Defines the destination type (Queue or Topic) for a JMS bridge destination.
      * This attribute is only applicable to JMS destinations"
      ::= { jmsBridgeDestinationEntry 40  }
   
   
   jmsBridgeDestinationInitialContextFactory OBJECT-TYPE
      SYNTAX      DisplayString (SIZE (1..2048))
      MAX-ACCESS  read-only
      STATUS      current
      DESCRIPTION "Defines the initial context factory name for a JMS bridge destination.
      * This attribute is only applicable to JMS destinations."
      ::= { jmsBridgeDestinationEntry 45  }
   
   
   jmsBridgeDestinationAdapterJNDIName OBJECT-TYPE
      SYNTAX      OCTET STRING
      MAX-ACCESS  read-only
      STATUS      current
      DESCRIPTION "The JNDI name of the adapter used to communicate with the specified destination.  This name is specified in the adapter's deployment descriptor file and is used by the WebLogic Server Connector container to bind the adapter in WebLogic Server JNDI."
      ::= { jmsBridgeDestinationEntry 46  }
   
   
   jmsBridgeDestinationClasspath OBJECT-TYPE
      SYNTAX      OCTET STRING
      MAX-ACCESS  read-only
      STATUS      current
      DESCRIPTION "The CLASSPATH of the bridge destination.    Used mainly to connect to another release of WebLogic Server.    When connecting to a destination that is running on WebLogic Server 6.0 or earlier, the bridge destination must supply a CLASSPATH that indicates the locations of the classes for the earlier WebLogic Server implementation.    When connecting to a third-party JMS product, the bridge destination must supply the product's CLASSPATH in the WebLogic Server CLASSPATH."
      ::= { jmsBridgeDestinationEntry 47  }
   
   
   jmsBridgeDestinationUserName OBJECT-TYPE
      SYNTAX      OCTET STRING
      MAX-ACCESS  read-only
      STATUS      current
      DESCRIPTION "The optional user name the adapter uses to access the bridge destination.  All operations on the specified destination are done using this user name and the corresponding password. Therefore, the User Name/Password for the source and target destinations must have permission to the access the underlying destinations in order for the messaging bridge to work."
      ::= { jmsBridgeDestinationEntry 48  }
   
   
   jmsConnectionConsumerTable OBJECT-TYPE
      SYNTAX      SEQUENCE OF JmsConnectionConsumerEntry
      MAX-ACCESS  not-accessible
      STATUS      current
      DESCRIPTION "This table defines a connection consumer."
      ::= { wls 600  }
      
   
   jmsConnectionConsumerEntry OBJECT-TYPE
      SYNTAX      JmsConnectionConsumerEntry
      MAX-ACCESS  not-accessible
      STATUS      current
      DESCRIPTION "Entry of jmsConnectionConsumerTable"
      INDEX { jmsConnectionConsumerIndex}
      ::= { jmsConnectionConsumerTable 1 }
      
   JmsConnectionConsumerEntry ::=
      SEQUENCE
      {
         jmsConnectionConsumerIndex DisplayString (SIZE (1..16)),
         jmsConnectionConsumerObjectName DisplayString (SIZE (1..256)),
         jmsConnectionConsumerType DisplayString (SIZE (1..64)),
         jmsConnectionConsumerName DisplayString (SIZE (1..64)),
         jmsConnectionConsumerParent DisplayString (SIZE (1..256)),
         jmsConnectionConsumerMessagesMaximum INTEGER,
         jmsConnectionConsumerSelector DisplayString (SIZE (1..256)),
         jmsConnectionConsumerDestination DisplayString (SIZE (1..256))
      }
      
   
   jmsConnectionConsumerIndex OBJECT-TYPE
      SYNTAX      DisplayString (SIZE (1..16))
      MAX-ACCESS  read-only
      STATUS      current
      DESCRIPTION "Unique value directed from ObjectName which is used as table index"
      ::= { jmsConnectionConsumerEntry 1  }
   
   
   jmsConnectionConsumerObjectName OBJECT-TYPE
      SYNTAX      DisplayString (SIZE (1..256))
      MAX-ACCESS  read-only
      STATUS      current
      DESCRIPTION "JMX-standard MBean name"
      ::= { jmsConnectionConsumerEntry 5  }
   
   
   jmsConnectionConsumerType OBJECT-TYPE
      SYNTAX      DisplayString (SIZE (1..64))
      MAX-ACCESS  read-only
      STATUS      current
      DESCRIPTION "BEA-proprietary MBean type"
      ::= { jmsConnectionConsumerEntry 10  }
   
   
   jmsConnectionConsumerName OBJECT-TYPE
      SYNTAX      DisplayString (SIZE (1..64))
      MAX-ACCESS  read-only
      STATUS      current
      DESCRIPTION "BEA-proprietary MBean name"
      ::= { jmsConnectionConsumerEntry 15  }
   
   
   jmsConnectionConsumerParent OBJECT-TYPE
      SYNTAX      DisplayString (SIZE (1..256))
      MAX-ACCESS  read-only
      STATUS      current
      DESCRIPTION "BEA-proprietary Parent object's identification, with syntax
      <type>:<name>"
      ::= { jmsConnectionConsumerEntry 20  }
   
   
   jmsConnectionConsumerMessagesMaximum OBJECT-TYPE
      SYNTAX      INTEGER
      MAX-ACCESS  read-only
      STATUS      current
      DESCRIPTION "Return the defined maximum number of messages that the connection 
      consumer may load at one time into a ServerSession's session."
      ::= { jmsConnectionConsumerEntry 25  }
   
   
   jmsConnectionConsumerSelector OBJECT-TYPE
      SYNTAX      DisplayString (SIZE (1..256))
      MAX-ACCESS  read-only
      STATUS      current
      DESCRIPTION "Return the defined selector of the connection consumer."
      ::= { jmsConnectionConsumerEntry 30  }
   
   
   jmsConnectionConsumerDestination OBJECT-TYPE
      SYNTAX      DisplayString (SIZE (1..256))
      MAX-ACCESS  read-only
      STATUS      current
      DESCRIPTION "Return the JNDI name of the destination for this connection consumer"
      ::= { jmsConnectionConsumerEntry 35  }
   
   
   jmsConnectionFactoryTable OBJECT-TYPE
      SYNTAX      SEQUENCE OF JmsConnectionFactoryEntry
      MAX-ACCESS  not-accessible
      STATUS      current
      DESCRIPTION "This table represents a JMS connection factory."
      ::= { wls 610  }
      
   
   jmsConnectionFactoryEntry OBJECT-TYPE
      SYNTAX      JmsConnectionFactoryEntry
      MAX-ACCESS  not-accessible
      STATUS      current
      DESCRIPTION "Entry of jmsConnectionFactoryTable"
      INDEX { jmsConnectionFactoryIndex}
      ::= { jmsConnectionFactoryTable 1 }
      
   JmsConnectionFactoryEntry ::=
      SEQUENCE
      {
         jmsConnectionFactoryIndex DisplayString (SIZE (1..16)),
         jmsConnectionFactoryObjectName DisplayString (SIZE (1..256)),
         jmsConnectionFactoryType DisplayString (SIZE (1..64)),
         jmsConnectionFactoryName DisplayString (SIZE (1..64)),
         jmsConnectionFactoryParent DisplayString (SIZE (1..256)),
         jmsConnectionFactoryJNDIName DisplayString (SIZE (1..256)),
         jmsConnectionFactoryClientId DisplayString (SIZE (1..256)),
         jmsConnectionFactoryDefaultPriority INTEGER,
         jmsConnectionFactoryDefaultTimeToLive Counter64,
         jmsConnectionFactoryDefaultDeliveryMode DisplayString (SIZE (1..16)),
         jmsConnectionFactoryTransactionTimeout Counter64,
         jmsConnectionFactoryUserTransactionsEnabled INTEGER
                     {
                        true(1),
                        false(2)
                     }
         ,
         jmsConnectionFactoryAllowCloseInOnMessage INTEGER
                     {
                        true(1),
                        false(2)
                     }
         ,
         jmsConnectionFactoryMessagesMaximum INTEGER,
         jmsConnectionFactoryOverrunPolicy DisplayString (SIZE (1..16)),
         jmsConnectionFactoryTargets DisplayString (SIZE (1..2048))
      }
      
   
   jmsConnectionFactoryIndex OBJECT-TYPE
      SYNTAX      DisplayString (SIZE (1..16))
      MAX-ACCESS  read-only
      STATUS      current
      DESCRIPTION "Unique value directed from ObjectName which is used as table index"
      ::= { jmsConnectionFactoryEntry 1  }
   
   
   jmsConnectionFactoryObjectName OBJECT-TYPE
      SYNTAX      DisplayString (SIZE (1..256))
      MAX-ACCESS  read-only
      STATUS      current
      DESCRIPTION "JMX-standard MBean name"
      ::= { jmsConnectionFactoryEntry 5  }
   
   
   jmsConnectionFactoryType OBJECT-TYPE
      SYNTAX      DisplayString (SIZE (1..64))
      MAX-ACCESS  read-only
      STATUS      current
      DESCRIPTION "BEA-proprietary MBean type"
      ::= { jmsConnectionFactoryEntry 10  }
   
   
   jmsConnectionFactoryName OBJECT-TYPE
      SYNTAX      DisplayString (SIZE (1..64))
      MAX-ACCESS  read-only
      STATUS      current
      DESCRIPTION "BEA-proprietary MBean name"
      ::= { jmsConnectionFactoryEntry 15  }
   
   
   jmsConnectionFactoryParent OBJECT-TYPE
      SYNTAX      DisplayString (SIZE (1..256))
      MAX-ACCESS  read-only
      STATUS      current
      DESCRIPTION "BEA-proprietary Parent object's identification, with syntax
      <type>:<name>"
      ::= { jmsConnectionFactoryEntry 20  }
   
   
   jmsConnectionFactoryJNDIName OBJECT-TYPE
      SYNTAX      DisplayString (SIZE (1..256))
      MAX-ACCESS  read-only
      STATUS      current
      DESCRIPTION "Return the JNDI name of the JMS ConnectionFactory."
      ::= { jmsConnectionFactoryEntry 25  }
   
   
   jmsConnectionFactoryClientId OBJECT-TYPE
      SYNTAX      DisplayString (SIZE (1..256))
      MAX-ACCESS  read-only
      STATUS      current
      DESCRIPTION "Return the client Id for a durable subscriber."
      ::= { jmsConnectionFactoryEntry 30  }
   
   
   jmsConnectionFactoryDefaultPriority OBJECT-TYPE
      SYNTAX      INTEGER
      MAX-ACCESS  read-only
      STATUS      current
      DESCRIPTION "Return the <i>defaultPriority</i> attribute for the connection
      factory. All messages with a <i>priority</i> of -1                                that are
      produced on a connection created with  this factory will receive
      this value."
      ::= { jmsConnectionFactoryEntry 35  }
   
   
   jmsConnectionFactoryDefaultTimeToLive OBJECT-TYPE
      SYNTAX      Counter64
      MAX-ACCESS  read-only
      STATUS      current
      DESCRIPTION "Return the value of the <i>defaultTimeToLive</i> attribute for
      the connection factory. All messages with a <i>timeToLive</i> of
      -1                                that are produced on a connection created with this factory
      will receive this value expressed in milliseconds."
      ::= { jmsConnectionFactoryEntry 40  }
   
   
   jmsConnectionFactoryDefaultDeliveryMode OBJECT-TYPE
      SYNTAX      DisplayString (SIZE (1..16))
      MAX-ACCESS  read-only
      STATUS      current
      DESCRIPTION "Return the value of the <i>defaultDeliveryMode</i> attribute
      for the connection factory. All messages with a
      <i>deliveryMode</i> of null that are produced on a connection
      created with this factory will receive this value."
      ::= { jmsConnectionFactoryEntry 45  }
   
   
   jmsConnectionFactoryTransactionTimeout OBJECT-TYPE
      SYNTAX      Counter64
      MAX-ACCESS  read-only
      STATUS      current
      DESCRIPTION "Return the value of the <i>transactionTimeout</i> attribute for
      the connection factory. All transactions on connections created
      with this connection factory will have this timeout value expressed
      in seconds."
      ::= { jmsConnectionFactoryEntry 50  }
   
   
   jmsConnectionFactoryUserTransactionsEnabled OBJECT-TYPE
      SYNTAX      INTEGER
                  {
                     true(1),
                     false(2)
                  }
      
      MAX-ACCESS  read-only
      STATUS      current
      DESCRIPTION "A boolean value (true Or false). Return the value of the <i>userTransactionsEnabled</i> 
      attribute for the connection factory."
      ::= { jmsConnectionFactoryEntry 55  }
   
   
   jmsConnectionFactoryAllowCloseInOnMessage OBJECT-TYPE
      SYNTAX      INTEGER
                  {
                     true(1),
                     false(2)
                  }
      
      MAX-ACCESS  read-only
      STATUS      current
      DESCRIPTION "A boolean value (true Or false). Return the value of the <i>stopAndCloseBlockingEnabled</i> 
      attribute for the connection factory."
      ::= { jmsConnectionFactoryEntry 60  }
   
   
   jmsConnectionFactoryMessagesMaximum OBJECT-TYPE
      SYNTAX      INTEGER
      MAX-ACCESS  read-only
      STATUS      current
      DESCRIPTION "Return the value of the <i>messagesMaximum</i> attribute for
      the connection factory."
      ::= { jmsConnectionFactoryEntry 65  }
   
   
   jmsConnectionFactoryOverrunPolicy OBJECT-TYPE
      SYNTAX      DisplayString (SIZE (1..16))
      MAX-ACCESS  read-only
      STATUS      current
      DESCRIPTION "Return the value of the <i>overrunPolicy</i> attribute for
      the connection factory."
      ::= { jmsConnectionFactoryEntry 70  }
   
   
   jmsConnectionFactoryTargets OBJECT-TYPE
      SYNTAX      DisplayString (SIZE (1..2048))
      MAX-ACCESS  read-only
      STATUS      current
      DESCRIPTION "targets on which this deployment is deployed."
      ::= { jmsConnectionFactoryEntry 75  }
   
   
   jmsDestCommonTable OBJECT-TYPE
      SYNTAX      SEQUENCE OF JmsDestCommonEntry
      MAX-ACCESS  not-accessible
      STATUS      current
      DESCRIPTION "This table represents a jmsDestCommon in the domain."
      ::= { wls 612  }
      
   
   jmsDestCommonEntry OBJECT-TYPE
      SYNTAX      JmsDestCommonEntry
      MAX-ACCESS  not-accessible
      STATUS      current
      DESCRIPTION "Entry of jmsDestCommonTable"
      INDEX { jmsDestCommonIndex}
      ::= { jmsDestCommonTable 1 }
      
   JmsDestCommonEntry ::=
      SEQUENCE
      {
         jmsDestCommonIndex   DisplayString (SIZE (1..16)),
         jmsDestCommonObjectName DisplayString (SIZE (1..256)),
         jmsDestCommonType    DisplayString (SIZE (1..64)),
         jmsDestCommonName    DisplayString (SIZE (1..64)),
         jmsDestCommonParent  DisplayString (SIZE (1..256)),
         jmsDestCommonBytesMaximum INTEGER,
         jmsDestCommonBytesThresholdHigh INTEGER,
         jmsDestCommonBytesThresholdLow INTEGER,
         jmsDestCommonDeliveryModeOverride DisplayString (SIZE (1..256)),
         jmsDestCommonMessagesMaximum INTEGER,
         jmsDestCommonMessagesThresholdHigh INTEGER,
         jmsDestCommonMessagesThresholdLow INTEGER,
         jmsDestCommonPriorityOverride INTEGER,
         jmsDestCommonRedeliveryDelayOverride INTEGER,
         jmsDestCommonRedeliveryLimit INTEGER,
         jmsDestCommonTimeToDeliverOverride DisplayString (SIZE (1..256)),
         jmsDestCommonTimeToLiveOverride INTEGER
      }
      
   
   jmsDestCommonIndex OBJECT-TYPE
      SYNTAX      DisplayString (SIZE (1..16))
      MAX-ACCESS  read-only
      STATUS      current
      DESCRIPTION "Unique value directed from ObjectName which is used as table index"
      ::= { jmsDestCommonEntry 1  }
   
   
   jmsDestCommonObjectName OBJECT-TYPE
      SYNTAX      DisplayString (SIZE (1..256))
      MAX-ACCESS  read-only
      STATUS      current
      DESCRIPTION "JMX-standard MBean name"
      ::= { jmsDestCommonEntry 5  }
   
   
   jmsDestCommonType OBJECT-TYPE
      SYNTAX      DisplayString (SIZE (1..64))
      MAX-ACCESS  read-only
      STATUS      current
      DESCRIPTION "BEA-proprietary MBean type"
      ::= { jmsDestCommonEntry 10  }
   
   
   jmsDestCommonName OBJECT-TYPE
      SYNTAX      DisplayString (SIZE (1..64))
      MAX-ACCESS  read-only
      STATUS      current
      DESCRIPTION "BEA-proprietary MBean name"
      ::= { jmsDestCommonEntry 15  }
   
   
   jmsDestCommonParent OBJECT-TYPE
      SYNTAX      DisplayString (SIZE (1..256))
      MAX-ACCESS  read-only
      STATUS      current
      DESCRIPTION "BEA-proprietary Parent object's identification, with syntax
      <type>:<name>"
      ::= { jmsDestCommonEntry 20  }
   
   
   jmsDestCommonBytesMaximum OBJECT-TYPE
      SYNTAX      INTEGER
      MAX-ACCESS  read-only
      STATUS      current
      DESCRIPTION "Returns the value of BytesMaximum."
      ::= { jmsDestCommonEntry 25  }
   
   
   jmsDestCommonBytesThresholdHigh OBJECT-TYPE
      SYNTAX      INTEGER
      MAX-ACCESS  read-only
      STATUS      current
      DESCRIPTION "Returns the value of BytesThresholdHigh."
      ::= { jmsDestCommonEntry 30  }
   
   
   jmsDestCommonBytesThresholdLow OBJECT-TYPE
      SYNTAX      INTEGER
      MAX-ACCESS  read-only
      STATUS      current
      DESCRIPTION "Returns the value of BytesThresholdLow."
      ::= { jmsDestCommonEntry 35  }
   
   
   jmsDestCommonDeliveryModeOverride OBJECT-TYPE
      SYNTAX      DisplayString (SIZE (1..256))
      MAX-ACCESS  read-only
      STATUS      current
      DESCRIPTION "Returns the DeliveryModeOverride value."
      ::= { jmsDestCommonEntry 40  }
   
   
   jmsDestCommonMessagesMaximum OBJECT-TYPE
      SYNTAX      INTEGER
      MAX-ACCESS  read-only
      STATUS      current
      DESCRIPTION "Returns the values of MessagesMaximum."
      ::= { jmsDestCommonEntry 45  }
   
   
   jmsDestCommonMessagesThresholdHigh OBJECT-TYPE
      SYNTAX      INTEGER
      MAX-ACCESS  read-only
      STATUS      current
      DESCRIPTION "Returns the values of MessagesThresholdHigh."
      ::= { jmsDestCommonEntry 50  }
   
   
   jmsDestCommonMessagesThresholdLow OBJECT-TYPE
      SYNTAX      INTEGER
      MAX-ACCESS  read-only
      STATUS      current
      DESCRIPTION "Returns the values of MessagesThresholdLow."
      ::= { jmsDestCommonEntry 55  }
   
   
   jmsDestCommonPriorityOverride OBJECT-TYPE
      SYNTAX      INTEGER
      MAX-ACCESS  read-only
      STATUS      current
      DESCRIPTION "Returns the values of PriorityOverride."
      ::= { jmsDestCommonEntry 65  }
   
   
   jmsDestCommonRedeliveryDelayOverride OBJECT-TYPE
      SYNTAX      INTEGER
      MAX-ACCESS  read-only
      STATUS      current
      DESCRIPTION "Returns the values of RedeliveryDelayOverride."
      ::= { jmsDestCommonEntry 70  }
   
   
   jmsDestCommonRedeliveryLimit OBJECT-TYPE
      SYNTAX      INTEGER
      MAX-ACCESS  read-only
      STATUS      current
      DESCRIPTION "Returns the values of RedeliveryLimit."
      ::= { jmsDestCommonEntry 75  }
   
   
   jmsDestCommonTimeToDeliverOverride OBJECT-TYPE
      SYNTAX      DisplayString (SIZE (1..256))
      MAX-ACCESS  read-only
      STATUS      current
      DESCRIPTION "Returns the values of TimeToDeliverOverride."
      ::= { jmsDestCommonEntry 80  }
   
   
   jmsDestCommonTimeToLiveOverride OBJECT-TYPE
      SYNTAX      INTEGER
      MAX-ACCESS  read-only
      STATUS      current
      DESCRIPTION "Returns the values of TimeToLiveOverride."
      ::= { jmsDestCommonEntry 85  }
   
   
   jmsDestinationTable OBJECT-TYPE
      SYNTAX      SEQUENCE OF JmsDestinationEntry
      MAX-ACCESS  not-accessible
      STATUS      current
      DESCRIPTION "This table represents a jmsDestination in the domain."
      ::= { wls 615  }
      
   
   jmsDestinationEntry OBJECT-TYPE
      SYNTAX      JmsDestinationEntry
      MAX-ACCESS  not-accessible
      STATUS      current
      DESCRIPTION "Entry of jmsDestinationTable"
      INDEX { jmsDestinationIndex}
      ::= { jmsDestinationTable 1 }
      
   JmsDestinationEntry ::=
      SEQUENCE
      {
         jmsDestinationIndex  DisplayString (SIZE (1..16)),
         jmsDestinationObjectName DisplayString (SIZE (1..256)),
         jmsDestinationType   DisplayString (SIZE (1..64)),
         jmsDestinationName   DisplayString (SIZE (1..64)),
         jmsDestinationParent DisplayString (SIZE (1..256)),
         jmsDestinationBytesPagingEnabled DisplayString (SIZE (1..256)),
         jmsDestinationJNDIName DisplayString (SIZE (1..256)),
         jmsDestinationMessagesPagingEnabled DisplayString (SIZE (1..256)),
         jmsDestinationStoreEnabled DisplayString (SIZE (1..256)),
         jmsDestinationJNDINameReplicated DisplayString (SIZE (1..256))
      }
      
   
   jmsDestinationIndex OBJECT-TYPE
      SYNTAX      DisplayString (SIZE (1..16))
      MAX-ACCESS  read-only
      STATUS      current
      DESCRIPTION "Unique value directed from ObjectName which is used as table index"
      ::= { jmsDestinationEntry 1  }
   
   
   jmsDestinationObjectName OBJECT-TYPE
      SYNTAX      DisplayString (SIZE (1..256))
      MAX-ACCESS  read-only
      STATUS      current
      DESCRIPTION "JMX-standard MBean name"
      ::= { jmsDestinationEntry 5  }
   
   
   jmsDestinationType OBJECT-TYPE
      SYNTAX      DisplayString (SIZE (1..64))
      MAX-ACCESS  read-only
      STATUS      current
      DESCRIPTION "BEA-proprietary MBean type"
      ::= { jmsDestinationEntry 10  }
   
   
   jmsDestinationName OBJECT-TYPE
      SYNTAX      DisplayString (SIZE (1..64))
      MAX-ACCESS  read-only
      STATUS      current
      DESCRIPTION "BEA-proprietary MBean name"
      ::= { jmsDestinationEntry 15  }
   
   
   jmsDestinationParent OBJECT-TYPE
      SYNTAX      DisplayString (SIZE (1..256))
      MAX-ACCESS  read-only
      STATUS      current
      DESCRIPTION "BEA-proprietary Parent object's identification, with syntax
      <type>:<name>"
      ::= { jmsDestinationEntry 20  }
   
   
   jmsDestinationBytesPagingEnabled OBJECT-TYPE
      SYNTAX      DisplayString (SIZE (1..256))
      MAX-ACCESS  read-only
      STATUS      current
      DESCRIPTION "returns true or false."
      ::= { jmsDestinationEntry 25  }
   
   
   jmsDestinationJNDIName OBJECT-TYPE
      SYNTAX      DisplayString (SIZE (1..256))
      MAX-ACCESS  read-only
      STATUS      current
      DESCRIPTION "Returns the JNDI name of the destination."
      ::= { jmsDestinationEntry 30  }
   
   
   jmsDestinationMessagesPagingEnabled OBJECT-TYPE
      SYNTAX      DisplayString (SIZE (1..256))
      MAX-ACCESS  read-only
      STATUS      current
      DESCRIPTION "pagiing enablesd."
      ::= { jmsDestinationEntry 35  }
   
   
   jmsDestinationStoreEnabled OBJECT-TYPE
      SYNTAX      DisplayString (SIZE (1..256))
      MAX-ACCESS  read-only
      STATUS      current
      DESCRIPTION "store enablesd."
      ::= { jmsDestinationEntry 40  }
   
   
   jmsDestinationJNDINameReplicated OBJECT-TYPE
      SYNTAX      DisplayString (SIZE (1..256))
      MAX-ACCESS  read-only
      STATUS      current
      DESCRIPTION "jndi name enabled."
      ::= { jmsDestinationEntry 45  }
   
   
   jmsDestinationKeyTable OBJECT-TYPE
      SYNTAX      SEQUENCE OF JmsDestinationKeyEntry
      MAX-ACCESS  not-accessible
      STATUS      current
      DESCRIPTION "This table represents a key value for a destination"
      ::= { wls 620  }
      
   
   jmsDestinationKeyEntry OBJECT-TYPE
      SYNTAX      JmsDestinationKeyEntry
      MAX-ACCESS  not-accessible
      STATUS      current
      DESCRIPTION "Entry of jmsDestinationKeyTable"
      INDEX { jmsDestinationKeyIndex}
      ::= { jmsDestinationKeyTable 1 }
      
   JmsDestinationKeyEntry ::=
      SEQUENCE
      {
         jmsDestinationKeyIndex DisplayString (SIZE (1..16)),
         jmsDestinationKeyObjectName DisplayString (SIZE (1..256)),
         jmsDestinationKeyType DisplayString (SIZE (1..64)),
         jmsDestinationKeyName DisplayString (SIZE (1..64)),
         jmsDestinationKeyParent DisplayString (SIZE (1..256)),
         jmsDestinationKeyProperty DisplayString (SIZE (1..64)),
         jmsDestinationKeyKeyType DisplayString (SIZE (1..32)),
         jmsDestinationKeyDirection DisplayString (SIZE (1..32))
      }
      
   
   jmsDestinationKeyIndex OBJECT-TYPE
      SYNTAX      DisplayString (SIZE (1..16))
      MAX-ACCESS  read-only
      STATUS      current
      DESCRIPTION "Unique value directed from ObjectName which is used as table index"
      ::= { jmsDestinationKeyEntry 1  }
   
   
   jmsDestinationKeyObjectName OBJECT-TYPE
      SYNTAX      DisplayString (SIZE (1..256))
      MAX-ACCESS  read-only
      STATUS      current
      DESCRIPTION "JMX-standard MBean name"
      ::= { jmsDestinationKeyEntry 5  }
   
   
   jmsDestinationKeyType OBJECT-TYPE
      SYNTAX      DisplayString (SIZE (1..64))
      MAX-ACCESS  read-only
      STATUS      current
      DESCRIPTION "BEA-proprietary MBean type"
      ::= { jmsDestinationKeyEntry 10  }
   
   
   jmsDestinationKeyName OBJECT-TYPE
      SYNTAX      DisplayString (SIZE (1..64))
      MAX-ACCESS  read-only
      STATUS      current
      DESCRIPTION "BEA-proprietary MBean name"
      ::= { jmsDestinationKeyEntry 15  }
   
   
   jmsDestinationKeyParent OBJECT-TYPE
      SYNTAX      DisplayString (SIZE (1..256))
      MAX-ACCESS  read-only
      STATUS      current
      DESCRIPTION "BEA-proprietary Parent object's identification, with syntax
      <type>:<name>"
      ::= { jmsDestinationKeyEntry 20  }
   
   
   jmsDestinationKeyProperty OBJECT-TYPE
      SYNTAX      DisplayString (SIZE (1..64))
      MAX-ACCESS  read-only
      STATUS      current
      DESCRIPTION "The property name for this key"
      ::= { jmsDestinationKeyEntry 25  }
   
   
   jmsDestinationKeyKeyType OBJECT-TYPE
      SYNTAX      DisplayString (SIZE (1..32))
      MAX-ACCESS  read-only
      STATUS      current
      DESCRIPTION "The expected property type for this key"
      ::= { jmsDestinationKeyEntry 30  }
   
   
   jmsDestinationKeyDirection OBJECT-TYPE
      SYNTAX      DisplayString (SIZE (1..32))
      MAX-ACCESS  read-only
      STATUS      current
      DESCRIPTION "The direction for this key"
      ::= { jmsDestinationKeyEntry 35  }
   
   
   jmsDistributedQueueTable OBJECT-TYPE
      SYNTAX      SEQUENCE OF JmsDistributedQueueEntry
      MAX-ACCESS  not-accessible
      STATUS      current
      DESCRIPTION "This table represents a key value for a destination"
      ::= { wls 622  }
      
   
   jmsDistributedQueueEntry OBJECT-TYPE
      SYNTAX      JmsDistributedQueueEntry
      MAX-ACCESS  not-accessible
      STATUS      current
      DESCRIPTION "Entry of jmsDistributedQueueTable"
      INDEX { jmsDistributedQueueIndex}
      ::= { jmsDistributedQueueTable 1 }
      
   JmsDistributedQueueEntry ::=
      SEQUENCE
      {
         jmsDistributedQueueIndex DisplayString (SIZE (1..16)),
         jmsDistributedQueueObjectName DisplayString (SIZE (1..256)),
         jmsDistributedQueueType DisplayString (SIZE (1..64)),
         jmsDistributedQueueName DisplayString (SIZE (1..64)),
         jmsDistributedQueueParent DisplayString (SIZE (1..256)),
         jmsDistributedQueueForwardDelay INTEGER
      }
      
   
   jmsDistributedQueueIndex OBJECT-TYPE
      SYNTAX      DisplayString (SIZE (1..16))
      MAX-ACCESS  read-only
      STATUS      current
      DESCRIPTION "Unique value directed from ObjectName which is used as table index"
      ::= { jmsDistributedQueueEntry 1  }
   
   
   jmsDistributedQueueObjectName OBJECT-TYPE
      SYNTAX      DisplayString (SIZE (1..256))
      MAX-ACCESS  read-only
      STATUS      current
      DESCRIPTION "JMX-standard MBean name"
      ::= { jmsDistributedQueueEntry 5  }
   
   
   jmsDistributedQueueType OBJECT-TYPE
      SYNTAX      DisplayString (SIZE (1..64))
      MAX-ACCESS  read-only
      STATUS      current
      DESCRIPTION "BEA-proprietary MBean type"
      ::= { jmsDistributedQueueEntry 10  }
   
   
   jmsDistributedQueueName OBJECT-TYPE
      SYNTAX      DisplayString (SIZE (1..64))
      MAX-ACCESS  read-only
      STATUS      current
      DESCRIPTION "BEA-proprietary MBean name"
      ::= { jmsDistributedQueueEntry 15  }
   
   
   jmsDistributedQueueParent OBJECT-TYPE
      SYNTAX      DisplayString (SIZE (1..256))
      MAX-ACCESS  read-only
      STATUS      current
      DESCRIPTION "BEA-proprietary Parent object's identification, with syntax
      <type>:<name>"
      ::= { jmsDistributedQueueEntry 20  }
   
   
   jmsDistributedQueueForwardDelay OBJECT-TYPE
      SYNTAX      INTEGER
      MAX-ACCESS  read-only
      STATUS      current
      DESCRIPTION "Return the message forwarding delay for this distributed queue."
      ::= { jmsDistributedQueueEntry 25  }
   
   
   jmsDistributedDestinationTable OBJECT-TYPE
      SYNTAX      SEQUENCE OF JmsDistributedDestinationEntry
      MAX-ACCESS  not-accessible
      STATUS      current
      DESCRIPTION "This table represents a key value for a destination"
      ::= { wls 623  }
      
   
   jmsDistributedDestinationEntry OBJECT-TYPE
      SYNTAX      JmsDistributedDestinationEntry
      MAX-ACCESS  not-accessible
      STATUS      current
      DESCRIPTION "Entry of jmsDistributedDestinationTable"
      INDEX { jmsDistributedDestinationIndex}
      ::= { jmsDistributedDestinationTable 1 }
      
   JmsDistributedDestinationEntry ::=
      SEQUENCE
      {
         jmsDistributedDestinationIndex DisplayString (SIZE (1..16)),
         jmsDistributedDestinationObjectName DisplayString (SIZE (1..256)),
         jmsDistributedDestinationType DisplayString (SIZE (1..64)),
         jmsDistributedDestinationName DisplayString (SIZE (1..64)),
         jmsDistributedDestinationParent DisplayString (SIZE (1..256)),
         jmsDistributedDestinationLoadBalancingPolicy DisplayString
      }
      
   
   jmsDistributedDestinationIndex OBJECT-TYPE
      SYNTAX      DisplayString (SIZE (1..16))
      MAX-ACCESS  read-only
      STATUS      current
      DESCRIPTION "Unique value directed from ObjectName which is used as table index"
      ::= { jmsDistributedDestinationEntry 1  }
   
   
   jmsDistributedDestinationObjectName OBJECT-TYPE
      SYNTAX      DisplayString (SIZE (1..256))
      MAX-ACCESS  read-only
      STATUS      current
      DESCRIPTION "JMX-standard MBean name"
      ::= { jmsDistributedDestinationEntry 5  }
   
   
   jmsDistributedDestinationType OBJECT-TYPE
      SYNTAX      DisplayString (SIZE (1..64))
      MAX-ACCESS  read-only
      STATUS      current
      DESCRIPTION "BEA-proprietary MBean type"
      ::= { jmsDistributedDestinationEntry 10  }
   
   
   jmsDistributedDestinationName OBJECT-TYPE
      SYNTAX      DisplayString (SIZE (1..64))
      MAX-ACCESS  read-only
      STATUS      current
      DESCRIPTION "BEA-proprietary MBean name"
      ::= { jmsDistributedDestinationEntry 15  }
   
   
   jmsDistributedDestinationParent OBJECT-TYPE
      SYNTAX      DisplayString (SIZE (1..256))
      MAX-ACCESS  read-only
      STATUS      current
      DESCRIPTION "BEA-proprietary Parent object's identification, with syntax
      <type>:<name>"
      ::= { jmsDistributedDestinationEntry 20  }
   
   
   jmsDistributedDestinationLoadBalancingPolicy OBJECT-TYPE
      SYNTAX      DisplayString
      MAX-ACCESS  read-only
      STATUS      current
      DESCRIPTION "Generated Object."
      ::= { jmsDistributedDestinationEntry 21  }
   
   
   jmsDistributedDestinationMemberTable OBJECT-TYPE
      SYNTAX      SEQUENCE OF JmsDistributedDestinationMemberEntry
      MAX-ACCESS  not-accessible
      STATUS      current
      DESCRIPTION "A JMS file based backing store."
      ::= { wls 624  }
      
   
   jmsDistributedDestinationMemberEntry OBJECT-TYPE
      SYNTAX      JmsDistributedDestinationMemberEntry
      MAX-ACCESS  not-accessible
      STATUS      current
      DESCRIPTION "Entry of jmsDistributedDestinationMemberTable"
      INDEX { jmsDistributedDestinationMemberIndex}
      ::= { jmsDistributedDestinationMemberTable 1 }
      
   JmsDistributedDestinationMemberEntry ::=
      SEQUENCE
      {
         jmsDistributedDestinationMemberIndex DisplayString (SIZE (1..16)),
         jmsDistributedDestinationMemberObjectName DisplayString (SIZE (1..256)),
         jmsDistributedDestinationMemberType DisplayString (SIZE (1..64)),
         jmsDistributedDestinationMemberName DisplayString (SIZE (1..64)),
         jmsDistributedDestinationMemberParent DisplayString (SIZE (1..256)),
         jmsDistributedDestinationMemberWeight INTEGER
      }
      
   
   jmsDistributedDestinationMemberIndex OBJECT-TYPE
      SYNTAX      DisplayString (SIZE (1..16))
      MAX-ACCESS  read-only
      STATUS      current
      DESCRIPTION "Unique value directed from ObjectName which is used as table index"
      ::= { jmsDistributedDestinationMemberEntry 1  }
   
   
   jmsDistributedDestinationMemberObjectName OBJECT-TYPE
      SYNTAX      DisplayString (SIZE (1..256))
      MAX-ACCESS  read-only
      STATUS      current
      DESCRIPTION "JMX-standard MBean name"
      ::= { jmsDistributedDestinationMemberEntry 5  }
   
   
   jmsDistributedDestinationMemberType OBJECT-TYPE
      SYNTAX      DisplayString (SIZE (1..64))
      MAX-ACCESS  read-only
      STATUS      current
      DESCRIPTION "BEA-proprietary MBean type"
      ::= { jmsDistributedDestinationMemberEntry 10  }
   
   
   jmsDistributedDestinationMemberName OBJECT-TYPE
      SYNTAX      DisplayString (SIZE (1..64))
      MAX-ACCESS  read-only
      STATUS      current
      DESCRIPTION "BEA-proprietary MBean name"
      ::= { jmsDistributedDestinationMemberEntry 15  }
   
   
   jmsDistributedDestinationMemberParent OBJECT-TYPE
      SYNTAX      DisplayString (SIZE (1..256))
      MAX-ACCESS  read-only
      STATUS      current
      DESCRIPTION "BEA-proprietary Parent object's identification, with syntax
      <type>:<name>"
      ::= { jmsDistributedDestinationMemberEntry 20  }
   
   
   jmsDistributedDestinationMemberWeight OBJECT-TYPE
      SYNTAX      INTEGER
      MAX-ACCESS  read-only
      STATUS      current
      DESCRIPTION "Generated Object."
      ::= { jmsDistributedDestinationMemberEntry 21  }
   
   
   jmsTemplateTable OBJECT-TYPE
      SYNTAX      SEQUENCE OF JmsTemplateEntry
      MAX-ACCESS  not-accessible
      STATUS      current
      DESCRIPTION "A JMS file based backing store."
      ::= { wls 626  }
      
   
   jmsTemplateEntry OBJECT-TYPE
      SYNTAX      JmsTemplateEntry
      MAX-ACCESS  not-accessible
      STATUS      current
      DESCRIPTION "Entry of jmsTemplateTable"
      INDEX { jmsTemplateIndex}
      ::= { jmsTemplateTable 1 }
      
   JmsTemplateEntry ::=
      SEQUENCE
      {
         jmsTemplateIndex     DisplayString (SIZE (1..16)),
         jmsTemplateObjectName DisplayString (SIZE (1..256)),
         jmsTemplateType      DisplayString (SIZE (1..64)),
         jmsTemplateName      DisplayString (SIZE (1..64)),
         jmsTemplateParent    DisplayString (SIZE (1..256)),
         jmsTemplateBytesPagingEnabled INTEGER,
         jmsTemplateMessagesPagingEnabled INTEGER
      }
      
   
   jmsTemplateIndex OBJECT-TYPE
      SYNTAX      DisplayString (SIZE (1..16))
      MAX-ACCESS  read-only
      STATUS      current
      DESCRIPTION "Unique value directed from ObjectName which is used as table index"
      ::= { jmsTemplateEntry 1  }
   
   
   jmsTemplateObjectName OBJECT-TYPE
      SYNTAX      DisplayString (SIZE (1..256))
      MAX-ACCESS  read-only
      STATUS      current
      DESCRIPTION "JMX-standard MBean name"
      ::= { jmsTemplateEntry 5  }
   
   
   jmsTemplateType OBJECT-TYPE
      SYNTAX      DisplayString (SIZE (1..64))
      MAX-ACCESS  read-only
      STATUS      current
      DESCRIPTION "BEA-proprietary MBean type"
      ::= { jmsTemplateEntry 10  }
   
   
   jmsTemplateName OBJECT-TYPE
      SYNTAX      DisplayString (SIZE (1..64))
      MAX-ACCESS  read-only
      STATUS      current
      DESCRIPTION "BEA-proprietary MBean name"
      ::= { jmsTemplateEntry 15  }
   
   
   jmsTemplateParent OBJECT-TYPE
      SYNTAX      DisplayString (SIZE (1..256))
      MAX-ACCESS  read-only
      STATUS      current
      DESCRIPTION "BEA-proprietary Parent object's identification, with syntax
      <type>:<name>"
      ::= { jmsTemplateEntry 20  }
   
   
   jmsTemplateBytesPagingEnabled OBJECT-TYPE
      SYNTAX      INTEGER
      MAX-ACCESS  read-only
      STATUS      current
      DESCRIPTION "Generated Object."
      ::= { jmsTemplateEntry 21  }
   
   
   jmsTemplateMessagesPagingEnabled OBJECT-TYPE
      SYNTAX      INTEGER
      MAX-ACCESS  read-only
      STATUS      current
      DESCRIPTION "Generated Object."
      ::= { jmsTemplateEntry 22  }
   
   
   jmsFileStoreTable OBJECT-TYPE
      SYNTAX      SEQUENCE OF JmsFileStoreEntry
      MAX-ACCESS  not-accessible
      STATUS      current
      DESCRIPTION "A JMS file based backing store."
      ::= { wls 630  }
      
   
   jmsFileStoreEntry OBJECT-TYPE
      SYNTAX      JmsFileStoreEntry
      MAX-ACCESS  not-accessible
      STATUS      current
      DESCRIPTION "Entry of jmsFileStoreTable"
      INDEX { jmsFileStoreIndex}
      ::= { jmsFileStoreTable 1 }
      
   JmsFileStoreEntry ::=
      SEQUENCE
      {
         jmsFileStoreIndex    DisplayString (SIZE (1..16)),
         jmsFileStoreObjectName DisplayString (SIZE (1..256)),
         jmsFileStoreType     DisplayString (SIZE (1..64)),
         jmsFileStoreName     DisplayString (SIZE (1..64)),
         jmsFileStoreParent   DisplayString (SIZE (1..256)),
         jmsFileStoreJMSServer DisplayString (SIZE (1..256)),
         jmsFileStoreDirectory DisplayString (SIZE (1..256))
      }
      
   
   jmsFileStoreIndex OBJECT-TYPE
      SYNTAX      DisplayString (SIZE (1..16))
      MAX-ACCESS  read-only
      STATUS      current
      DESCRIPTION "Unique value directed from ObjectName which is used as table index"
      ::= { jmsFileStoreEntry 1  }
   
   
   jmsFileStoreObjectName OBJECT-TYPE
      SYNTAX      DisplayString (SIZE (1..256))
      MAX-ACCESS  read-only
      STATUS      current
      DESCRIPTION "JMX-standard MBean name"
      ::= { jmsFileStoreEntry 5  }
   
   
   jmsFileStoreType OBJECT-TYPE
      SYNTAX      DisplayString (SIZE (1..64))
      MAX-ACCESS  read-only
      STATUS      current
      DESCRIPTION "BEA-proprietary MBean type"
      ::= { jmsFileStoreEntry 10  }
   
   
   jmsFileStoreName OBJECT-TYPE
      SYNTAX      DisplayString (SIZE (1..64))
      MAX-ACCESS  read-only
      STATUS      current
      DESCRIPTION "BEA-proprietary MBean name"
      ::= { jmsFileStoreEntry 15  }
   
   
   jmsFileStoreParent OBJECT-TYPE
      SYNTAX      DisplayString (SIZE (1..256))
      MAX-ACCESS  read-only
      STATUS      current
      DESCRIPTION "BEA-proprietary Parent object's identification, with syntax
      <type>:<name>"
      ::= { jmsFileStoreEntry 20  }
   
   
   jmsFileStoreJMSServer OBJECT-TYPE
      SYNTAX      DisplayString (SIZE (1..256))
      MAX-ACCESS  read-only
      STATUS      current
      DESCRIPTION "The JMS Server for this store"
      ::= { jmsFileStoreEntry 25  }
   
   
   jmsFileStoreDirectory OBJECT-TYPE
      SYNTAX      DisplayString (SIZE (1..256))
      MAX-ACCESS  read-only
      STATUS      current
      DESCRIPTION "Get the directory for this file based store."
      ::= { jmsFileStoreEntry 30  }
   
   
   jmsJDBCStoreTable OBJECT-TYPE
      SYNTAX      SEQUENCE OF JmsJDBCStoreEntry
      MAX-ACCESS  not-accessible
      STATUS      current
      DESCRIPTION "A JMS JDBC based backing store."
      ::= { wls 640  }
      
   
   jmsJDBCStoreEntry OBJECT-TYPE
      SYNTAX      JmsJDBCStoreEntry
      MAX-ACCESS  not-accessible
      STATUS      current
      DESCRIPTION "Entry of jmsJDBCStoreTable"
      INDEX { jmsJDBCStoreIndex}
      ::= { jmsJDBCStoreTable 1 }
      
   JmsJDBCStoreEntry ::=
      SEQUENCE
      {
         jmsJDBCStoreIndex    DisplayString (SIZE (1..16)),
         jmsJDBCStoreObjectName DisplayString (SIZE (1..256)),
         jmsJDBCStoreType     DisplayString (SIZE (1..64)),
         jmsJDBCStoreName     DisplayString (SIZE (1..64)),
         jmsJDBCStoreParent   DisplayString (SIZE (1..256)),
         jmsJDBCStoreJMSServer DisplayString (SIZE (1..256)),
         jmsJDBCStoreConnectionPool DisplayString (SIZE (1..256)),
         jmsJDBCStorePrefixName DisplayString (SIZE (1..32))
      }
      
   
   jmsJDBCStoreIndex OBJECT-TYPE
      SYNTAX      DisplayString (SIZE (1..16))
      MAX-ACCESS  read-only
      STATUS      current
      DESCRIPTION "Unique value directed from ObjectName which is used as table index"
      ::= { jmsJDBCStoreEntry 1  }
   
   
   jmsJDBCStoreObjectName OBJECT-TYPE
      SYNTAX      DisplayString (SIZE (1..256))
      MAX-ACCESS  read-only
      STATUS      current
      DESCRIPTION "JMX-standard MBean name"
      ::= { jmsJDBCStoreEntry 5  }
   
   
   jmsJDBCStoreType OBJECT-TYPE
      SYNTAX      DisplayString (SIZE (1..64))
      MAX-ACCESS  read-only
      STATUS      current
      DESCRIPTION "BEA-proprietary MBean type"
      ::= { jmsJDBCStoreEntry 10  }
   
   
   jmsJDBCStoreName OBJECT-TYPE
      SYNTAX      DisplayString (SIZE (1..64))
      MAX-ACCESS  read-only
      STATUS      current
      DESCRIPTION "BEA-proprietary MBean name"
      ::= { jmsJDBCStoreEntry 15  }
   
   
   jmsJDBCStoreParent OBJECT-TYPE
      SYNTAX      DisplayString (SIZE (1..256))
      MAX-ACCESS  read-only
      STATUS      current
      DESCRIPTION "BEA-proprietary Parent object's identification, with syntax
      <type>:<name>"
      ::= { jmsJDBCStoreEntry 20  }
   
   
   jmsJDBCStoreJMSServer OBJECT-TYPE
      SYNTAX      DisplayString (SIZE (1..256))
      MAX-ACCESS  read-only
      STATUS      current
      DESCRIPTION "The JMS Server for this store"
      ::= { jmsJDBCStoreEntry 25  }
   
   
   jmsJDBCStoreConnectionPool OBJECT-TYPE
      SYNTAX      DisplayString (SIZE (1..256))
      MAX-ACCESS  read-only
      STATUS      current
      DESCRIPTION "Get the JDBC Connection Pool for this backing store."
      ::= { jmsJDBCStoreEntry 30  }
   
   
   jmsJDBCStorePrefixName OBJECT-TYPE
      SYNTAX      DisplayString (SIZE (1..32))
      MAX-ACCESS  read-only
      STATUS      current
      DESCRIPTION "Get the prefix name of JMS tables in this backing store."
      ::= { jmsJDBCStoreEntry 35  }
   
   
   jmsQueueTable OBJECT-TYPE
      SYNTAX      SEQUENCE OF JmsQueueEntry
      MAX-ACCESS  not-accessible
      STATUS      current
      DESCRIPTION "A JMS Destination queue."
      ::= { wls 650  }
      
   
   jmsQueueEntry OBJECT-TYPE
      SYNTAX      JmsQueueEntry
      MAX-ACCESS  not-accessible
      STATUS      current
      DESCRIPTION "Entry of jmsQueueTable"
      INDEX { jmsQueueIndex}
      ::= { jmsQueueTable 1 }
      
   JmsQueueEntry ::=
      SEQUENCE
      {
         jmsQueueIndex        DisplayString (SIZE (1..16)),
         jmsQueueObjectName   DisplayString (SIZE (1..256)),
         jmsQueueType         DisplayString (SIZE (1..64)),
         jmsQueueName         DisplayString (SIZE (1..64)),
         jmsQueueParent       DisplayString (SIZE (1..256)),
         jmsQueueDestinationKeys DisplayString (SIZE (1..2048)),
         jmsQueueBytesMaximum INTEGER,
         jmsQueueBytesThresholdHigh INTEGER,
         jmsQueueBytesThresholdLow INTEGER,
         jmsQueueMessagesMaximum INTEGER,
         jmsQueueMessagesThresholdHigh INTEGER,
         jmsQueueMessagesThresholdLow INTEGER,
         jmsQueuePriorityOverride INTEGER,
         jmsQueueTimeToDeliverOverride INTEGER,
         jmsQueueRedeliveryDelayOverride INTEGER,
         jmsQueueRedeliveryLimit INTEGER,
         jmsQueueErrorDestination DisplayString (SIZE (1..256)),
         jmsQueueTimeToLiveOverride INTEGER,
         jmsQueueDeliveryModeOverride DisplayString (SIZE (1..256)),
         jmsQueueJNDIName     DisplayString (SIZE (1..256)),
         jmsQueueStoreEnabled DisplayString (SIZE (1..16))
      }
      
   
   jmsQueueIndex OBJECT-TYPE
      SYNTAX      DisplayString (SIZE (1..16))
      MAX-ACCESS  read-only
      STATUS      current
      DESCRIPTION "Unique value directed from ObjectName which is used as table index"
      ::= { jmsQueueEntry 1  }
   
   
   jmsQueueObjectName OBJECT-TYPE
      SYNTAX      DisplayString (SIZE (1..256))
      MAX-ACCESS  read-only
      STATUS      current
      DESCRIPTION "JMX-standard MBean name"
      ::= { jmsQueueEntry 5  }
   
   
   jmsQueueType OBJECT-TYPE
      SYNTAX      DisplayString (SIZE (1..64))
      MAX-ACCESS  read-only
      STATUS      current
      DESCRIPTION "BEA-proprietary MBean type"
      ::= { jmsQueueEntry 10  }
   
   
   jmsQueueName OBJECT-TYPE
      SYNTAX      DisplayString (SIZE (1..64))
      MAX-ACCESS  read-only
      STATUS      current
      DESCRIPTION "BEA-proprietary MBean name"
      ::= { jmsQueueEntry 15  }
   
   
   jmsQueueParent OBJECT-TYPE
      SYNTAX      DisplayString (SIZE (1..256))
      MAX-ACCESS  read-only
      STATUS      current
      DESCRIPTION "BEA-proprietary Parent object's identification, with syntax
      <type>:<name>"
      ::= { jmsQueueEntry 20  }
   
   
   jmsQueueDestinationKeys OBJECT-TYPE
      SYNTAX      DisplayString (SIZE (1..2048))
      MAX-ACCESS  read-only
      STATUS      current
      DESCRIPTION "Return a read-only array of the DestinationKeys of the Template."
      ::= { jmsQueueEntry 25  }
   
   
   jmsQueueBytesMaximum OBJECT-TYPE
      SYNTAX      INTEGER
      MAX-ACCESS  read-only
      STATUS      current
      DESCRIPTION "The value of bytesMaximum."
      ::= { jmsQueueEntry 35  }
   
   
   jmsQueueBytesThresholdHigh OBJECT-TYPE
      SYNTAX      INTEGER
      MAX-ACCESS  read-only
      STATUS      current
      DESCRIPTION "The value of bytesThresholdHigh."
      ::= { jmsQueueEntry 40  }
   
   
   jmsQueueBytesThresholdLow OBJECT-TYPE
      SYNTAX      INTEGER
      MAX-ACCESS  read-only
      STATUS      current
      DESCRIPTION "The value of bytesThresholdLow."
      ::= { jmsQueueEntry 45  }
   
   
   jmsQueueMessagesMaximum OBJECT-TYPE
      SYNTAX      INTEGER
      MAX-ACCESS  read-only
      STATUS      current
      DESCRIPTION "The value of messagesMaximum."
      ::= { jmsQueueEntry 50  }
   
   
   jmsQueueMessagesThresholdHigh OBJECT-TYPE
      SYNTAX      INTEGER
      MAX-ACCESS  read-only
      STATUS      current
      DESCRIPTION "The value of messagesThresholdHigh."
      ::= { jmsQueueEntry 55  }
   
   
   jmsQueueMessagesThresholdLow OBJECT-TYPE
      SYNTAX      INTEGER
      MAX-ACCESS  read-only
      STATUS      current
      DESCRIPTION "The value of messagesThresholdLow."
      ::= { jmsQueueEntry 60  }
   
   
   jmsQueuePriorityOverride OBJECT-TYPE
      SYNTAX      INTEGER
      MAX-ACCESS  read-only
      STATUS      current
      DESCRIPTION "The priority override value."
      ::= { jmsQueueEntry 65  }
   
   
   jmsQueueTimeToDeliverOverride OBJECT-TYPE
      SYNTAX      INTEGER
      MAX-ACCESS  read-only
      STATUS      current
      DESCRIPTION "The time-to-deliver override in milliseconds.  
      This is the delay between when a message is produced and 
      when it is made visible on its target destination."
      ::= { jmsQueueEntry 70  }
   
   
   jmsQueueRedeliveryDelayOverride OBJECT-TYPE
      SYNTAX      INTEGER
      MAX-ACCESS  read-only
      STATUS      current
      DESCRIPTION "The redelivery delay override in milliseconds 
      for roll backs and recovers of consumed messages."
      ::= { jmsQueueEntry 75  }
   
   
   jmsQueueRedeliveryLimit OBJECT-TYPE
      SYNTAX      INTEGER
      MAX-ACCESS  read-only
      STATUS      current
      DESCRIPTION "The number of redelivery tries a message may have 
      before it is placed in the error destination."
      ::= { jmsQueueEntry 80  }
   
   
   jmsQueueErrorDestination OBJECT-TYPE
      SYNTAX      DisplayString (SIZE (1..256))
      MAX-ACCESS  read-only
      STATUS      current
      DESCRIPTION "The error destination for messages that 
      have reach their redelivery limit."
      ::= { jmsQueueEntry 85  }
   
   
   jmsQueueTimeToLiveOverride OBJECT-TYPE
      SYNTAX      INTEGER
      MAX-ACCESS  read-only
      STATUS      current
      DESCRIPTION "The <timeToLiveOverride> attribute defines the time-to-live assigned 
      to all messages that arrive at the destination regardless of 
      the time-to-live specified by the producer."
      ::= { jmsQueueEntry 90  }
   
   
   jmsQueueDeliveryModeOverride OBJECT-TYPE
      SYNTAX      DisplayString (SIZE (1..256))
      MAX-ACCESS  read-only
      STATUS      current
      DESCRIPTION "The <deliveryModeOverride> attribute defines the delivery mode assigned 
      to all messages that arrive at the destination regardless
      of the delivery mode specified by the producer."
      ::= { jmsQueueEntry 95  }
   
   
   jmsQueueJNDIName OBJECT-TYPE
      SYNTAX      DisplayString (SIZE (1..256))
      MAX-ACCESS  read-only
      STATUS      current
      DESCRIPTION "The JNDI name of the destination."
      ::= { jmsQueueEntry 100  }
   
   
   jmsQueueStoreEnabled OBJECT-TYPE
      SYNTAX      DisplayString (SIZE (1..16))
      MAX-ACCESS  read-only
      STATUS      current
      DESCRIPTION "One of tru, false, or default.  See setStoreEnabled() for more
      information"
      ::= { jmsQueueEntry 105  }
   
   
   jmsServerTable OBJECT-TYPE
      SYNTAX      SEQUENCE OF JmsServerEntry
      MAX-ACCESS  not-accessible
      STATUS      current
      DESCRIPTION "This table is used to monitor an EJBHome object of an Entity bean."
      ::= { wls 660  }
      
   
   jmsServerEntry OBJECT-TYPE
      SYNTAX      JmsServerEntry
      MAX-ACCESS  not-accessible
      STATUS      current
      DESCRIPTION "Entry of jmsServerTable"
      INDEX { jmsServerIndex}
      ::= { jmsServerTable 1 }
      
   JmsServerEntry ::=
      SEQUENCE
      {
         jmsServerIndex       DisplayString (SIZE (1..16)),
         jmsServerObjectName  DisplayString (SIZE (1..256)),
         jmsServerType        DisplayString (SIZE (1..64)),
         jmsServerName        DisplayString (SIZE (1..64)),
         jmsServerParent      DisplayString (SIZE (1..256)),
         jmsServerTargets     DisplayString (SIZE (1..2048)),
         jmsServerSessionPools DisplayString (SIZE (1..2048)),
         jmsServerDestinations DisplayString (SIZE (1..2048)),
         jmsServerStore       DisplayString (SIZE (1..256)),
         jmsServerBytesMaximum INTEGER,
         jmsServerBytesThresholdHigh INTEGER,
         jmsServerBytesThresholdLow INTEGER,
         jmsServerMessagesMaximum INTEGER,
         jmsServerMessagesThresholdHigh INTEGER,
         jmsServerMessagesThresholdLow INTEGER,
         jmsServerInsertionPausedAtStartup OCTET STRING,
         jmsServerStoreEnabled OCTET STRING,
         jmsServerAllowsPersistentDowngrade OCTET STRING,
         jmsServerExpirationScanInterval INTEGER,
         jmsServerProductionPausedAtStartup OCTET STRING,
         jmsServerTemporaryTemplateName OCTET STRING,
         jmsServerMaximumMessageSize INTEGER,
         jmsServerDeploymentOrder INTEGER,
         jmsServerMessageBufferSize Counter64,
         jmsServerBlockingSendPolicy OCTET STRING,
         jmsServerHostingTemporaryDestinations OCTET STRING,
         jmsServerPagingDirectory OCTET STRING,
         jmsServerTemporaryTemplateResource OCTET STRING,
         jmsServerConsumptionPausedAtStartup OCTET STRING
      }
      
   
   jmsServerIndex OBJECT-TYPE
      SYNTAX      DisplayString (SIZE (1..16))
      MAX-ACCESS  read-only
      STATUS      current
      DESCRIPTION "Unique value directed from ObjectName which is used as table index"
      ::= { jmsServerEntry 1  }
   
   
   jmsServerObjectName OBJECT-TYPE
      SYNTAX      DisplayString (SIZE (1..256))
      MAX-ACCESS  read-only
      STATUS      current
      DESCRIPTION "JMX-standard MBean name"
      ::= { jmsServerEntry 5  }
   
   
   jmsServerType OBJECT-TYPE
      SYNTAX      DisplayString (SIZE (1..64))
      MAX-ACCESS  read-only
      STATUS      current
      DESCRIPTION "BEA-proprietary MBean type"
      ::= { jmsServerEntry 10  }
   
   
   jmsServerName OBJECT-TYPE
      SYNTAX      DisplayString (SIZE (1..64))
      MAX-ACCESS  read-only
      STATUS      current
      DESCRIPTION "BEA-proprietary MBean name"
      ::= { jmsServerEntry 15  }
   
   
   jmsServerParent OBJECT-TYPE
      SYNTAX      DisplayString (SIZE (1..256))
      MAX-ACCESS  read-only
      STATUS      current
      DESCRIPTION "BEA-proprietary Parent object's identification, with syntax
      <type>:<name>"
      ::= { jmsServerEntry 20  }
   
   
   jmsServerTargets OBJECT-TYPE
      SYNTAX      DisplayString (SIZE (1..2048))
      MAX-ACCESS  read-only
      STATUS      current
      DESCRIPTION "Targets on which this deployment is deployed."
      ::= { jmsServerEntry 25  }
   
   
   jmsServerSessionPools OBJECT-TYPE
      SYNTAX      DisplayString (SIZE (1..2048))
      MAX-ACCESS  read-only
      STATUS      current
      DESCRIPTION "Get all the session pools defined for the JMS Server."
      ::= { jmsServerEntry 30  }
   
   
   jmsServerDestinations OBJECT-TYPE
      SYNTAX      DisplayString (SIZE (1..2048))
      MAX-ACCESS  read-only
      STATUS      current
      DESCRIPTION "A map containing all defined destinations and their associated JNDI
      names."
      ::= { jmsServerEntry 35  }
   
   
   jmsServerStore OBJECT-TYPE
      SYNTAX      DisplayString (SIZE (1..256))
      MAX-ACCESS  read-only
      STATUS      current
      DESCRIPTION "Get the backing store for the JMS server."
      ::= { jmsServerEntry 40  }
   
   
   jmsServerBytesMaximum OBJECT-TYPE
      SYNTAX      INTEGER
      MAX-ACCESS  read-only
      STATUS      current
      DESCRIPTION "The value of bytesMaximum.
      This is the maximum number  of bytes that can be stored in  
      the JMS Server  at  any  one  time."
      ::= { jmsServerEntry 45  }
   
   
   jmsServerBytesThresholdHigh OBJECT-TYPE
      SYNTAX      INTEGER
      MAX-ACCESS  read-only
      STATUS      current
      DESCRIPTION "The value of bytesThresholdHigh. If there is no threshold condition  
      and  the  number  of  bytes  stored  in  the  JMS Server exceeds this value,  
      then the condition is set and  an  event is generated"
      ::= { jmsServerEntry 50  }
   
   
   jmsServerBytesThresholdLow OBJECT-TYPE
      SYNTAX      INTEGER
      MAX-ACCESS  read-only
      STATUS      current
      DESCRIPTION "The value of bytesThresholdLow. If  there  is  a  threshold condition and 
      the number of bytes stored in the JMS Server drops below this value,  
      then the condition is cleared and an event is generated."
      ::= { jmsServerEntry 55  }
   
   
   jmsServerMessagesMaximum OBJECT-TYPE
      SYNTAX      INTEGER
      MAX-ACCESS  read-only
      STATUS      current
      DESCRIPTION "The value of messagesMaximum. This is the maximum number of messages that can be stored 
      in  the  JMS Server  at  any  one  time. A value of zero means there is no limit."
      ::= { jmsServerEntry 60  }
   
   
   jmsServerMessagesThresholdHigh OBJECT-TYPE
      SYNTAX      INTEGER
      MAX-ACCESS  read-only
      STATUS      current
      DESCRIPTION "The value of messagesThresholdHigh. If there is no threshold condition and the number 
      of  messages stored in the JMS Server exceeds this value,  then the condition is set 
      and an event is generated"
      ::= { jmsServerEntry 65  }
   
   
   jmsServerMessagesThresholdLow OBJECT-TYPE
      SYNTAX      INTEGER
      MAX-ACCESS  read-only
      STATUS      current
      DESCRIPTION "The value of messagesThresholdLow. If  there is a threshold condition and the nubmer 
      of  messages  stored  in  the  JMS Server drops below this value,  
      then the condition  is  cleared  and  an event is generated."
      ::= { jmsServerEntry 70  }
   
   
   jmsServerInsertionPausedAtStartup OBJECT-TYPE
      SYNTAX      OCTET STRING
      MAX-ACCESS  read-only
      STATUS      current
      DESCRIPTION "Indicates whether insertion is paused at startup on destinations targeted to this JMS server. A destination cannot receive any new messages while it is paused.  When the value is set to true, then immediately after the host server instance is booted, then this JMS server and its targeted destinations are modified such that they are in a 'insertion paused' state, which results preventing messages that are result of the 'in-flight' work completion to arrive on those destinations.  Note: For a detailed definition of 'in-flight' work/messages, see weblogic.management.runtime.JMSServerRuntimeMBean#resumeInsertion and weblogic.management.runtime.JMSDestinationRuntime#resumeInsertion  To allow in-flight work messages to appear on the destinations, later you will have to change the state of this JMS server to an 'insertion enabled' state by setting this value to false, and then either redeploy the JMS server or reboot the hosting server instance.  When the value is set to default, then the Insertion Paused At Startup is determined based on the corresponding setting on the individual destination."
      ::= { jmsServerEntry 71  }
   
   
   jmsServerStoreEnabled OBJECT-TYPE
      SYNTAX      OCTET STRING
      MAX-ACCESS  read-only
      STATUS      current
      DESCRIPTION "Specifies whether message persistence is supported for this JMS server.  When set to true, the default, then if the JMS server has no store configured, the targeted WebLogic Server instance's default store is used to store persistent messages. When set to false, then this JMS server does not support persistent messages, and instead downgrades them to non-persistent.  BEA recommends not setting this parameter to false. It is available to provide compatibility with older releases."
      ::= { jmsServerEntry 72  }
   
   
   jmsServerAllowsPersistentDowngrade OBJECT-TYPE
      SYNTAX      OCTET STRING
      MAX-ACCESS  read-only
      STATUS      current
      DESCRIPTION "Specifies whether JMS clients will get an exception when sending persistent messages to a destination targeted to a JMS server that does not have a persistent store configured. This parameter only has effect when the Store Enabled parameter is disabled (false).  When set to false, the default, clients will get an exception when sending persistent messages to a JMS server with no store configured. When set to true, then persistent messages are downgraded to non-persistent; however, the send operations are allowed to continue."
      ::= { jmsServerEntry 73  }
   
   
   jmsServerExpirationScanInterval OBJECT-TYPE
      SYNTAX      INTEGER
      MAX-ACCESS  read-only
      STATUS      current
      DESCRIPTION "The number of seconds between this JMS server's cycles of scanning local destinations for expired messages. A value of 0 disables active scanning. A very large scan interval effectively disables active scanning.  With scanning disabled, users still do not receive expired messages and any expired messages that are discovered by other system activities are removed. However, expired messages sitting in idle destinations (such as an inactive queue or disconnected durable subscriber) are not removed and continue to consume system resources.  The scanning cycle for expired messages occurs as follows:   After the specified waiting period, the JMS server devotes a separate thread to scan all of its local destinations for expired messages.   After the scanning is completed, all located expired messages are processed according to the specified Expiration Policy on the destination (Discard, Log, or Redirect).   The entire process repeats after another specified waiting period.    Note: Because a new scan does not start until the current one is finished and until the specified waiting period ends, an expired message could still remain in the system for the maximum scan waiting period plus the amount of time it takes to perform the scan."
      ::= { jmsServerEntry 74  }
   
   
   jmsServerProductionPausedAtStartup OBJECT-TYPE
      SYNTAX      OCTET STRING
      MAX-ACCESS  read-only
      STATUS      current
      DESCRIPTION "Specifies whether production is paused at server startup on destinations targeted to this JMS server. A destination cannot receive any new messages while it is paused.  When the value is set to true, then immediately after the host server instance is rebooted, then this JMS server and its targeted destinations are modified such that they are in a 'production paused' state, which results in preventing new message production activities on those destinations.  To resume normal new message production activity, later you will have to change the state of this JMS server to a 'production enabled' state by setting this value to false, and then either redeploy the JMS server or reboot the hosting server instance.   When the value is set to default, then the Production Paused At Startup is determined based on the corresponding setting on the individual destination."
      ::= { jmsServerEntry 75  }
   
   
   jmsServerTemporaryTemplateName OBJECT-TYPE
      SYNTAX      OCTET STRING
      MAX-ACCESS  read-only
      STATUS      current
      DESCRIPTION "The name of a configured JMS template that this JMS server uses to create temporary destinations.  Entering a template name, requires you to specify the JMS module that contains this template. However, a template name cannot be specified if the Hosting Temporary Destinations field is disabled.  Note: If the specified JMS template provides persistent store values, they are ignored because temporary destinations do not support persistent messaging."
      ::= { jmsServerEntry 76  }
   
   
   jmsServerMaximumMessageSize OBJECT-TYPE
      SYNTAX      INTEGER
      MAX-ACCESS  read-only
      STATUS      current
      DESCRIPTION "The maximum number of bytes allowed in individual messages on this JMS server. The size of a message includes the message body, any user-defined properties, and the user-defined JMS header fields JMSCorrelationID and JMSType.  The maximum message size is only enforced for the initial production of a message. Messages that are redirected to an error destination or forwarded to a member of a distributed destination are not checked for size. For instance, if a destination and its corresponding error destination are configured with a maximum message size of 128K bytes and 64K bytes, respectively, a message of 96K bytes could be redirected to the error destination (even though it exceeds the 64K byte maximum), but a producer could not directly send the 96K byte message to the error destination.  Note: Any change to this maximum affects only incoming messages; stored messages are not affected."
      ::= { jmsServerEntry 77  }
   
   
   jmsServerDeploymentOrder OBJECT-TYPE
      SYNTAX      INTEGER
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { jmsServerEntry 78  }
   
   
   jmsServerMessageBufferSize OBJECT-TYPE
      SYNTAX      Counter64
      MAX-ACCESS  read-only
      STATUS      current
      DESCRIPTION "The amount of memory (in bytes) that this JMS server can use to store message bodies before it writes them to disk. When the JMS server writes the message bodies to disk, it clears them from memory.  A value of -1 (the default) specifies that the server will automatically determine a size based on the maximum heap size of the JVM. This default will be set to either one-third the maximum heap size, or 512 megabytes, whichever is larger.  The larger the buffer, the more memory JMS will consume when many messages are waiting on queues or topics. Once the buffer is surpassed, JMS may write message bodies to the directory specified by PagingDirectory in an effort to reduce memory usage below this buffer.  Surpassing the buffer size does not stop the JMS server from accepting new messages. It is still possible to run out of memory if messages are arriving faster than they can be written to disk. Users with high messaging loads who wish to support the highest possible availability should consider setting a quota or setting a threshold and enabling flow control.  Paging is always supported."
      ::= { jmsServerEntry 79  }
   
   
   jmsServerBlockingSendPolicy OBJECT-TYPE
      SYNTAX      OCTET STRING
      MAX-ACCESS  read-only
      STATUS      current
      DESCRIPTION "Determines whether the JMS server delivers smaller messages before larger ones when a destination has exceeded its maximum number of messages. FIFO prevents the JMS server from delivering smaller messages when larger ones are already waiting for space. Preemptive allows smaller send requests to preempt previous larger ones when there is sufficient space for smaller messages on the destination.  This policy is defined only for the JMS server; it cannot be set on individual destinations.  Additional information on the FIFO and Preemptive policies is provided below.  FIFO (first in, first out) indicates that all send requests for the same destination are queued up one behind the other until space is available. No send request is permitted to successfully complete if there is another send request waiting for space before it. When space is limited, the FIFO policy prevents the starvation of larger requests because smaller requests cannot continuously use the remaining available space. Smaller requests are delayed, though not starved, until the larger request can be completed. When space does become available, requests are considered in the order in which they were made. If there is sufficient space for a given request, then that request is completed and the next request is considered. If there is insufficient space for a given request, then no further requests are considered until sufficient space becomes available for the current request to complete.  Preemptive indicates that a send operation can preempt other blocking send operations if space is available. That is, if there is sufficient space for the current request, then that space is used even if there are other requests waiting for space. When space is limited, the Preemptive policy can result in the starvation of larger requests. For example, if there is insufficient available space for a large request, then it is queued up behind other existing requests. When space does become available, all requests are considered in the order in which they were originally made. If there is sufficient space for a given request, then that request is allowed to continue and the next request is considered. If there is insufficient space for a given request, then that request is skipped and the next request is considered."
      ::= { jmsServerEntry 80  }
   
   
   jmsServerHostingTemporaryDestinations OBJECT-TYPE
      SYNTAX      OCTET STRING
      MAX-ACCESS  read-only
      STATUS      current
      DESCRIPTION "Specifies whether this JMS server can be used to host temporary destinations.  If this field is enabled and no Temporary Template Name is defined, then the temporary destinations created on this JMS server will use all default destination values. If this field is enabled, then the JMS template to be used for creating temporary destinations is specified by the Temporary Template Name field. If this field is disabled, then this JMS server will not host temporary destinations."
      ::= { jmsServerEntry 81  }
   
   
   jmsServerPagingDirectory OBJECT-TYPE
      SYNTAX      OCTET STRING
      MAX-ACCESS  read-only
      STATUS      current
      DESCRIPTION "Specifies where message bodies are written when the size of the message bodies in the JMS server exceeds the message buffer size.  If unspecified, messages are written to the default tmp directory inside the server-name subdirectory of a domain's root directory. For example, domain-name/servers/server-name/tmp, where domain-name is the root directory of your domain.   For best performance, this directory should not be the same as the directory used by the JMS server's persistent store."
      ::= { jmsServerEntry 82  }
   
   
   jmsServerTemporaryTemplateResource OBJECT-TYPE
      SYNTAX      OCTET STRING
      MAX-ACCESS  read-only
      STATUS      current
      DESCRIPTION "The name of a JMS module that contains a template that this JMS server can use to create temporary destinations.  Entering a JMS module name requires you to specify a temporary template name. However, a module name cannot be specified if the Hosting Temporary Destinations field is disabled."
      ::= { jmsServerEntry 83  }
   
   
   jmsServerConsumptionPausedAtStartup OBJECT-TYPE
      SYNTAX      OCTET STRING
      MAX-ACCESS  read-only
      STATUS      current
      DESCRIPTION "Indicates whether consumption is paused at startup on destinations targeted to this JMS server at startup. A destination cannot receive any new messages while it is paused.  When the value is set to true, then immediately after the host server instance is booted, then this JMS server and its targeted destinations are modified such that they are in a 'consumption paused' state, which prevents any message consuming activity on those destinations.  To allow normal message consumption on the destinations, later you will have to change the state of this JMS server to a 'consumption enabled' state by setting this value to false, and then either redeploy the JMS server or reboot the hosting server instance.  When the value is set to default, then the Consumption Paused At Startup is determined based on the corresponding setting on the individual destination."
      ::= { jmsServerEntry 84  }
   
   
   jmsSessionPoolTable OBJECT-TYPE
      SYNTAX      SEQUENCE OF JmsSessionPoolEntry
      MAX-ACCESS  not-accessible
      STATUS      current
      DESCRIPTION "This table represents a JMS session pool."
      ::= { wls 670  }
      
   
   jmsSessionPoolEntry OBJECT-TYPE
      SYNTAX      JmsSessionPoolEntry
      MAX-ACCESS  not-accessible
      STATUS      current
      DESCRIPTION "Entry of jmsSessionPoolTable"
      INDEX { jmsSessionPoolIndex}
      ::= { jmsSessionPoolTable 1 }
      
   JmsSessionPoolEntry ::=
      SEQUENCE
      {
         jmsSessionPoolIndex  DisplayString (SIZE (1..16)),
         jmsSessionPoolObjectName DisplayString (SIZE (1..256)),
         jmsSessionPoolType   DisplayString (SIZE (1..64)),
         jmsSessionPoolName   DisplayString (SIZE (1..64)),
         jmsSessionPoolParent DisplayString (SIZE (1..256)),
         jmsSessionPoolConnectionConsumers DisplayString (SIZE (1..2048)),
         jmsSessionPoolConnectionFactory DisplayString (SIZE (1..256)),
         jmsSessionPoolListenerClass DisplayString (SIZE (1..256)),
         jmsSessionPoolAcknowledgeMode DisplayString (SIZE (1..32)),
         jmsSessionPoolSessionsMaximum INTEGER,
         jmsSessionPoolTransacted INTEGER
                     {
                        true(1),
                        false(2)
                     }
      }
      
   
   jmsSessionPoolIndex OBJECT-TYPE
      SYNTAX      DisplayString (SIZE (1..16))
      MAX-ACCESS  read-only
      STATUS      current
      DESCRIPTION "Unique value directed from ObjectName which is used as table index"
      ::= { jmsSessionPoolEntry 1  }
   
   
   jmsSessionPoolObjectName OBJECT-TYPE
      SYNTAX      DisplayString (SIZE (1..256))
      MAX-ACCESS  read-only
      STATUS      current
      DESCRIPTION "JMX-standard MBean name"
      ::= { jmsSessionPoolEntry 5  }
   
   
   jmsSessionPoolType OBJECT-TYPE
      SYNTAX      DisplayString (SIZE (1..64))
      MAX-ACCESS  read-only
      STATUS      current
      DESCRIPTION "BEA-proprietary MBean type"
      ::= { jmsSessionPoolEntry 10  }
   
   
   jmsSessionPoolName OBJECT-TYPE
      SYNTAX      DisplayString (SIZE (1..64))
      MAX-ACCESS  read-only
      STATUS      current
      DESCRIPTION "BEA-proprietary MBean name"
      ::= { jmsSessionPoolEntry 15  }
   
   
   jmsSessionPoolParent OBJECT-TYPE
      SYNTAX      DisplayString (SIZE (1..256))
      MAX-ACCESS  read-only
      STATUS      current
      DESCRIPTION "BEA-proprietary Parent object's identification, with syntax
      <type>:<name>"
      ::= { jmsSessionPoolEntry 20  }
   
   
   jmsSessionPoolConnectionConsumers OBJECT-TYPE
      SYNTAX      DisplayString (SIZE (1..2048))
      MAX-ACCESS  read-only
      STATUS      current
      DESCRIPTION "Return a read-only array of the ConnectionConsumers of the
      SessionPool."
      ::= { jmsSessionPoolEntry 25  }
   
   
   jmsSessionPoolConnectionFactory OBJECT-TYPE
      SYNTAX      DisplayString (SIZE (1..256))
      MAX-ACCESS  read-only
      STATUS      current
      DESCRIPTION "Return the JNDI name of the connection factory for the session pool"
      ::= { jmsSessionPoolEntry 30  }
   
   
   jmsSessionPoolListenerClass OBJECT-TYPE
      SYNTAX      DisplayString (SIZE (1..256))
      MAX-ACCESS  read-only
      STATUS      current
      DESCRIPTION "Return the name of the listener class for the SessionPool."
      ::= { jmsSessionPoolEntry 35  }
   
   
   jmsSessionPoolAcknowledgeMode OBJECT-TYPE
      SYNTAX      DisplayString (SIZE (1..32))
      MAX-ACCESS  read-only
      STATUS      current
      DESCRIPTION "Return the acknowledge mode of the SessionPool."
      ::= { jmsSessionPoolEntry 40  }
   
   
   jmsSessionPoolSessionsMaximum OBJECT-TYPE
      SYNTAX      INTEGER
      MAX-ACCESS  read-only
      STATUS      current
      DESCRIPTION "Return the maximum number of sessions allowed for the SessionPool."
      ::= { jmsSessionPoolEntry 45  }
   
   
   jmsSessionPoolTransacted OBJECT-TYPE
      SYNTAX      INTEGER
                  {
                     true(1),
                     false(2)
                  }
      
      MAX-ACCESS  read-only
      STATUS      current
      DESCRIPTION "returns boolean true if the SessionPool is transacted"
      ::= { jmsSessionPoolEntry 50  }
   
   
   jmsTopicTable OBJECT-TYPE
      SYNTAX      SEQUENCE OF JmsTopicEntry
      MAX-ACCESS  not-accessible
      STATUS      current
      DESCRIPTION "A JMS Destination topic."
      ::= { wls 680  }
      
   
   jmsTopicEntry OBJECT-TYPE
      SYNTAX      JmsTopicEntry
      MAX-ACCESS  not-accessible
      STATUS      current
      DESCRIPTION "Entry of jmsTopicTable"
      INDEX { jmsTopicIndex}
      ::= { jmsTopicTable 1 }
      
   JmsTopicEntry ::=
      SEQUENCE
      {
         jmsTopicIndex        DisplayString (SIZE (1..16)),
         jmsTopicObjectName   DisplayString (SIZE (1..256)),
         jmsTopicType         DisplayString (SIZE (1..64)),
         jmsTopicName         DisplayString (SIZE (1..64)),
         jmsTopicParent       DisplayString (SIZE (1..256)),
         jmsTopicDestinationKeys DisplayString (SIZE (1..2048)),
         jmsTopicBytesMaximum INTEGER,
         jmsTopicBytesThresholdHigh INTEGER,
         jmsTopicBytesThresholdLow INTEGER,
         jmsTopicMessagesMaximum INTEGER,
         jmsTopicMessagesThresholdHigh INTEGER,
         jmsTopicMessagesThresholdLow INTEGER,
         jmsTopicPriorityOverride INTEGER,
         jmsTopicTimeToDeliverOverride INTEGER,
         jmsTopicRedeliveryDelayOverride INTEGER,
         jmsTopicRedeliveryLimit INTEGER,
         jmsTopicErrorDestination DisplayString (SIZE (1..256)),
         jmsTopicTimeToLiveOverride INTEGER,
         jmsTopicDeliveryModeOverride DisplayString (SIZE (1..256)),
         jmsTopicJNDIName     DisplayString (SIZE (1..256)),
         jmsTopicStoreEnabled DisplayString (SIZE (1..16)),
         jmsTopicMulticastAddress DisplayString (SIZE (1..16)),
         jmsTopicMulticastTTL INTEGER,
         jmsTopicMulticastPort INTEGER
      }
      
   
   jmsTopicIndex OBJECT-TYPE
      SYNTAX      DisplayString (SIZE (1..16))
      MAX-ACCESS  read-only
      STATUS      current
      DESCRIPTION "Unique value directed from ObjectName which is used as table index"
      ::= { jmsTopicEntry 1  }
   
   
   jmsTopicObjectName OBJECT-TYPE
      SYNTAX      DisplayString (SIZE (1..256))
      MAX-ACCESS  read-only
      STATUS      current
      DESCRIPTION "JMX-standard MBean name"
      ::= { jmsTopicEntry 5  }
   
   
   jmsTopicType OBJECT-TYPE
      SYNTAX      DisplayString (SIZE (1..64))
      MAX-ACCESS  read-only
      STATUS      current
      DESCRIPTION "BEA-proprietary MBean type"
      ::= { jmsTopicEntry 10  }
   
   
   jmsTopicName OBJECT-TYPE
      SYNTAX      DisplayString (SIZE (1..64))
      MAX-ACCESS  read-only
      STATUS      current
      DESCRIPTION "BEA-proprietary MBean name"
      ::= { jmsTopicEntry 15  }
   
   
   jmsTopicParent OBJECT-TYPE
      SYNTAX      DisplayString (SIZE (1..256))
      MAX-ACCESS  read-only
      STATUS      current
      DESCRIPTION "BEA-proprietary Parent object's identification, with syntax
      <type>:<name>"
      ::= { jmsTopicEntry 20  }
   
   
   jmsTopicDestinationKeys OBJECT-TYPE
      SYNTAX      DisplayString (SIZE (1..2048))
      MAX-ACCESS  read-only
      STATUS      current
      DESCRIPTION "Return a read-only array of the DestinationKeys of the Template."
      ::= { jmsTopicEntry 25  }
   
   
   jmsTopicBytesMaximum OBJECT-TYPE
      SYNTAX      INTEGER
      MAX-ACCESS  read-only
      STATUS      current
      DESCRIPTION "The value of bytesMaximum."
      ::= { jmsTopicEntry 35  }
   
   
   jmsTopicBytesThresholdHigh OBJECT-TYPE
      SYNTAX      INTEGER
      MAX-ACCESS  read-only
      STATUS      current
      DESCRIPTION "The value of bytesThresholdHigh."
      ::= { jmsTopicEntry 40  }
   
   
   jmsTopicBytesThresholdLow OBJECT-TYPE
      SYNTAX      INTEGER
      MAX-ACCESS  read-only
      STATUS      current
      DESCRIPTION "The value of bytesThresholdLow."
      ::= { jmsTopicEntry 45  }
   
   
   jmsTopicMessagesMaximum OBJECT-TYPE
      SYNTAX      INTEGER
      MAX-ACCESS  read-only
      STATUS      current
      DESCRIPTION "The value of messagesMaximum."
      ::= { jmsTopicEntry 50  }
   
   
   jmsTopicMessagesThresholdHigh OBJECT-TYPE
      SYNTAX      INTEGER
      MAX-ACCESS  read-only
      STATUS      current
      DESCRIPTION "The value of messagesThresholdHigh."
      ::= { jmsTopicEntry 55  }
   
   
   jmsTopicMessagesThresholdLow OBJECT-TYPE
      SYNTAX      INTEGER
      MAX-ACCESS  read-only
      STATUS      current
      DESCRIPTION "The value of messagesThresholdLow."
      ::= { jmsTopicEntry 60  }
   
   
   jmsTopicPriorityOverride OBJECT-TYPE
      SYNTAX      INTEGER
      MAX-ACCESS  read-only
      STATUS      current
      DESCRIPTION "The priority override value."
      ::= { jmsTopicEntry 65  }
   
   
   jmsTopicTimeToDeliverOverride OBJECT-TYPE
      SYNTAX      INTEGER
      MAX-ACCESS  read-only
      STATUS      current
      DESCRIPTION "The time-to-deliver override in milliseconds.  
      This is the delay between when a message is produced and 
      when it is made visible on its target destination."
      ::= { jmsTopicEntry 70  }
   
   
   jmsTopicRedeliveryDelayOverride OBJECT-TYPE
      SYNTAX      INTEGER
      MAX-ACCESS  read-only
      STATUS      current
      DESCRIPTION "The redelivery delay override in milliseconds 
      for roll backs and recovers of consumed messages."
      ::= { jmsTopicEntry 75  }
   
   
   jmsTopicRedeliveryLimit OBJECT-TYPE
      SYNTAX      INTEGER
      MAX-ACCESS  read-only
      STATUS      current
      DESCRIPTION "The number of redelivery tries a message may have 
      before it is placed in the error destination."
      ::= { jmsTopicEntry 80  }
   
   
   jmsTopicErrorDestination OBJECT-TYPE
      SYNTAX      DisplayString (SIZE (1..256))
      MAX-ACCESS  read-only
      STATUS      current
      DESCRIPTION "The error destination for messages that 
      have reach their redelivery limit."
      ::= { jmsTopicEntry 85  }
   
   
   jmsTopicTimeToLiveOverride OBJECT-TYPE
      SYNTAX      INTEGER
      MAX-ACCESS  read-only
      STATUS      current
      DESCRIPTION "The <timeToLiveOverride> attribute defines the time-to-live assigned 
      to all messages that arrive at the destination regardless of 
      the time-to-live specified by the producer."
      ::= { jmsTopicEntry 90  }
   
   
   jmsTopicDeliveryModeOverride OBJECT-TYPE
      SYNTAX      DisplayString (SIZE (1..256))
      MAX-ACCESS  read-only
      STATUS      current
      DESCRIPTION "The <deliveryModeOverride> attribute defines the delivery mode assigned 
      to all messages that arrive at the destination regardless
      of the delivery mode specified by the producer."
      ::= { jmsTopicEntry 95  }
   
   
   jmsTopicJNDIName OBJECT-TYPE
      SYNTAX      DisplayString (SIZE (1..256))
      MAX-ACCESS  read-only
      STATUS      current
      DESCRIPTION "The JNDI name of the destination."
      ::= { jmsTopicEntry 100  }
   
   
   jmsTopicStoreEnabled OBJECT-TYPE
      SYNTAX      DisplayString (SIZE (1..16))
      MAX-ACCESS  read-only
      STATUS      current
      DESCRIPTION "One of true, false, or default.  See setStoreEnabled() for more
      information"
      ::= { jmsTopicEntry 105  }
   
   
   jmsTopicMulticastAddress OBJECT-TYPE
      SYNTAX      DisplayString (SIZE (1..16))
      MAX-ACCESS  read-only
      STATUS      current
      DESCRIPTION "The multicast address used by the destination."
      ::= { jmsTopicEntry 110  }
   
   
   jmsTopicMulticastTTL OBJECT-TYPE
      SYNTAX      INTEGER
      MAX-ACCESS  read-only
      STATUS      current
      DESCRIPTION "The time-to-live value for the multicast message."
      ::= { jmsTopicEntry 115  }
   
   
   jmsTopicMulticastPort OBJECT-TYPE
      SYNTAX      INTEGER
      MAX-ACCESS  read-only
      STATUS      current
      DESCRIPTION "The multicast port for the destination."
      ::= { jmsTopicEntry 120  }
   
   
   jmsVirtualDestinationTable OBJECT-TYPE
      SYNTAX      SEQUENCE OF JmsVirtualDestinationEntry
      MAX-ACCESS  not-accessible
      STATUS      current
      DESCRIPTION "This table represents a key value for a destination"
      ::= { wls 682  }
      
   
   jmsVirtualDestinationEntry OBJECT-TYPE
      SYNTAX      JmsVirtualDestinationEntry
      MAX-ACCESS  not-accessible
      STATUS      current
      DESCRIPTION "Entry of jmsVirtualDestinationTable"
      INDEX { jmsVirtualDestinationIndex}
      ::= { jmsVirtualDestinationTable 1 }
      
   JmsVirtualDestinationEntry ::=
      SEQUENCE
      {
         jmsVirtualDestinationIndex DisplayString (SIZE (1..16)),
         jmsVirtualDestinationObjectName DisplayString (SIZE (1..256)),
         jmsVirtualDestinationType DisplayString (SIZE (1..64)),
         jmsVirtualDestinationName DisplayString (SIZE (1..64)),
         jmsVirtualDestinationParent DisplayString (SIZE (1..256)),
         jmsVirtualDestinationJNDIName INTEGER
      }
      
   
   jmsVirtualDestinationIndex OBJECT-TYPE
      SYNTAX      DisplayString (SIZE (1..16))
      MAX-ACCESS  read-only
      STATUS      current
      DESCRIPTION "Unique value directed from ObjectName which is used as table index"
      ::= { jmsVirtualDestinationEntry 1  }
   
   
   jmsVirtualDestinationObjectName OBJECT-TYPE
      SYNTAX      DisplayString (SIZE (1..256))
      MAX-ACCESS  read-only
      STATUS      current
      DESCRIPTION "JMX-standard MBean name"
      ::= { jmsVirtualDestinationEntry 5  }
   
   
   jmsVirtualDestinationType OBJECT-TYPE
      SYNTAX      DisplayString (SIZE (1..64))
      MAX-ACCESS  read-only
      STATUS      current
      DESCRIPTION "BEA-proprietary MBean type"
      ::= { jmsVirtualDestinationEntry 10  }
   
   
   jmsVirtualDestinationName OBJECT-TYPE
      SYNTAX      DisplayString (SIZE (1..64))
      MAX-ACCESS  read-only
      STATUS      current
      DESCRIPTION "BEA-proprietary MBean name"
      ::= { jmsVirtualDestinationEntry 15  }
   
   
   jmsVirtualDestinationParent OBJECT-TYPE
      SYNTAX      DisplayString (SIZE (1..256))
      MAX-ACCESS  read-only
      STATUS      current
      DESCRIPTION "BEA-proprietary Parent object's identification, with syntax
      <type>:<name>"
      ::= { jmsVirtualDestinationEntry 20  }
   
   
   jmsVirtualDestinationJNDIName OBJECT-TYPE
      SYNTAX      INTEGER
      MAX-ACCESS  read-only
      STATUS      current
      DESCRIPTION "Return the JNDI name of the distributed destination."
      ::= { jmsVirtualDestinationEntry 25  }
   
   
   jtaTable OBJECT-TYPE
      SYNTAX      SEQUENCE OF JtaEntry
      MAX-ACCESS  not-accessible
      STATUS      current
      DESCRIPTION "This table provides access to the JTA configuration attributes."
      ::= { wls 690  }
      
   
   jtaEntry OBJECT-TYPE
      SYNTAX      JtaEntry
      MAX-ACCESS  not-accessible
      STATUS      current
      DESCRIPTION "Entry of jtaTable"
      INDEX { jtaIndex}
      ::= { jtaTable 1 }
      
   JtaEntry ::=
      SEQUENCE
      {
         jtaIndex             DisplayString (SIZE (1..16)),
         jtaObjectName        DisplayString (SIZE (1..256)),
         jtaType              DisplayString (SIZE (1..64)),
         jtaName              DisplayString (SIZE (1..64)),
         jtaParent            DisplayString (SIZE (1..256)),
         jtaTimeoutSeconds    INTEGER,
         jtaAbandonTimeoutSeconds INTEGER,
         jtaForgetHeuristics  INTEGER
                     {
                        true(1),
                        false(2)
                     }
         ,
         jtaBeforeCompletionIterationLimit INTEGER,
         jtaMaxTransactions   INTEGER,
         jtaMaxUniqueNameStatistics INTEGER,
         jtaMaxResourceRequestsOnServer INTEGER,
         jtaMaxResourceUnavailableMillis Counter64,
         jtaCheckpointIntervalSeconds INTEGER,
         jtaSerializeEnlistmentsGCIntervalMillis Counter64,
         jtaUnregisterResourceGracePeriod INTEGER,
         jtaSecurityInteropMode OCTET STRING,
         jtaMaxXACallMillis   Counter64
      }
      
   
   jtaIndex OBJECT-TYPE
      SYNTAX      DisplayString (SIZE (1..16))
      MAX-ACCESS  read-only
      STATUS      current
      DESCRIPTION "Unique value directed from ObjectName which is used as table index"
      ::= { jtaEntry 1  }
   
   
   jtaObjectName OBJECT-TYPE
      SYNTAX      DisplayString (SIZE (1..256))
      MAX-ACCESS  read-only
      STATUS      current
      DESCRIPTION "JMX-standard MBean name"
      ::= { jtaEntry 5  }
   
   
   jtaType OBJECT-TYPE
      SYNTAX      DisplayString (SIZE (1..64))
      MAX-ACCESS  read-only
      STATUS      current
      DESCRIPTION "BEA-proprietary MBean type"
      ::= { jtaEntry 10  }
   
   
   jtaName OBJECT-TYPE
      SYNTAX      DisplayString (SIZE (1..64))
      MAX-ACCESS  read-only
      STATUS      current
      DESCRIPTION "BEA-proprietary MBean name"
      ::= { jtaEntry 15  }
   
   
   jtaParent OBJECT-TYPE
      SYNTAX      DisplayString (SIZE (1..256))
      MAX-ACCESS  read-only
      STATUS      current
      DESCRIPTION "BEA-proprietary Parent object's identification, with syntax
      <type>:<name>"
      ::= { jtaEntry 20  }
   
   
   jtaTimeoutSeconds OBJECT-TYPE
      SYNTAX      INTEGER
      MAX-ACCESS  read-only
      STATUS      current
      DESCRIPTION "The transaction timeout in seconds."
      ::= { jtaEntry 25  }
   
   
   jtaAbandonTimeoutSeconds OBJECT-TYPE
      SYNTAX      INTEGER
      MAX-ACCESS  read-only
      STATUS      current
      DESCRIPTION "The transaction abandon timeout in seconds."
      ::= { jtaEntry 30  }
   
   
   jtaForgetHeuristics OBJECT-TYPE
      SYNTAX      INTEGER
                  {
                     true(1),
                     false(2)
                  }
      
      MAX-ACCESS  read-only
      STATUS      current
      DESCRIPTION "A boolean value (true Or false). Returns a boolean indicating whether the transaction manager
      will automatically perform an XAResource forget operation for 
      transaction heuristic completions."
      ::= { jtaEntry 35  }
   
   
   jtaBeforeCompletionIterationLimit OBJECT-TYPE
      SYNTAX      INTEGER
      MAX-ACCESS  read-only
      STATUS      current
      DESCRIPTION "The maximum number of iterations the transaction
      manager will perform the beforeCompletion synchronization callback."
      ::= { jtaEntry 40  }
   
   
   jtaMaxTransactions OBJECT-TYPE
      SYNTAX      INTEGER
      MAX-ACCESS  read-only
      STATUS      current
      DESCRIPTION "The maximum number of simultaneous in progress
      transactions allowed on a server."
      ::= { jtaEntry 45  }
   
   
   jtaMaxUniqueNameStatistics OBJECT-TYPE
      SYNTAX      INTEGER
      MAX-ACCESS  read-only
      STATUS      current
      DESCRIPTION "The maximum number of unique transaction names
      for which statistics will be maintained."
      ::= { jtaEntry 50  }
   
   
   jtaMaxResourceRequestsOnServer OBJECT-TYPE
      SYNTAX      INTEGER
      MAX-ACCESS  read-only
      STATUS      current
      DESCRIPTION "Maximum number of concurrent requests to resources allowed for each server."
      ::= { jtaEntry 51  }
   
   
   jtaMaxResourceUnavailableMillis OBJECT-TYPE
      SYNTAX      Counter64
      MAX-ACCESS  read-only
      STATUS      current
      DESCRIPTION "Maximum duration in milliseconds that a resource is declared dead. After the duration, the resource will be declared available again, even if the resource provider does not explicitly re-register the resource."
      ::= { jtaEntry 52  }
   
   
   jtaCheckpointIntervalSeconds OBJECT-TYPE
      SYNTAX      INTEGER
      MAX-ACCESS  read-only
      STATUS      current
      DESCRIPTION "The interval at which the transaction manager creates a new transaction log file and checks all old transaction log files to see if they are ready to be deleted."
      ::= { jtaEntry 53  }
   
   
   jtaSerializeEnlistmentsGCIntervalMillis OBJECT-TYPE
      SYNTAX      Counter64
      MAX-ACCESS  read-only
      STATUS      current
      DESCRIPTION "The interval at which internal objects used to serialize resource enlistment are cleaned up."
      ::= { jtaEntry 54  }
   
   
   jtaUnregisterResourceGracePeriod OBJECT-TYPE
      SYNTAX      INTEGER
      MAX-ACCESS  read-only
      STATUS      current
      DESCRIPTION "The grace period (number of seconds) that the transaction manager waits for transactions involving the resource to complete before unregistering a resource. The grace period can help minimize the risk of abandoned transactions because of an unregistered resource, such as a JDBC data source module packaged with an application.  During the specified grace period, the unregisterResource call will block until the call can return, and no new transactions are started for the associated resource. If the number of outstanding transactions for the resource goes to 0, the unregisterResource call returns immediately.  At the end of the grace period, if there are still outstanding transactions associated with the resource, the unregisterResource call returns and a log message is written on the server on which the resource was previously registered."
      ::= { jtaEntry 55  }
   
   
   jtaSecurityInteropMode OBJECT-TYPE
      SYNTAX      OCTET STRING
      MAX-ACCESS  read-only
      STATUS      current
      DESCRIPTION "Specifies the security mode of the communication channel used for XA calls between servers that participate in a global transaction. All server instances in a domain must have the same security mode setting.  Security Interoperability Mode options:  default  The transaction coordinator makes calls using the kernel identity over an admin channel if it is enabled, and anonymous otherwise. Man-in-the-middle attacks are possible if the admin channel is not enabled.  performance  The transaction coordinator makes calls using anonymous at all times. This implies a security risk since a malicious third party could then try to affect the outcome of transactions using a man-in-the-middle attack.  compatibility  The transaction coordinator makes calls as the kernel identity over an insecure channel. This is a high security risk because a successful man-in-the-middle attack would allow the attacker to gain administrative control over both domains. This setting should only be used when strong network security is in place."
      ::= { jtaEntry 56  }
   
   
   jtaMaxXACallMillis OBJECT-TYPE
      SYNTAX      Counter64
      MAX-ACCESS  read-only
      STATUS      current
      DESCRIPTION "Maximum allowed duration of XA calls to resources. If a particular XA call to a resource exceeds the limit, the resource is declared unavailable."
      ::= { jtaEntry 57  }
   
   
   kernelTable OBJECT-TYPE
      SYNTAX      SEQUENCE OF KernelEntry
      MAX-ACCESS  not-accessible
      STATUS      current
      DESCRIPTION "This table represents a kernel in the domain."
      ::= { wls 692  }
      
   
   kernelEntry OBJECT-TYPE
      SYNTAX      KernelEntry
      MAX-ACCESS  not-accessible
      STATUS      current
      DESCRIPTION "Entry of kernelTable"
      INDEX { kernelIndex}
      ::= { kernelTable 1 }
      
   KernelEntry ::=
      SEQUENCE
      {
         kernelIndex          DisplayString (SIZE (1..16)),
         kernelObjectName     DisplayString (SIZE (1..256)),
         kernelType           DisplayString (SIZE (1..64)),
         kernelName           DisplayString (SIZE (1..64)),
         kernelParent         DisplayString (SIZE (1..256)),
         kernelCompleteCOMMessageTimeout INTEGER,
         kernelCompleteHTTPMessageTimeout INTEGER,
         kernelCompleteIIOPMessageTimeout INTEGER,
         kernelCompleteT3MessageTimeout INTEGER,
         kernelDefaultGIOPMinorVersion INTEGER,
         kernelDefaultProtocol DisplayString (SIZE (1..256)),
         kernelDefaultSecureProtocol DisplayString (SIZE (1..256)),
         kernelDGCIdlePeriodsUntilTimeout INTEGER,
         kernelIdleIIOPConnectionTimeout INTEGER,
         kernelMaxCOMMessageSize INTEGER,
         kernelMaxHTTPMessageSize INTEGER,
         kernelMaxIIOPMessageSize INTEGER,
         kernelMaxOpenSockCount INTEGER,
         kernelMaxT3MessageSize INTEGER,
         kernelStdoutFormat   DisplayString (SIZE (1..256)),
         kernelStdoutSeverityLevel INTEGER,
         kernelStuckThreadMaxTime INTEGER,
         kernelStuckThreadTimerInterval INTEGER,
         kernelThreadPoolPercentSocketReaders INTEGER,
         kernelInstrumentStackTraceEnabled INTEGER,
         kernelLogRemoteExceptionsEnabled INTEGER,
         kernelNativeIOEnabled INTEGER,
         kernelReverseDNSAllowed INTEGER,
         kernelStdoutDebugEnabled INTEGER,
         kernelStdoutEnabled  INTEGER,
         kernelStdoutLogStack INTEGER
      }
      
   
   kernelIndex OBJECT-TYPE
      SYNTAX      DisplayString (SIZE (1..16))
      MAX-ACCESS  read-only
      STATUS      current
      DESCRIPTION "Unique value directed from ObjectName which is used as table index"
      ::= { kernelEntry 1  }
   
   
   kernelObjectName OBJECT-TYPE
      SYNTAX      DisplayString (SIZE (1..256))
      MAX-ACCESS  read-only
      STATUS      current
      DESCRIPTION "JMX-standard MBean name"
      ::= { kernelEntry 5  }
   
   
   kernelType OBJECT-TYPE
      SYNTAX      DisplayString (SIZE (1..64))
      MAX-ACCESS  read-only
      STATUS      current
      DESCRIPTION "BEA-proprietary MBean type"
      ::= { kernelEntry 10  }
   
   
   kernelName OBJECT-TYPE
      SYNTAX      DisplayString (SIZE (1..64))
      MAX-ACCESS  read-only
      STATUS      current
      DESCRIPTION "BEA-proprietary MBean name"
      ::= { kernelEntry 15  }
   
   
   kernelParent OBJECT-TYPE
      SYNTAX      DisplayString (SIZE (1..256))
      MAX-ACCESS  read-only
      STATUS      current
      DESCRIPTION "BEA-proprietary Parent object's identification, with syntax
      <type>:<name>"
      ::= { kernelEntry 20  }
   
   
   kernelCompleteCOMMessageTimeout OBJECT-TYPE
      SYNTAX      INTEGER
      MAX-ACCESS  read-only
      STATUS      current
      DESCRIPTION "Specify the maximum number of seconds spent
      waiting for a complete COM message to be received.
      This attribute helps guard against denial of
      service attacks in which a caller indicates that
      they will be sending a message of a certain size
      which they never finish sending."
      ::= { kernelEntry 25  }
   
   
   kernelCompleteHTTPMessageTimeout OBJECT-TYPE
      SYNTAX      INTEGER
      MAX-ACCESS  read-only
      STATUS      current
      DESCRIPTION "Specify the maximum number of seconds spent
      * waiting for a complete HTTP message to be received.
      * This attribute helps guard against denial of
      * service attacks in which a caller indicates that
      * they will be sending a message of a certain size
      * which they never finish sending."
      ::= { kernelEntry 30  }
   
   
   kernelCompleteIIOPMessageTimeout OBJECT-TYPE
      SYNTAX      INTEGER
      MAX-ACCESS  read-only
      STATUS      current
      DESCRIPTION "Specify the maximum number of seconds spent
      waiting for a complete HTTP message to be received.
      This attribute helps guard against denial of
      service attacks in which a caller indicates that
      they will be sending a message of a certain size
      which they never finish sending."
      ::= { kernelEntry 35  }
   
   
   kernelCompleteT3MessageTimeout OBJECT-TYPE
      SYNTAX      INTEGER
      MAX-ACCESS  read-only
      STATUS      current
      DESCRIPTION "Specify the maximum number of seconds spent
      waiting for a complete T3 message to be received.
       This attribute helps guard against denial of
       service attacks in which a caller indicates that
       they will be sending a message of a certain size
      which they never finish sending."
      ::= { kernelEntry 40  }
   
   
   kernelDefaultGIOPMinorVersion OBJECT-TYPE
      SYNTAX      INTEGER
      MAX-ACCESS  read-only
      STATUS      current
      DESCRIPTION "Specify the default minor GIOP version for IIOP messages.  This
      attribute is useful for client orbs with broken GIOP 1.2
      implementations."
      ::= { kernelEntry 45  }
   
   
   kernelDefaultProtocol OBJECT-TYPE
      SYNTAX      DisplayString (SIZE (1..256))
      MAX-ACCESS  read-only
      STATUS      current
      DESCRIPTION "Returns the protocol to be used for connections when none is
      specified."
      ::= { kernelEntry 55  }
   
   
   kernelDefaultSecureProtocol OBJECT-TYPE
      SYNTAX      DisplayString (SIZE (1..256))
      MAX-ACCESS  read-only
      STATUS      current
      DESCRIPTION "Returns the protocol to be used for secure connections when none
      is specified."
      ::= { kernelEntry 60  }
   
   
   kernelDGCIdlePeriodsUntilTimeout OBJECT-TYPE
      SYNTAX      INTEGER
      MAX-ACCESS  read-only
      STATUS      current
      DESCRIPTION "Number of idle periods allowed before object is collected."
      ::= { kernelEntry 65  }
   
   
   kernelIdleIIOPConnectionTimeout OBJECT-TYPE
      SYNTAX      INTEGER
      MAX-ACCESS  read-only
      STATUS      current
      DESCRIPTION "Specify the maximum number of seconds an IIOP connection is
      allowed to be idle before it is closed by the server. This
      attribute helps guard against server deadlock through too many
      open connections."
      ::= { kernelEntry 70  }
   
   
   kernelMaxCOMMessageSize OBJECT-TYPE
      SYNTAX      INTEGER
      MAX-ACCESS  read-only
      STATUS      current
      DESCRIPTION "Specify the maximum COM message size allowable in a message header.
      This attribute attempts to prevent a denial of service attack whereby
      a caller attempts to force the server to allocate more memory than
      is available thereby keeping the server from responding quickly to
      other requests."
      ::= { kernelEntry 75  }
   
   
   kernelMaxHTTPMessageSize OBJECT-TYPE
      SYNTAX      INTEGER
      MAX-ACCESS  read-only
      STATUS      current
      DESCRIPTION "Specify the maximum HTTP message size allowable in a message header.
      This attribute attempts to prevent a denial of service attack whereby
      a caller attempts to force the server to allocate more memory than
      is available thereby keeping the server from responding quickly to
      other requests."
      ::= { kernelEntry 85  }
   
   
   kernelMaxIIOPMessageSize OBJECT-TYPE
      SYNTAX      INTEGER
      MAX-ACCESS  read-only
      STATUS      current
      DESCRIPTION "Specify the maximum IIOP message size allowable in a message header.
      This attribute attempts to prevent a denial of service attack whereby
      a caller attempts to force the server to allocate more memory than
      is available thereby keeping the server from responding quickly to
      other requests."
      ::= { kernelEntry 90  }
   
   
   kernelMaxOpenSockCount OBJECT-TYPE
      SYNTAX      INTEGER
      MAX-ACCESS  read-only
      STATUS      current
      DESCRIPTION "Returns the maximum number of open sockets allowed
      in server at a given point of time. When max threshold is reached,
      server stops accepting any more new requests until no of sockets
      drops below threshold."
      ::= { kernelEntry 95  }
   
   
   kernelMaxT3MessageSize OBJECT-TYPE
      SYNTAX      INTEGER
      MAX-ACCESS  read-only
      STATUS      current
      DESCRIPTION "Specify the maximum T3 message size allowable in a message header.
      This attribute attempts to prevent a denial of service attack whereby
      a caller attempts to force the server to allocate more memory than
      is available thereby keeping the server from responding quickly to
      other requests."
      ::= { kernelEntry 100  }
   
   
   kernelStdoutFormat OBJECT-TYPE
      SYNTAX      DisplayString (SIZE (1..256))
      MAX-ACCESS  read-only
      STATUS      current
      DESCRIPTION "The output format to use when logging to the console."
      ::= { kernelEntry 105  }
   
   
   kernelStdoutSeverityLevel OBJECT-TYPE
      SYNTAX      INTEGER
      MAX-ACCESS  read-only
      STATUS      current
      DESCRIPTION "The minimum severity of a message that the server sends to standard out."
      ::= { kernelEntry 110  }
   
   
   kernelStuckThreadMaxTime OBJECT-TYPE
      SYNTAX      INTEGER
      MAX-ACCESS  read-only
      STATUS      current
      DESCRIPTION "Returns the time that is used to determine when a thread might be stuck."
      ::= { kernelEntry 115  }
   
   
   kernelStuckThreadTimerInterval OBJECT-TYPE
      SYNTAX      INTEGER
      MAX-ACCESS  read-only
      STATUS      current
      DESCRIPTION "Returns the time interval that is used to scan the state of the running
      threads.  This along with StuckThreadMaxTime is used to determine when a
      thread might be stuck."
      ::= { kernelEntry 120  }
   
   
   kernelThreadPoolPercentSocketReaders OBJECT-TYPE
      SYNTAX      INTEGER
      MAX-ACCESS  read-only
      STATUS      current
      DESCRIPTION "Returns the percentage (1-99                          ) of execute threads from the default
      queue hat may be used as socket readers."
      ::= { kernelEntry 125  }
   
   
   kernelInstrumentStackTraceEnabled OBJECT-TYPE
      SYNTAX      INTEGER
      MAX-ACCESS  read-only
      STATUS      current
      DESCRIPTION "Determines whether exception messages include the server-side stack trace."
      ::= { kernelEntry 130  }
   
   
   kernelLogRemoteExceptionsEnabled OBJECT-TYPE
      SYNTAX      INTEGER
      MAX-ACCESS  read-only
      STATUS      current
      DESCRIPTION "Determines whether the server message log includes exceptions that are
      raised in remote systems."
      ::= { kernelEntry 135  }
   
   
   kernelNativeIOEnabled OBJECT-TYPE
      SYNTAX      INTEGER
      MAX-ACCESS  read-only
      STATUS      current
      DESCRIPTION "Whether or not native I/O is enabled for the server.."
      ::= { kernelEntry 140  }
   
   
   kernelReverseDNSAllowed OBJECT-TYPE
      SYNTAX      INTEGER
      MAX-ACCESS  read-only
      STATUS      current
      DESCRIPTION "Returns whether or not the kernel is allowed to perform reverse
      DNS lookups."
      ::= { kernelEntry 145  }
   
   
   kernelStdoutDebugEnabled OBJECT-TYPE
      SYNTAX      INTEGER
      MAX-ACCESS  read-only
      STATUS      current
      DESCRIPTION "Determines whether the server sends debug messages to standard out in
      addition to the log file. You must enable <code>Log to Standard Out</code>
      for this property to be relevant."
      ::= { kernelEntry 150  }
   
   
   kernelStdoutEnabled OBJECT-TYPE
      SYNTAX      INTEGER
      MAX-ACCESS  read-only
      STATUS      current
      DESCRIPTION "Enables the server to send messages to standard out in addition to the
      log file."
      ::= { kernelEntry 155  }
   
   
   kernelStdoutLogStack OBJECT-TYPE
      SYNTAX      INTEGER
      MAX-ACCESS  read-only
      STATUS      current
      DESCRIPTION "Whether to dump stack traces to the console when included in logged message."
      ::= { kernelEntry 160  }
   
   
   logTable OBJECT-TYPE
      SYNTAX      SEQUENCE OF LogEntry
      MAX-ACCESS  not-accessible
      STATUS      current
      DESCRIPTION "Generated SNMP Table."
      ::= { wls 700  }
      
   
   logEntry OBJECT-TYPE
      SYNTAX      LogEntry
      MAX-ACCESS  not-accessible
      STATUS      current
      DESCRIPTION "Entry of logTable"
      INDEX { logIndex}
      ::= { logTable 1 }
      
   LogEntry ::=
      SEQUENCE
      {
         logIndex             DisplayString (SIZE (1..16)),
         logObjectName        DisplayString (SIZE (1..256)),
         logType              DisplayString (SIZE (1..64)),
         logName              DisplayString (SIZE (1..64)),
         logParent            DisplayString (SIZE (1..256)),
         logFileName          DisplayString (SIZE (1..256)),
         logRotationType      DisplayString (SIZE (1..16)),
         logNumberOfFilesLimited INTEGER
                     {
                        true(1),
                        false(2)
                     }
         ,
         logFileCount         INTEGER,
         logFileTimeSpan      INTEGER,
         logFileMinSize       INTEGER,
         logRedirectStderrToServerLogEnabled OCTET STRING,
         logLogFileSeverity   OCTET STRING,
         logLoggerSeverity    OCTET STRING,
         logBufferSizeKB      INTEGER,
         logMemoryBufferSeverity OCTET STRING,
         logLog4jLoggingEnabled OCTET STRING,
         logRotationTime      OCTET STRING,
         logStdoutLogStack    OCTET STRING,
         logRotateLogOnStartup OCTET STRING,
         logRedirectStdoutToServerLogEnabled OCTET STRING,
         logMemoryBufferSize  INTEGER,
         logStdoutFormat      OCTET STRING,
         logDomainLogBroadcasterBufferSize INTEGER,
         logDateFormatPattern OCTET STRING,
         logDomainLogBroadcastSeverity OCTET STRING,
         logStdoutSeverity    OCTET STRING,
         logLogFileRotationDir OCTET STRING
      }
      
   
   logIndex OBJECT-TYPE
      SYNTAX      DisplayString (SIZE (1..16))
      MAX-ACCESS  read-only
      STATUS      current
      DESCRIPTION "Unique value directed from ObjectName which is used as table index"
      ::= { logEntry 1  }
   
   
   logObjectName OBJECT-TYPE
      SYNTAX      DisplayString (SIZE (1..256))
      MAX-ACCESS  read-only
      STATUS      current
      DESCRIPTION "JMX-standard MBean name"
      ::= { logEntry 5  }
   
   
   logType OBJECT-TYPE
      SYNTAX      DisplayString (SIZE (1..64))
      MAX-ACCESS  read-only
      STATUS      current
      DESCRIPTION "BEA-proprietary MBean type"
      ::= { logEntry 10  }
   
   
   logName OBJECT-TYPE
      SYNTAX      DisplayString (SIZE (1..64))
      MAX-ACCESS  read-only
      STATUS      current
      DESCRIPTION "BEA-proprietary MBean name"
      ::= { logEntry 15  }
   
   
   logParent OBJECT-TYPE
      SYNTAX      DisplayString (SIZE (1..256))
      MAX-ACCESS  read-only
      STATUS      current
      DESCRIPTION "BEA-proprietary Parent object's identification, with syntax
      <type>:<name>"
      ::= { logEntry 20  }
   
   
   logFileName OBJECT-TYPE
      SYNTAX      DisplayString (SIZE (1..256))
      MAX-ACCESS  read-only
      STATUS      current
      DESCRIPTION "name of the error log file, including the absolute directory path."
      ::= { logEntry 25  }
   
   
   logRotationType OBJECT-TYPE
      SYNTAX      DisplayString (SIZE (1..16))
      MAX-ACCESS  read-only
      STATUS      current
      DESCRIPTION "Return rotation type for this logfile."
      ::= { logEntry 30  }
   
   
   logNumberOfFilesLimited OBJECT-TYPE
      SYNTAX      INTEGER
                  {
                     true(1),
                     false(2)
                  }
      
      MAX-ACCESS  read-only
      STATUS      current
      DESCRIPTION "A boolean value (true Or false)."
      ::= { logEntry 35  }
   
   
   logFileCount OBJECT-TYPE
      SYNTAX      INTEGER
      MAX-ACCESS  read-only
      STATUS      current
      DESCRIPTION "This attribute defines the number of file instances which are kept 
      by the logging system, other than the current logfile."
      ::= { logEntry 40  }
   
   
   logFileTimeSpan OBJECT-TYPE
      SYNTAX      INTEGER
      MAX-ACCESS  read-only
      STATUS      current
      DESCRIPTION "Timespan (in hours) after which logfile should be rotated."
      ::= { logEntry 45  }
   
   
   logFileMinSize OBJECT-TYPE
      SYNTAX      INTEGER
      MAX-ACCESS  read-only
      STATUS      current
      DESCRIPTION "The minimum size (in kilobytes) that the error log file
      must reach before it is rolled over."
      ::= { logEntry 50  }
   
   
   logRedirectStderrToServerLogEnabled OBJECT-TYPE
      SYNTAX      OCTET STRING
      MAX-ACCESS  read-only
      STATUS      current
      DESCRIPTION "When enabled, this redirects the stderr of the JVM in which a WebLogic Server instance runs, to the WebLogic Logging system. The stderr content is published to all the registered log destinations, like the server terminal console and log file."
      ::= { logEntry 51  }
   
   
   logLogFileSeverity OBJECT-TYPE
      SYNTAX      OCTET STRING
      MAX-ACCESS  read-only
      STATUS      current
      DESCRIPTION "The minimum severity of log messages going to the server log file. By default all messages go to the log file."
      ::= { logEntry 52  }
   
   
   logLoggerSeverity OBJECT-TYPE
      SYNTAX      OCTET STRING
      MAX-ACCESS  read-only
      STATUS      current
      DESCRIPTION "The minimum severity of log messages going to all log destinations. By default all messages are published."
      ::= { logEntry 53  }
   
   
   logBufferSizeKB OBJECT-TYPE
      SYNTAX      INTEGER
      MAX-ACCESS  read-only
      STATUS      current
      DESCRIPTION "Gets the underlying log buffer size in kilo bytes"
      ::= { logEntry 54  }
   
   
   logMemoryBufferSeverity OBJECT-TYPE
      SYNTAX      OCTET STRING
      MAX-ACCESS  read-only
      STATUS      current
      DESCRIPTION "The minimum severity of log messages going to the memory buffer of recent log events. Messages with a lower severity than the specified value will not be cached in the buffer."
      ::= { logEntry 55  }
   
   
   logLog4jLoggingEnabled OBJECT-TYPE
      SYNTAX      OCTET STRING
      MAX-ACCESS  read-only
      STATUS      current
      DESCRIPTION "Specifies whether the server logging is based on a Log4j implementation. By default, WebLogic logging uses an implementation based on the Java Logging APIs which are part of the JDK.  Applications that use the WebLogic Message Catalog framework or the NonCatalogLogger will not be affected by the underlying Logging implementation."
      ::= { logEntry 56  }
   
   
   logRotationTime OBJECT-TYPE
      SYNTAX      OCTET STRING
      MAX-ACCESS  read-only
      STATUS      current
      DESCRIPTION "Determines the start time (hour and minute) for a time-based rotation sequence.  At the time that this value specifies, the server renames the current log file. Thereafter, the server renames the log file at an interval that you specify in File Time Span.  If the specified time has already past, then the server starts its file rotation immediately.   Use the following format: k:mm, where k is the hour in a 24-hour format. mm is the minute"
      ::= { logEntry 57  }
   
   
   logStdoutLogStack OBJECT-TYPE
      SYNTAX      OCTET STRING
      MAX-ACCESS  read-only
      STATUS      current
      DESCRIPTION "Specifies whether to dump stack traces to the console when included in logged message."
      ::= { logEntry 58  }
   
   
   logRotateLogOnStartup OBJECT-TYPE
      SYNTAX      OCTET STRING
      MAX-ACCESS  read-only
      STATUS      current
      DESCRIPTION "Specifies whether a server rotates its log file during its startup cycle."
      ::= { logEntry 59  }
   
   
   logRedirectStdoutToServerLogEnabled OBJECT-TYPE
      SYNTAX      OCTET STRING
      MAX-ACCESS  read-only
      STATUS      current
      DESCRIPTION "When enabled, this redirects the stdout of the JVM in which a WebLogic Server instance runs, to the WebLogic logging system. The stdout content is published to all the registered log destinations, like the server terminal console and log file."
      ::= { logEntry 60  }
   
   
   logMemoryBufferSize OBJECT-TYPE
      SYNTAX      INTEGER
      MAX-ACCESS  read-only
      STATUS      current
      DESCRIPTION "The size of the memory buffer that holds the last n log records. This is used to support viewing the most recent log record entries (tail viewing) from the WebLogic Administration Console."
      ::= { logEntry 61  }
   
   
   logStdoutFormat OBJECT-TYPE
      SYNTAX      OCTET STRING
      MAX-ACCESS  read-only
      STATUS      current
      DESCRIPTION "The output format to use when logging to the console."
      ::= { logEntry 62  }
   
   
   logDomainLogBroadcasterBufferSize OBJECT-TYPE
      SYNTAX      INTEGER
      MAX-ACCESS  read-only
      STATUS      current
      DESCRIPTION "Broadcasts log messages to the domain log in batch mode. The size of the buffer for log messages that are sent to the domain log. The buffer is maintained on the Managed Server and gets broadcasted to the domain log when it gets full."
      ::= { logEntry 63  }
   
   
   logDateFormatPattern OBJECT-TYPE
      SYNTAX      OCTET STRING
      MAX-ACCESS  read-only
      STATUS      current
      DESCRIPTION "The date format pattern used for rendering dates in the  log. The DateFormatPattern string conforms to the specification of the java.text.SimpleDateFormat class."
      ::= { logEntry 64  }
   
   
   logDomainLogBroadcastSeverity OBJECT-TYPE
      SYNTAX      OCTET STRING
      MAX-ACCESS  read-only
      STATUS      current
      DESCRIPTION "The minimum severity of log messages going to the domain log from this server's log broadcaster. Messages with a lower severity than the specified value will not be published to the domain log."
      ::= { logEntry 65  }
   
   
   logStdoutSeverity OBJECT-TYPE
      SYNTAX      OCTET STRING
      MAX-ACCESS  read-only
      STATUS      current
      DESCRIPTION "The minimum severity of log messages going to the standard out. Messages with a lower severity than the specified value will not be published to standard out."
      ::= { logEntry 66  }
   
   
   logLogFileRotationDir OBJECT-TYPE
      SYNTAX      OCTET STRING
      MAX-ACCESS  read-only
      STATUS      current
      DESCRIPTION "The directory where the rotated log files will be stored. By default the rotated files are stored in the same directory where the log file is stored."
      ::= { logEntry 67  }
   
   
   networkChannelTable OBJECT-TYPE
      SYNTAX      SEQUENCE OF NetworkChannelEntry
      MAX-ACCESS  not-accessible
      STATUS      current
      DESCRIPTION "This table represents a networkChannel in the domain."
      ::= { wls 703  }
      
   
   networkChannelEntry OBJECT-TYPE
      SYNTAX      NetworkChannelEntry
      MAX-ACCESS  not-accessible
      STATUS      current
      DESCRIPTION "Entry of networkChannelTable"
      INDEX { networkChannelIndex}
      ::= { networkChannelTable 1 }
      
   NetworkChannelEntry ::=
      SEQUENCE
      {
         networkChannelIndex  DisplayString (SIZE (1..16)),
         networkChannelObjectName DisplayString (SIZE (1..256)),
         networkChannelType   DisplayString (SIZE (1..64)),
         networkChannelName   DisplayString (SIZE (1..64)),
         networkChannelParent DisplayString (SIZE (1..256)),
         networkChannelAcceptBacklog INTEGER,
         networkChannelChannelWeight INTEGER,
         networkChannelClusterAddress DisplayString (SIZE (1..256)),
         networkChannelCompleteCOMMessageTimeout INTEGER,
         networkChannelCompleteHTTPMessageTimeout INTEGER,
         networkChannelCompleteT3MessageTimeout INTEGER,
         networkChannelDescription DisplayString (SIZE (1..64)),
         networkChannelListenPort INTEGER,
         networkChannelLoginTimeoutMillis INTEGER,
         networkChannelLoginTimeoutMillisSSL INTEGER,
         networkChannelMaxCOMMessageSize INTEGER,
         networkChannelMaxT3MessageSize INTEGER,
         networkChannelMaxHTTPMessageSize INTEGER,
         networkChannelSSLListenPort INTEGER,
         networkChannelTunnelingClientPingSecs INTEGER,
         networkChannelTunnelingClientTimeoutSecs INTEGER,
         networkChannelBoundOutgoingEnabled INTEGER,
         networkChannelCOMEnabled INTEGER,
         networkChannelHTTPEnabled INTEGER,
         networkChannelHTTPSEnabled INTEGER,
         networkChannelListenPortEnabled INTEGER,
         networkChannelOutgoingEnabled INTEGER,
         networkChannelSSLListenPortEnabled INTEGER,
         networkChannelT3Enabled INTEGER,
         networkChannelT3SEnabled INTEGER,
         networkChannelTunnelingEnabled INTEGER
      }
      
   
   networkChannelIndex OBJECT-TYPE
      SYNTAX      DisplayString (SIZE (1..16))
      MAX-ACCESS  read-only
      STATUS      current
      DESCRIPTION "Unique value directed from ObjectName which is used as table index"
      ::= { networkChannelEntry 1  }
   
   
   networkChannelObjectName OBJECT-TYPE
      SYNTAX      DisplayString (SIZE (1..256))
      MAX-ACCESS  read-only
      STATUS      current
      DESCRIPTION "JMX-standard MBean name"
      ::= { networkChannelEntry 5  }
   
   
   networkChannelType OBJECT-TYPE
      SYNTAX      DisplayString (SIZE (1..64))
      MAX-ACCESS  read-only
      STATUS      current
      DESCRIPTION "BEA-proprietary MBean type"
      ::= { networkChannelEntry 10  }
   
   
   networkChannelName OBJECT-TYPE
      SYNTAX      DisplayString (SIZE (1..64))
      MAX-ACCESS  read-only
      STATUS      current
      DESCRIPTION "BEA-proprietary MBean name"
      ::= { networkChannelEntry 15  }
   
   
   networkChannelParent OBJECT-TYPE
      SYNTAX      DisplayString (SIZE (1..256))
      MAX-ACCESS  read-only
      STATUS      current
      DESCRIPTION "BEA-proprietary Parent object's identification, with syntax
      <type>:<name>"
      ::= { networkChannelEntry 20  }
   
   
   networkChannelAcceptBacklog OBJECT-TYPE
      SYNTAX      INTEGER
      MAX-ACCESS  read-only
      STATUS      current
      DESCRIPTION "Allowed backlog of connection requests on the listen port(s).
      * Individual servers may override this value using a NetworkAccessPointMBean.
      * Setting the backlog to 0 may prevent accepting any incoming connection on
      * some of the OS."
      ::= { networkChannelEntry 25  }
   
   
   networkChannelChannelWeight OBJECT-TYPE
      SYNTAX      INTEGER
      MAX-ACCESS  read-only
      STATUS      current
      DESCRIPTION "A weight to give this channel when creating server-to-server
      * connections."
      ::= { networkChannelEntry 30  }
   
   
   networkChannelClusterAddress OBJECT-TYPE
      SYNTAX      DisplayString (SIZE (1..256))
      MAX-ACCESS  read-only
      STATUS      current
      DESCRIPTION "This channel's cluster address.  If this
      * is not set, the cluster address from the cluster
      * configuration is used in its place."
      ::= { networkChannelEntry 35  }
   
   
   networkChannelCompleteCOMMessageTimeout OBJECT-TYPE
      SYNTAX      INTEGER
      MAX-ACCESS  read-only
      STATUS      current
      DESCRIPTION "The maximum number of seconds spent
      * waiting for a complete COM message to be received.
      * This attribute helps guard against denial of
      * service attacks in which a caller indicates that
      * they will be sending a message of a certain size
      * which they never finish sending."
      ::= { networkChannelEntry 40  }
   
   
   networkChannelCompleteHTTPMessageTimeout OBJECT-TYPE
      SYNTAX      INTEGER
      MAX-ACCESS  read-only
      STATUS      current
      DESCRIPTION "The maximum number of seconds spent
      * waiting for a complete HTTP message to be received.
      * This attribute helps guard against denial of
      * service attacks in which a caller indicates that
      * they will be sending a message of a certain size
      * which they never finish sending."
      ::= { networkChannelEntry 45  }
   
   
   networkChannelCompleteT3MessageTimeout OBJECT-TYPE
      SYNTAX      INTEGER
      MAX-ACCESS  read-only
      STATUS      current
      DESCRIPTION "The maximum number of seconds spent
      * waiting for a complete T3 message to be received.
      * This attribute helps guard against denial of
      * service attacks in which a caller indicates that
      * they will be sending a message of a certain size
      * which they never finish sending.
      * Individual servers may override this value using a NetworkAccessPointMBean."
      ::= { networkChannelEntry 50  }
   
   
   networkChannelDescription OBJECT-TYPE
      SYNTAX      DisplayString (SIZE (1..64))
      MAX-ACCESS  read-only
      STATUS      current
      DESCRIPTION "Optional short description of this channel for console display
      * purposes."
      ::= { networkChannelEntry 55  }
   
   
   networkChannelListenPort OBJECT-TYPE
      SYNTAX      INTEGER
      MAX-ACCESS  read-only
      STATUS      current
      DESCRIPTION "he plaintext (non-SSL) listen port for the channel.  Individual servers
      * may override
      * this value, but may not enable the port if disabled here
      * and may not disable the port if enabled here.
      * Individual servers may override this value using a NetworkAccessPointMBean."
      ::= { networkChannelEntry 60  }
   
   
   networkChannelLoginTimeoutMillis OBJECT-TYPE
      SYNTAX      INTEGER
      MAX-ACCESS  read-only
      STATUS      current
      DESCRIPTION "The login timeout for the server, in milliseconds. This
      * value must be equal to or greater than 0.
      * Individual servers may override this value using a NetworkAccessPointMBean."
      ::= { networkChannelEntry 65  }
   
   
   networkChannelLoginTimeoutMillisSSL OBJECT-TYPE
      SYNTAX      INTEGER
      MAX-ACCESS  read-only
      STATUS      current
      DESCRIPTION "Duration allowed for an SSL login sequence.  If the duration is exceeded, the
      * login is timed out.  0 to disable.
      * Individual servers may override this value using a NetworkAccessPointMBean."
      ::= { networkChannelEntry 70  }
   
   
   networkChannelMaxCOMMessageSize OBJECT-TYPE
      SYNTAX      INTEGER
      MAX-ACCESS  read-only
      STATUS      current
      DESCRIPTION "The maximum COM message size allowable in a message header.
      * This attribute attempts to prevent a denial of service attack whereby
      * a caller attempts to force the server to allocate more memory than
      * is available thereby keeping the server from responding quickly to
      * other requests."
      ::= { networkChannelEntry 75  }
   
   
   networkChannelMaxT3MessageSize OBJECT-TYPE
      SYNTAX      INTEGER
      MAX-ACCESS  read-only
      STATUS      current
      DESCRIPTION "The maximum T3 message size allowable in a message header.
      * This attribute attempts to prevent a denial of service attack whereby
      * a caller attempts to force the server to allocate more memory than
      * is available thereby keeping the server from responding quickly to
      * other requests."
      ::= { networkChannelEntry 80  }
   
   
   networkChannelMaxHTTPMessageSize OBJECT-TYPE
      SYNTAX      INTEGER
      MAX-ACCESS  read-only
      STATUS      current
      DESCRIPTION "The SSL listen port for the channel.  Individual server's may override
      * this value, but may not enable the port if disabled here
      * and may not disable the port if enabled here.   SSL must be configured
      * and enabled for this port to work.
      * Individual servers may override this value using a NetworkAccessPointMBean."
      ::= { networkChannelEntry 85  }
   
   
   networkChannelSSLListenPort OBJECT-TYPE
      SYNTAX      INTEGER
      MAX-ACCESS  read-only
      STATUS      current
      DESCRIPTION "The maximum number of seconds spent
      * waiting for a complete HTTP message to be received.
      * This attribute helps guard against denial of
      * service attacks in which a caller indicates that
      * they will be sending a message of a certain size
      * which they never finish sending."
      ::= { networkChannelEntry 90  }
   
   
   networkChannelTunnelingClientPingSecs OBJECT-TYPE
      SYNTAX      INTEGER
      MAX-ACCESS  read-only
      STATUS      current
      DESCRIPTION "Interval (in seconds) at which to ping an http-tunneled client to see
      * if its still alive.
      * Individual servers may override this value using a NetworkAccessPointMBean."
      ::= { networkChannelEntry 95  }
   
   
   networkChannelTunnelingClientTimeoutSecs OBJECT-TYPE
      SYNTAX      INTEGER
      MAX-ACCESS  read-only
      STATUS      current
      DESCRIPTION "Duration (in seconds) after which a missing http-tunneled client is
      * considered dead.
      * Individual servers may override this value using a NetworkAccessPointMBean."
      ::= { networkChannelEntry 100  }
   
   
   networkChannelBoundOutgoingEnabled OBJECT-TYPE
      SYNTAX      INTEGER
      MAX-ACCESS  read-only
      STATUS      current
      DESCRIPTION "Bind new outgoing server side T3 or T3S connections 
      * to the server channel's listen address.  Other
      * protocols ignore this field.  This field is ignored
      * for connections initiated via URLs, it takes
      * effect if and only if the connection was initiated
      * by accessing a remote reference (such as an EJB
      * or RMI stub.)."
      ::= { networkChannelEntry 105  }
   
   
   networkChannelCOMEnabled OBJECT-TYPE
      SYNTAX      INTEGER
      MAX-ACCESS  read-only
      STATUS      current
      DESCRIPTION "Whether or not plaintext (non-SSL) COM traffic is enabled."
      ::= { networkChannelEntry 110  }
   
   
   networkChannelHTTPEnabled OBJECT-TYPE
      SYNTAX      INTEGER
      MAX-ACCESS  read-only
      STATUS      current
      DESCRIPTION "Whether or not plaintext (non-SSL) HTTP traffic is enabled."
      ::= { networkChannelEntry 115  }
   
   
   networkChannelHTTPSEnabled OBJECT-TYPE
      SYNTAX      INTEGER
      MAX-ACCESS  read-only
      STATUS      current
      DESCRIPTION "Whether or not secure (SSL) HTTP traffic is enabled."
      ::= { networkChannelEntry 120  }
   
   
   networkChannelListenPortEnabled OBJECT-TYPE
      SYNTAX      INTEGER
      MAX-ACCESS  read-only
      STATUS      current
      DESCRIPTION "Whether or not plaintext port is enabled for the channel."
      ::= { networkChannelEntry 125  }
   
   
   networkChannelOutgoingEnabled OBJECT-TYPE
      SYNTAX      INTEGER
      MAX-ACCESS  read-only
      STATUS      current
      DESCRIPTION "Whether or not new server-to-server connections may
      * consider this channel when initiating"
      ::= { networkChannelEntry 130  }
   
   
   networkChannelSSLListenPortEnabled OBJECT-TYPE
      SYNTAX      INTEGER
      MAX-ACCESS  read-only
      STATUS      current
      DESCRIPTION "Whether or not SSL port is enabled for the channel.  SSL must be configured
      * and enabled in addition to this setting for the SSL port to work"
      ::= { networkChannelEntry 135  }
   
   
   networkChannelT3Enabled OBJECT-TYPE
      SYNTAX      INTEGER
      MAX-ACCESS  read-only
      STATUS      current
      DESCRIPTION "Whether or not plaintext (non-SSL) T3 traffic is enabled.
      * Note that it is not possible to disable T3 traffic on the default channel(s)"
      ::= { networkChannelEntry 140  }
   
   
   networkChannelT3SEnabled OBJECT-TYPE
      SYNTAX      INTEGER
      MAX-ACCESS  read-only
      STATUS      current
      DESCRIPTION "Whether or not secure T3 traffic is enabled.
      * Note that it is not possible to disable T3 traffic on the default channel(s)"
      ::= { networkChannelEntry 145  }
   
   
   networkChannelTunnelingEnabled OBJECT-TYPE
      SYNTAX      INTEGER
      MAX-ACCESS  read-only
      STATUS      current
      DESCRIPTION "Enables tunneling via http."
      ::= { networkChannelEntry 150  }
   
   
   networkAccessPointTable OBJECT-TYPE
      SYNTAX      SEQUENCE OF NetworkAccessPointEntry
      MAX-ACCESS  not-accessible
      STATUS      current
      DESCRIPTION "This table represents a networkAccessPoint in the domain."
      ::= { wls 705  }
      
   
   networkAccessPointEntry OBJECT-TYPE
      SYNTAX      NetworkAccessPointEntry
      MAX-ACCESS  not-accessible
      STATUS      current
      DESCRIPTION "Entry of networkAccessPointTable"
      INDEX { networkAccessPointIndex}
      ::= { networkAccessPointTable 1 }
      
   NetworkAccessPointEntry ::=
      SEQUENCE
      {
         networkAccessPointIndex DisplayString (SIZE (1..16)),
         networkAccessPointObjectName DisplayString (SIZE (1..256)),
         networkAccessPointType DisplayString (SIZE (1..64)),
         networkAccessPointName DisplayString (SIZE (1..64)),
         networkAccessPointParent DisplayString (SIZE (1..256)),
         networkAccessPointAcceptBacklog INTEGER,
         networkAccessPointCompleteCOMMessageTimeout INTEGER,
         networkAccessPointCompleteHTTPMessageTimeout INTEGER,
         networkAccessPointCompleteT3MessageTimeout INTEGER,
         networkAccessPointListenAddress DisplayString (SIZE (1..256)),
         networkAccessPointListenPort INTEGER,
         networkAccessPointLoginTimeoutMillisSSL INTEGER,
         networkAccessPointLoginTimeoutMillis INTEGER,
         networkAccessPointSSLListenPort INTEGER,
         networkAccessPointTunnelingClientPingSecs INTEGER,
         networkAccessPointTunnelingClientTimeoutSecs INTEGER,
         networkAccessPointUseFastSerialization OCTET STRING,
         networkAccessPointProxyPort INTEGER,
         networkAccessPointTwoWaySSLEnabled OCTET STRING,
         networkAccessPointChannelWeight INTEGER,
         networkAccessPointHttpEnabledForThisProtocol OCTET STRING,
         networkAccessPointTimeoutConnectionWithPendingResponses OCTET STRING,
         networkAccessPointOutboundEnabled OCTET STRING,
         networkAccessPointEnabled OCTET STRING,
         networkAccessPointCustomPrivateKeyAlias OCTET STRING,
         networkAccessPointConnectTimeout INTEGER,
         networkAccessPointMaxConnectedClients INTEGER,
         networkAccessPointIdleConnectionTimeout INTEGER,
         networkAccessPointMaxBackoffBetweenFailures INTEGER,
         networkAccessPointProtocol OCTET STRING,
         networkAccessPointPrivateKeyAlias OCTET STRING,
         networkAccessPointTunnelingEnabled OCTET STRING,
         networkAccessPointClusterAddress OCTET STRING,
         networkAccessPointChannelIdentityCustomized OCTET STRING,
         networkAccessPointMaxMessageSize INTEGER,
         networkAccessPointPublicPort INTEGER,
         networkAccessPointOutboundPrivateKeyEnabled OCTET STRING,
         networkAccessPointCompleteMessageTimeout INTEGER,
         networkAccessPointPublicAddress OCTET STRING,
         networkAccessPointClientCertificateEnforced OCTET STRING,
         networkAccessPointPrivateKeyPassPhrase OCTET STRING,
         networkAccessPointProxyAddress OCTET STRING
      }
      
   
   networkAccessPointIndex OBJECT-TYPE
      SYNTAX      DisplayString (SIZE (1..16))
      MAX-ACCESS  read-only
      STATUS      current
      DESCRIPTION "Unique value directed from ObjectName which is used as table index"
      ::= { networkAccessPointEntry 1  }
   
   
   networkAccessPointObjectName OBJECT-TYPE
      SYNTAX      DisplayString (SIZE (1..256))
      MAX-ACCESS  read-only
      STATUS      current
      DESCRIPTION "JMX-standard MBean name"
      ::= { networkAccessPointEntry 5  }
   
   
   networkAccessPointType OBJECT-TYPE
      SYNTAX      DisplayString (SIZE (1..64))
      MAX-ACCESS  read-only
      STATUS      current
      DESCRIPTION "BEA-proprietary MBean type"
      ::= { networkAccessPointEntry 10  }
   
   
   networkAccessPointName OBJECT-TYPE
      SYNTAX      DisplayString (SIZE (1..64))
      MAX-ACCESS  read-only
      STATUS      current
      DESCRIPTION "BEA-proprietary MBean name"
      ::= { networkAccessPointEntry 15  }
   
   
   networkAccessPointParent OBJECT-TYPE
      SYNTAX      DisplayString (SIZE (1..256))
      MAX-ACCESS  read-only
      STATUS      current
      DESCRIPTION "BEA-proprietary Parent object's identification, with syntax
      <type>:<name>"
      ::= { networkAccessPointEntry 20  }
   
   
   networkAccessPointAcceptBacklog OBJECT-TYPE
      SYNTAX      INTEGER
      MAX-ACCESS  read-only
      STATUS      current
      DESCRIPTION "Allowed backlog of connection requests on the listen port.
      * -1                         implies that this value is inherited from the channel."
      ::= { networkAccessPointEntry 25  }
   
   
   networkAccessPointCompleteCOMMessageTimeout OBJECT-TYPE
      SYNTAX      INTEGER
      MAX-ACCESS  read-only
      STATUS      current
      DESCRIPTION "The maximum number of seconds spent
      * waiting for a complete COM message to be received.
      * This attribute helps guard against denial of
      * service attacks in which a caller indicates that
      * they will be sending a message of a certain size
      * which they never finish sending.
      * -1                         implies that this value is inherited from the channel."
      ::= { networkAccessPointEntry 30  }
   
   
   networkAccessPointCompleteHTTPMessageTimeout OBJECT-TYPE
      SYNTAX      INTEGER
      MAX-ACCESS  read-only
      STATUS      current
      DESCRIPTION "The maximum number of seconds spent
      * waiting for a complete HTTP message to be received.
      * This attribute helps guard against denial of
      * service attacks in which a caller indicates that
      * they will be sending a message of a certain size
      * which they never finish sending.
      * -1                         implies that this value is inherited from the channel."
      ::= { networkAccessPointEntry 35  }
   
   
   networkAccessPointCompleteT3MessageTimeout OBJECT-TYPE
      SYNTAX      INTEGER
      MAX-ACCESS  read-only
      STATUS      current
      DESCRIPTION "The maximum number of seconds spent
      * waiting for a complete T3 message to be received.
      * This attribute helps guard against denial of
      * service attacks in which a caller indicates that
      * they will be sending a message of a certain size
      * which they never finish sending.
      * -1                         implies that this value is inherited from the channel."
      ::= { networkAccessPointEntry 40  }
   
   
   networkAccessPointListenAddress OBJECT-TYPE
      SYNTAX      DisplayString (SIZE (1..256))
      MAX-ACCESS  read-only
      STATUS      current
      DESCRIPTION "A value of null indicates that this value is inherited from the server."
      ::= { networkAccessPointEntry 45  }
   
   
   networkAccessPointListenPort OBJECT-TYPE
      SYNTAX      INTEGER
      MAX-ACCESS  read-only
      STATUS      current
      DESCRIPTION "The plaintext (non-SSL) listen port for the channel.
      * -1                         implies that this value is inherited from the channel."
      ::= { networkAccessPointEntry 50  }
   
   
   networkAccessPointLoginTimeoutMillisSSL OBJECT-TYPE
      SYNTAX      INTEGER
      MAX-ACCESS  read-only
      STATUS      current
      DESCRIPTION "Duration allowed for an SSL login sequence.  If the duration is exceeded, the
      * login is timed out.  0 to disable.
      * -1                         implies that this value is inherited from the channel."
      ::= { networkAccessPointEntry 55  }
   
   
   networkAccessPointLoginTimeoutMillis OBJECT-TYPE
      SYNTAX      INTEGER
      MAX-ACCESS  read-only
      STATUS      current
      DESCRIPTION "A value of null indicates that this value is inherited from the server."
      ::= { networkAccessPointEntry 60  }
   
   
   networkAccessPointSSLListenPort OBJECT-TYPE
      SYNTAX      INTEGER
      MAX-ACCESS  read-only
      STATUS      current
      DESCRIPTION "The SSL listen port for the channel.
      * -1                         implies that this value is inherited from the channel.."
      ::= { networkAccessPointEntry 65  }
   
   
   networkAccessPointTunnelingClientPingSecs OBJECT-TYPE
      SYNTAX      INTEGER
      MAX-ACCESS  read-only
      STATUS      current
      DESCRIPTION "Interval (in seconds) at which to ping an http-tunneled client to see
      * if its still alive.
      * -1                         implies that this value is inherited from the channel."
      ::= { networkAccessPointEntry 70  }
   
   
   networkAccessPointTunnelingClientTimeoutSecs OBJECT-TYPE
      SYNTAX      INTEGER
      MAX-ACCESS  read-only
      STATUS      current
      DESCRIPTION "Duration (in seconds) after which a missing http-tunneled client is
      * considered dead.
      * -1                         implies that this value is inherited from the channel."
      ::= { networkAccessPointEntry 75  }
   
   
   networkAccessPointUseFastSerialization OBJECT-TYPE
      SYNTAX      OCTET STRING
      MAX-ACCESS  read-only
      STATUS      current
      DESCRIPTION "Specifies whether to use non-standard object serialization for performance. This option works in different ways for different protocols. In particular under IIOP this option uses Java serialization rather than RMI-IIOP serialization. In general using non-standard serialization is not suitable for interop scenarios and may imply some feature loss."
      ::= { networkAccessPointEntry 76  }
   
   
   networkAccessPointProxyPort OBJECT-TYPE
      SYNTAX      INTEGER
      MAX-ACCESS  read-only
      STATUS      current
      DESCRIPTION "The port of the HTTP proxy to use for outbound connections on this channel. The HTTP proxy must support the CONNECT tunneling command.  This option is only effective when OutboundEnabled and ProxyHost are set on the channel."
      ::= { networkAccessPointEntry 77  }
   
   
   networkAccessPointTwoWaySSLEnabled OBJECT-TYPE
      SYNTAX      OCTET STRING
      MAX-ACCESS  read-only
      STATUS      current
      DESCRIPTION "Specifies whether this network channel uses two way SSL."
      ::= { networkAccessPointEntry 78  }
   
   
   networkAccessPointChannelWeight OBJECT-TYPE
      SYNTAX      INTEGER
      MAX-ACCESS  read-only
      STATUS      current
      DESCRIPTION "A weight to give this channel when creating server-to-server connections."
      ::= { networkAccessPointEntry 79  }
   
   
   networkAccessPointHttpEnabledForThisProtocol OBJECT-TYPE
      SYNTAX      OCTET STRING
      MAX-ACCESS  read-only
      STATUS      current
      DESCRIPTION "Specifies whether HTTP traffic should be allowed over this network channel.  HTTP is generally required by binary protocols for downloading stubs and other resources."
      ::= { networkAccessPointEntry 80  }
   
   
   networkAccessPointTimeoutConnectionWithPendingResponses OBJECT-TYPE
      SYNTAX      OCTET STRING
      MAX-ACCESS  read-only
      STATUS      current
      DESCRIPTION "Determines if connections with pending responses are allowed to timeout. It defaults to false. If set to true, the connection will be timed out for this channel if it exceeds the idleConnectionTimeout value.  Note: This setting only applies to IIOP connections."
      ::= { networkAccessPointEntry 81  }
   
   
   networkAccessPointOutboundEnabled OBJECT-TYPE
      SYNTAX      OCTET STRING
      MAX-ACCESS  read-only
      STATUS      current
      DESCRIPTION "Specifies whether new server-to-server connections may consider this network channel when initiating a connection. This is only relevant if the connection needs to be bound to the network channel's listen address. This will only work for binary protocols that support both outbound and inbound traffic.  When this feature is not enabled, connections are initiated using a local address selected by the underlying hardware.  The default is true for all admin channels and false otherwise.  Outbound channels are selected at runtime either by virtue of the fact of being the only outbound-enabled channel for the required protocol, or by name in weblogic.jndi.Environment#setProviderChannel."
      ::= { networkAccessPointEntry 82  }
   
   
   networkAccessPointEnabled OBJECT-TYPE
      SYNTAX      OCTET STRING
      MAX-ACCESS  read-only
      STATUS      current
      DESCRIPTION "Specifies whether this channel should be started."
      ::= { networkAccessPointEntry 83  }
   
   
   networkAccessPointCustomPrivateKeyAlias OBJECT-TYPE
      SYNTAX      OCTET STRING
      MAX-ACCESS  read-only
      STATUS      current
      DESCRIPTION "The string alias used to store and retrieve the channel's private key in the keystore. This private key is associated with the server's digital certificate. A value of null indicates that the network channel uses the alias specified in the server's SSL configuration."
      ::= { networkAccessPointEntry 84  }
   
   
   networkAccessPointConnectTimeout OBJECT-TYPE
      SYNTAX      INTEGER
      MAX-ACCESS  read-only
      STATUS      current
      DESCRIPTION "The amount of time that this network channel should wait to establish an outbound socket connection before timing out. A value of 0 disables network channel connect timeout."
      ::= { networkAccessPointEntry 85  }
   
   
   networkAccessPointMaxConnectedClients OBJECT-TYPE
      SYNTAX      INTEGER
      MAX-ACCESS  read-only
      STATUS      current
      DESCRIPTION "The maximum number of clients that can be connected on this network channel."
      ::= { networkAccessPointEntry 86  }
   
   
   networkAccessPointIdleConnectionTimeout OBJECT-TYPE
      SYNTAX      INTEGER
      MAX-ACCESS  read-only
      STATUS      current
      DESCRIPTION "The maximum amount of time (in seconds) that a connection is allowed to be idle before it is closed by this network channel. A value of -1 indicates that the network channel obtains this timeout value from the ServerMBean.  This timeout helps guard against server deadlock through too many open connections."
      ::= { networkAccessPointEntry 87  }
   
   
   networkAccessPointMaxBackoffBetweenFailures OBJECT-TYPE
      SYNTAX      INTEGER
      MAX-ACCESS  read-only
      STATUS      current
      DESCRIPTION "The maximum back off time between failures while accepting client connections. -1 implies that this value is inherited from the server."
      ::= { networkAccessPointEntry 88  }
   
   
   networkAccessPointProtocol OBJECT-TYPE
      SYNTAX      OCTET STRING
      MAX-ACCESS  read-only
      STATUS      current
      DESCRIPTION "The protocol this network channel should use for connections."
      ::= { networkAccessPointEntry 89  }
   
   
   networkAccessPointPrivateKeyAlias OBJECT-TYPE
      SYNTAX      OCTET STRING
      MAX-ACCESS  read-only
      STATUS      current
      DESCRIPTION "The string alias used to store and retrieve the channel's private key in the keystore. This private key is associated with the server's digital certificate. This value is derived from other settings on the channel and cannot be physically set."
      ::= { networkAccessPointEntry 90  }
   
   
   networkAccessPointTunnelingEnabled OBJECT-TYPE
      SYNTAX      OCTET STRING
      MAX-ACCESS  read-only
      STATUS      current
      DESCRIPTION "Specifies whether tunneling via HTTP should be enabled for this network channel. This value is not inherited from the server's configuration."
      ::= { networkAccessPointEntry 91  }
   
   
   networkAccessPointClusterAddress OBJECT-TYPE
      SYNTAX      OCTET STRING
      MAX-ACCESS  read-only
      STATUS      current
      DESCRIPTION "The address this network channel uses to generate EJB handles and failover addresses for use in a cluster. This value is determined according to the following order of precedence:  If the cluster address is specified via the the NAPMBean, then that value is used If this value is not specified, the value of PublicAddress is used. If PublicAddress is not set, this value is derive from the ClusterAddress attribute of the ClusterMbean. If ClusterMbean.clusterAddress is not set, this value is derive from the listen address of the NAPMbean."
      ::= { networkAccessPointEntry 92  }
   
   
   networkAccessPointChannelIdentityCustomized OBJECT-TYPE
      SYNTAX      OCTET STRING
      MAX-ACCESS  read-only
      STATUS      current
      DESCRIPTION "Whether or not the channel's custom identity should be used. This setting only has an effect if the server is using a customized keystore. By default the channel's identity is inherited from the server's identity."
      ::= { networkAccessPointEntry 93  }
   
   
   networkAccessPointMaxMessageSize OBJECT-TYPE
      SYNTAX      INTEGER
      MAX-ACCESS  read-only
      STATUS      current
      DESCRIPTION "The maximum message size allowable in a message header.  This maximum attempts to prevent a denial of service attack whereby a caller attempts to force the server to allocate more memory than is available thereby keeping the server from responding quickly to other requests."
      ::= { networkAccessPointEntry 94  }
   
   
   networkAccessPointPublicPort OBJECT-TYPE
      SYNTAX      INTEGER
      MAX-ACCESS  read-only
      STATUS      current
      DESCRIPTION "The externally published listen port for this network channel. A value of -1 indicates that the network channel's Listen Port is also its public listen port. If the Listen Port is -1,the network channel obtains its public listen port from the server's configuration."
      ::= { networkAccessPointEntry 95  }
   
   
   networkAccessPointOutboundPrivateKeyEnabled OBJECT-TYPE
      SYNTAX      OCTET STRING
      MAX-ACCESS  read-only
      STATUS      current
      DESCRIPTION "Specifies whether the identity specifed by {@link #getCustomPrivateKeyAlias} should be used for outbound SSL connections on this channel. In normal circumstances the outbound identity is determined by the caller's environment."
      ::= { networkAccessPointEntry 96  }
   
   
   networkAccessPointCompleteMessageTimeout OBJECT-TYPE
      SYNTAX      INTEGER
      MAX-ACCESS  read-only
      STATUS      current
      DESCRIPTION "The maximum amount of time this network channel waits for a complete message to be received. A value of 0 disables network channel complete message timeout. A value of -1 indicates that the network channel obtains this timeout value from the ServerMBean.  This timeout helps guard against denial of service attacks in which a caller indicates that they will be sending a message of a certain size which they never finish sending."
      ::= { networkAccessPointEntry 97  }
   
   
   networkAccessPointPublicAddress OBJECT-TYPE
      SYNTAX      OCTET STRING
      MAX-ACCESS  read-only
      STATUS      current
      DESCRIPTION "The IP address or DNS name representing the external identity of this network channel. A value of null indicates that the network channel's Listen Address is also its external address. If the Listen Address is null,the network channel obtains its external identity from the server's configuration.  This is required for the configurations which need to cross a firewall doing Network Address Translation."
      ::= { networkAccessPointEntry 98  }
   
   
   networkAccessPointClientCertificateEnforced OBJECT-TYPE
      SYNTAX      OCTET STRING
      MAX-ACCESS  read-only
      STATUS      current
      DESCRIPTION "Specifies whether clients must present digital certificates from a trusted certificate authority to WebLogic Server on this channel."
      ::= { networkAccessPointEntry 99  }
   
   
   networkAccessPointPrivateKeyPassPhrase OBJECT-TYPE
      SYNTAX      OCTET STRING
      MAX-ACCESS  read-only
      STATUS      current
      DESCRIPTION "The passphrase used to retrieve the server's private key from the keystore. This passphrase is assigned to the private key when it is generated. This value is derived from other settings on the channel and cannot be physically set."
      ::= { networkAccessPointEntry 100  }
   
   
   networkAccessPointProxyAddress OBJECT-TYPE
      SYNTAX      OCTET STRING
      MAX-ACCESS  read-only
      STATUS      current
      DESCRIPTION "The IP address or DNS name of the HTTP proxy to use for outbound connections on this channel. The HTTP proxy must support the CONNECT tunneling command.  This option is only effective when OutboundEnabled is set on the channel."
      ::= { networkAccessPointEntry 101  }
   
   
   nodeManagerTable OBJECT-TYPE
      SYNTAX      SEQUENCE OF NodeManagerEntry
      MAX-ACCESS  not-accessible
      STATUS      current
      DESCRIPTION "This table represents a nodeManager in the domain."
      ::= { wls 707  }
      
   
   nodeManagerEntry OBJECT-TYPE
      SYNTAX      NodeManagerEntry
      MAX-ACCESS  not-accessible
      STATUS      current
      DESCRIPTION "Entry of nodeManagerTable"
      INDEX { nodeManagerIndex}
      ::= { nodeManagerTable 1 }
      
   NodeManagerEntry ::=
      SEQUENCE
      {
         nodeManagerIndex     DisplayString (SIZE (1..16)),
         nodeManagerObjectName DisplayString (SIZE (1..256)),
         nodeManagerType      DisplayString (SIZE (1..64)),
         nodeManagerName      DisplayString (SIZE (1..64)),
         nodeManagerParent    DisplayString (SIZE (1..256)),
         nodeManagerListenAddress DisplayString (SIZE (1..256)),
         nodeManagerListenPort INTEGER,
         nodeManagerShellCommand OCTET STRING,
         nodeManagerNodeManagerHome OCTET STRING,
         nodeManagerDebugEnabled OCTET STRING,
         nodeManagerNMType    OCTET STRING
      }
      
   
   nodeManagerIndex OBJECT-TYPE
      SYNTAX      DisplayString (SIZE (1..16))
      MAX-ACCESS  read-only
      STATUS      current
      DESCRIPTION "Unique value directed from ObjectName which is used as table index"
      ::= { nodeManagerEntry 1  }
   
   
   nodeManagerObjectName OBJECT-TYPE
      SYNTAX      DisplayString (SIZE (1..256))
      MAX-ACCESS  read-only
      STATUS      current
      DESCRIPTION "JMX-standard MBean name"
      ::= { nodeManagerEntry 5  }
   
   
   nodeManagerType OBJECT-TYPE
      SYNTAX      DisplayString (SIZE (1..64))
      MAX-ACCESS  read-only
      STATUS      current
      DESCRIPTION "BEA-proprietary MBean type"
      ::= { nodeManagerEntry 10  }
   
   
   nodeManagerName OBJECT-TYPE
      SYNTAX      DisplayString (SIZE (1..64))
      MAX-ACCESS  read-only
      STATUS      current
      DESCRIPTION "BEA-proprietary MBean name"
      ::= { nodeManagerEntry 15  }
   
   
   nodeManagerParent OBJECT-TYPE
      SYNTAX      DisplayString (SIZE (1..256))
      MAX-ACCESS  read-only
      STATUS      current
      DESCRIPTION "BEA-proprietary Parent object's identification, with syntax
      <type>:<name>"
      ::= { nodeManagerEntry 20  }
   
   
   nodeManagerListenAddress OBJECT-TYPE
      SYNTAX      DisplayString (SIZE (1..256))
      MAX-ACCESS  read-only
      STATUS      current
      DESCRIPTION "The address on which NodeManager listens for connections."
      ::= { nodeManagerEntry 35  }
   
   
   nodeManagerListenPort OBJECT-TYPE
      SYNTAX      INTEGER
      MAX-ACCESS  read-only
      STATUS      current
      DESCRIPTION "The port on which NodeManager listens for connections."
      ::= { nodeManagerEntry 40  }
   
   
   nodeManagerShellCommand OBJECT-TYPE
      SYNTAX      OCTET STRING
      MAX-ACCESS  read-only
      STATUS      current
      DESCRIPTION "Returns the local command line to use when invoking SSH or RSH node manager functions."
      ::= { nodeManagerEntry 41  }
   
   
   nodeManagerNodeManagerHome OBJECT-TYPE
      SYNTAX      OCTET STRING
      MAX-ACCESS  read-only
      STATUS      current
      DESCRIPTION "Returns the nodemanager home directory that will be used to substitute for the shell command template"
      ::= { nodeManagerEntry 42  }
   
   
   nodeManagerDebugEnabled OBJECT-TYPE
      SYNTAX      OCTET STRING
      MAX-ACCESS  read-only
      STATUS      current
      DESCRIPTION "Specifies whether communication with this Node Manager needs to be debugged. When enabled, Node Manager provides more information about request processing. This information is sent to the log of the server making requests to Node Manager."
      ::= { nodeManagerEntry 43  }
   
   
   nodeManagerNMType OBJECT-TYPE
      SYNTAX      OCTET STRING
      MAX-ACCESS  read-only
      STATUS      current
      DESCRIPTION "Returns the node manager type."
      ::= { nodeManagerEntry 44  }
   
   
   rmcFactoryTable OBJECT-TYPE
      SYNTAX      SEQUENCE OF RmcFactoryEntry
      MAX-ACCESS  not-accessible
      STATUS      current
      DESCRIPTION "This table represents a rmcFactory in the domain."
      ::= { wls 708  }
      
   
   rmcFactoryEntry OBJECT-TYPE
      SYNTAX      RmcFactoryEntry
      MAX-ACCESS  not-accessible
      STATUS      current
      DESCRIPTION "Entry of rmcFactoryTable"
      INDEX { rmcFactoryIndex}
      ::= { rmcFactoryTable 1 }
      
   RmcFactoryEntry ::=
      SEQUENCE
      {
         rmcFactoryIndex      DisplayString (SIZE (1..16)),
         rmcFactoryObjectName DisplayString (SIZE (1..256)),
         rmcFactoryType       DisplayString (SIZE (1..64)),
         rmcFactoryName       DisplayString (SIZE (1..64)),
         rmcFactoryParent     DisplayString (SIZE (1..256)),
         rmcFactoryJNDIName   DisplayString
      }
      
   
   rmcFactoryIndex OBJECT-TYPE
      SYNTAX      DisplayString (SIZE (1..16))
      MAX-ACCESS  read-only
      STATUS      current
      DESCRIPTION "Unique value directed from ObjectName which is used as table index"
      ::= { rmcFactoryEntry 1  }
   
   
   rmcFactoryObjectName OBJECT-TYPE
      SYNTAX      DisplayString (SIZE (1..256))
      MAX-ACCESS  read-only
      STATUS      current
      DESCRIPTION "JMX-standard MBean name"
      ::= { rmcFactoryEntry 5  }
   
   
   rmcFactoryType OBJECT-TYPE
      SYNTAX      DisplayString (SIZE (1..64))
      MAX-ACCESS  read-only
      STATUS      current
      DESCRIPTION "BEA-proprietary MBean type"
      ::= { rmcFactoryEntry 10  }
   
   
   rmcFactoryName OBJECT-TYPE
      SYNTAX      DisplayString (SIZE (1..64))
      MAX-ACCESS  read-only
      STATUS      current
      DESCRIPTION "BEA-proprietary MBean name"
      ::= { rmcFactoryEntry 15  }
   
   
   rmcFactoryParent OBJECT-TYPE
      SYNTAX      DisplayString (SIZE (1..256))
      MAX-ACCESS  read-only
      STATUS      current
      DESCRIPTION "BEA-proprietary Parent object's identification, with syntax
      <type>:<name>"
      ::= { rmcFactoryEntry 20  }
   
   
   rmcFactoryJNDIName OBJECT-TYPE
      SYNTAX      DisplayString
      MAX-ACCESS  read-only
      STATUS      current
      DESCRIPTION "Generated Object."
      ::= { rmcFactoryEntry 21  }
   
   
   securityTable OBJECT-TYPE
      SYNTAX      SEQUENCE OF SecurityEntry
      MAX-ACCESS  not-accessible
      STATUS      current
      DESCRIPTION "This table represents a security in the domain."
      ::= { wls 710  }
      
   
   securityEntry OBJECT-TYPE
      SYNTAX      SecurityEntry
      MAX-ACCESS  not-accessible
      STATUS      current
      DESCRIPTION "Entry of securityTable"
      INDEX { securityIndex}
      ::= { securityTable 1 }
      
   SecurityEntry ::=
      SEQUENCE
      {
         securityIndex        DisplayString (SIZE (1..16)),
         securityObjectName   DisplayString (SIZE (1..256)),
         securityType         DisplayString (SIZE (1..64)),
         securityName         DisplayString (SIZE (1..64)),
         securityParent       DisplayString (SIZE (1..256)),
         securityConnectionFilter DisplayString (SIZE (1..256)),
         securityConnectionFilterRules DisplayString (SIZE (1..256)),
         securityConnectionLoggerEnabled DisplayString (SIZE (1..256))
      }
      
   
   securityIndex OBJECT-TYPE
      SYNTAX      DisplayString (SIZE (1..16))
      MAX-ACCESS  read-only
      STATUS      current
      DESCRIPTION "Unique value directed from ObjectName which is used as table index"
      ::= { securityEntry 1  }
   
   
   securityObjectName OBJECT-TYPE
      SYNTAX      DisplayString (SIZE (1..256))
      MAX-ACCESS  read-only
      STATUS      current
      DESCRIPTION "JMX-standard MBean name"
      ::= { securityEntry 5  }
   
   
   securityType OBJECT-TYPE
      SYNTAX      DisplayString (SIZE (1..64))
      MAX-ACCESS  read-only
      STATUS      current
      DESCRIPTION "BEA-proprietary MBean type"
      ::= { securityEntry 10  }
   
   
   securityName OBJECT-TYPE
      SYNTAX      DisplayString (SIZE (1..64))
      MAX-ACCESS  read-only
      STATUS      current
      DESCRIPTION "BEA-proprietary MBean name"
      ::= { securityEntry 15  }
   
   
   securityParent OBJECT-TYPE
      SYNTAX      DisplayString (SIZE (1..256))
      MAX-ACCESS  read-only
      STATUS      current
      DESCRIPTION "BEA-proprietary Parent object's identification, with syntax
      <type>:<name>"
      ::= { securityEntry 20  }
   
   
   securityConnectionFilter OBJECT-TYPE
      SYNTAX      DisplayString (SIZE (1..256))
      MAX-ACCESS  read-only
      STATUS      current
      DESCRIPTION "The name of the Java class that implements a connection filter.
      * The connection filter must be an implementation of the 
      * <tt>weblogic.security.net.ConnectionFilter</tt> interface."
      ::= { securityEntry 30  }
   
   
   securityConnectionFilterRules OBJECT-TYPE
      SYNTAX      DisplayString (SIZE (1..256))
      MAX-ACCESS  read-only
      STATUS      current
      DESCRIPTION "The list of rules for the system connection filter.
      * If none are specified, all connections are accepted."
      ::= { securityEntry 35  }
   
   
   securityConnectionLoggerEnabled OBJECT-TYPE
      SYNTAX      DisplayString (SIZE (1..256))
      MAX-ACCESS  read-only
      STATUS      current
      DESCRIPTION "Enables the logging of accepted connections.  This attribute can be used by
      * a system administrator to dynamically check the incoming connections in the
      * log file to determine if filtering needs to be performed."
      ::= { securityEntry 40  }
   
   
   serverTable OBJECT-TYPE
      SYNTAX      SEQUENCE OF ServerEntry
      MAX-ACCESS  not-accessible
      STATUS      current
      DESCRIPTION "This table represents a WebLogic Server. A WebLogic Server is a
      Java process that is a container for J2EE applications."
      ::= { wls 730  }
      
   
   serverEntry OBJECT-TYPE
      SYNTAX      ServerEntry
      MAX-ACCESS  not-accessible
      STATUS      current
      DESCRIPTION "Entry of serverTable"
      INDEX { serverIndex}
      ::= { serverTable 1 }
      
   ServerEntry ::=
      SEQUENCE
      {
         serverIndex          DisplayString (SIZE (1..16)),
         serverObjectName     DisplayString (SIZE (1..256)),
         serverType           DisplayString (SIZE (1..64)),
         serverName           DisplayString (SIZE (1..64)),
         serverParent         DisplayString (SIZE (1..256)),
         serverReverseDNSAllowed INTEGER
                     {
                        true(1),
                        false(2)
                     }
         ,
         serverDefaultProtocol DisplayString (SIZE (1..32)),
         serverDefaultSecureProtocol DisplayString (SIZE (1..32)),
         serverThreadPoolSize INTEGER,
         serverNativeIOEnabled INTEGER
                     {
                        true(1),
                        false(2)
                     }
         ,
         serverThreadPoolPercentSocketReaders INTEGER,
         serverMaxT3MessageSize INTEGER,
         serverMaxHTTPMessageSize INTEGER,
         serverMaxIIOPMessageSize INTEGER,
         serverCompleteT3MessageTimeout INTEGER,
         serverCompleteHTTPMessageTimeout INTEGER,
         serverCompleteIIOPMessageTimeout INTEGER,
         serverStdoutEnabled  INTEGER
                     {
                        true(1),
                        false(2)
                     }
         ,
         serverStdoutSeverityLevel INTEGER,
         serverLogRemoteExceptionsEnabled INTEGER
                     {
                        true(1),
                        false(2)
                     }
         ,
         serverInstrumentStackTraceEnabled INTEGER
                     {
                        true(1),
                        false(2)
                     }
         ,
         serverRootDirectory  DisplayString (SIZE (1..256)),
         serverMachine        DisplayString (SIZE (1..256)),
         serverListenPort     INTEGER,
         serverLoginTimeout   INTEGER,
         serverCluster        DisplayString (SIZE (1..256)),
         serverClusterWeight  INTEGER,
         serverReplicationGroup DisplayString (SIZE (1..64)),
         serverPreferredSecondaryGroup DisplayString (SIZE (1..64)),
         serverWebServer      DisplayString (SIZE (1..256)),
         serverExpectedToRun  INTEGER
                     {
                        true(1),
                        false(2)
                     }
         ,
         serverJDBCLoggingEnabled INTEGER
                     {
                        true(1),
                        false(2)
                     }
         ,
         serverJDBCLogFileName DisplayString (SIZE (1..256)),
         serverIIOPEnabled    INTEGER
                     {
                        true(1),
                        false(2)
                     }
         ,
         serverDefaultIIOPUser DisplayString (SIZE (1..64)),
         serverHttpdEnabled   INTEGER
                     {
                        true(1),
                        false(2)
                     }
         ,
         serverConsoleInputEnabled INTEGER
                     {
                        true(1),
                        false(2)
                     }
         ,
         serverListenThreadStartDelaySecs INTEGER,
         serverListenAddress  DisplayString (SIZE (1..256)),
         serverLoginTimeoutMillis INTEGER,
         serverAdministrationPort INTEGER,
         serverJavaCompiler   DisplayString (SIZE (1..32)),
         serverJavaCompilerPreClassPath DisplayString (SIZE (1..256)),
         serverJavaCompilerPostClassPath DisplayString (SIZE (1..256)),
         serverExtraRmicOptions DisplayString (SIZE (1..256)),
         serverTransactionLogFilePrefix DisplayString (SIZE (1..32)),
         serverEnabledForDomainLog INTEGER
                     {
                        true(1),
                        false(2)
                     }
         ,
         serverTunnelingEnabled INTEGER
                     {
                        true(1),
                        false(2)
                     }
         ,
         serverTunnelingClientTimeoutSecs INTEGER,
         serverTunnelingClientPingSecs INTEGER,
         serverJMSDefaultConnectionFactoriesEnabled INTEGER
                     {
                        true(1),
                        false(2)
                     }
         ,
         serverDomainLogFilter DisplayString (SIZE (1..256)),
         serverAcceptBacklog  INTEGER,
         serverListenPortEnabled OCTET STRING,
         serverUse81StyleExecuteQueues OCTET STRING,
         serverStagingMode    OCTET STRING,
         serverLowMemoryGCThreshold INTEGER,
         serverStagingDirectoryName OCTET STRING,
         serverGracefulShutdownTimeout INTEGER,
         serverManagedServerIndependenceEnabled OCTET STRING,
         serverStartupTimeout INTEGER,
         serverSocketBufferSizeAsChunkSize OCTET STRING,
         serverRestartMax     INTEGER,
         serverCompleteMessageTimeout INTEGER,
         serverServerLifeCycleTimeoutVal INTEGER,
         serverVerboseEJBDeploymentEnabled OCTET STRING,
         serverAdminReconnectIntervalSeconds INTEGER,
         serverClientCertProxyEnabled OCTET STRING,
         serverRestartDelaySeconds INTEGER,
         serverLowMemoryGranularityLevel INTEGER,
         serverSocketReaders  INTEGER,
         serverOutboundEnabled OCTET STRING,
         serverJDBCLLRTableName OCTET STRING,
         serverInterfaceAddress OCTET STRING,
         serverExtraEjbcOptions OCTET STRING,
         serverCOMEnabled     OCTET STRING,
         serverMessageIdPrefixEnabled OCTET STRING,
         serverAutoRestart    OCTET STRING,
         serverIgnoreSessionsDuringShutdown OCTET STRING,
         serverDefaultTGIOPUser OCTET STRING,
         serverMaxOpenSockCount INTEGER,
         serverLowMemorySampleSize INTEGER,
         serverAutoKillIfFailed OCTET STRING,
         serverCustomIdentityKeyStoreFileName OCTET STRING,
         serverTGIOPEnabled   OCTET STRING,
         serverHealthCheckStartDelaySeconds INTEGER,
         serverUploadDirectoryName OCTET STRING,
         serverWeblogicPluginEnabled OCTET STRING,
         serverJDBCLoginTimeoutSeconds INTEGER,
         serverClasspathServletDisabled OCTET STRING,
         serverIdleConnectionTimeout INTEGER,
         serverDefaultInternalServletsDisabled OCTET STRING,
         serverMaxMessageSize INTEGER,
         serverCustomTrustKeyStoreType OCTET STRING,
         serverListenersBindEarly OCTET STRING,
         serverLowMemoryTimeInterval INTEGER,
         serverTransactionLogFileWritePolicy OCTET STRING,
         serverHttpTraceSupportEnabled OCTET STRING,
         serverKeyStores      OCTET STRING,
         serverAutoMigrationEnabled OCTET STRING,
         serverPeriodLength   INTEGER,
         serverStuckThreadTimerInterval INTEGER,
         serverDGCIdlePeriodsUntilTimeout INTEGER,
         serverMuxerClass     OCTET STRING,
         serverHealthCheckIntervalSeconds INTEGER,
         serverRestartIntervalSeconds INTEGER,
         serverIdlePeriodsUntilTimeout INTEGER,
         serverCustomTrustKeyStoreFileName OCTET STRING,
         serverHostsMigratableServices OCTET STRING,
         serverExternalDNSName OCTET STRING,
         serverOutboundPrivateKeyEnabled OCTET STRING,
         serverAdministrationProtocol OCTET STRING,
         serverCustomIdentityKeyStoreType OCTET STRING,
         serverStartupMode    OCTET STRING,
         serverNMSocketCreateTimeoutInMillis INTEGER
      }
      
   
   serverIndex OBJECT-TYPE
      SYNTAX      DisplayString (SIZE (1..16))
      MAX-ACCESS  read-only
      STATUS      current
      DESCRIPTION "Unique value directed from ObjectName which is used as table index"
      ::= { serverEntry 1  }
   
   
   serverObjectName OBJECT-TYPE
      SYNTAX      DisplayString (SIZE (1..256))
      MAX-ACCESS  read-only
      STATUS      current
      DESCRIPTION "JMX-standard MBean name"
      ::= { serverEntry 5  }
   
   
   serverType OBJECT-TYPE
      SYNTAX      DisplayString (SIZE (1..64))
      MAX-ACCESS  read-only
      STATUS      current
      DESCRIPTION "BEA-proprietary MBean type"
      ::= { serverEntry 10  }
   
   
   serverName OBJECT-TYPE
      SYNTAX      DisplayString (SIZE (1..64))
      MAX-ACCESS  read-only
      STATUS      current
      DESCRIPTION "BEA-proprietary MBean name"
      ::= { serverEntry 15  }
   
   
   serverParent OBJECT-TYPE
      SYNTAX      DisplayString (SIZE (1..256))
      MAX-ACCESS  read-only
      STATUS      current
      DESCRIPTION "BEA-proprietary Parent object's identification, with syntax
      <type>:<name>"
      ::= { serverEntry 20  }
   
   
   serverReverseDNSAllowed OBJECT-TYPE
      SYNTAX      INTEGER
                  {
                     true(1),
                     false(2)
                  }
      
      MAX-ACCESS  read-only
      STATUS      current
      DESCRIPTION "boolean value (true Or false). Returns whether or not the kernel is allowed to perform reverse
      DNS lookups."
      ::= { serverEntry 30  }
   
   
   serverDefaultProtocol OBJECT-TYPE
      SYNTAX      DisplayString (SIZE (1..32))
      MAX-ACCESS  read-only
      STATUS      current
      DESCRIPTION "The protocol to be used for connections when none is
      specified."
      ::= { serverEntry 35  }
   
   
   serverDefaultSecureProtocol OBJECT-TYPE
      SYNTAX      DisplayString (SIZE (1..32))
      MAX-ACCESS  read-only
      STATUS      current
      DESCRIPTION "The protocol to be used for secure connections when none
      is specified."
      ::= { serverEntry 40  }
   
   
   serverThreadPoolSize OBJECT-TYPE
      SYNTAX      INTEGER
      MAX-ACCESS  read-only
      STATUS      current
      DESCRIPTION "The size of the execute thread pool."
      ::= { serverEntry 45  }
   
   
   serverNativeIOEnabled OBJECT-TYPE
      SYNTAX      INTEGER
                  {
                     true(1),
                     false(2)
                  }
      
      MAX-ACCESS  read-only
      STATUS      current
      DESCRIPTION "boolean value (true Or false). Whether or not native I/O is enabled for the server."
      ::= { serverEntry 50  }
   
   
   serverThreadPoolPercentSocketReaders OBJECT-TYPE
      SYNTAX      INTEGER
      MAX-ACCESS  read-only
      STATUS      current
      DESCRIPTION "The percentage (1-99                               ) of execute threads that may be used
      as socket readers."
      ::= { serverEntry 55  }
   
   
   serverMaxT3MessageSize OBJECT-TYPE
      SYNTAX      INTEGER
      MAX-ACCESS  read-only
      STATUS      current
      DESCRIPTION "Specify the maximum T3 message size allowable in a message header.
      This attribute attempts to prevent a denial of service attack whereby
      a caller attempts to force the server to allocate more memory than
      is available thereby keeping the server from responding quickly to
      other requests."
      ::= { serverEntry 60  }
   
   
   serverMaxHTTPMessageSize OBJECT-TYPE
      SYNTAX      INTEGER
      MAX-ACCESS  read-only
      STATUS      current
      DESCRIPTION "Specify the maximum HTTP message size allowable in a message header.
      This attribute attempts to prevent a denial of service attack whereby
      a caller attempts to force the server to allocate more memory than
      is available thereby keeping the server from responding quickly to
      other requests."
      ::= { serverEntry 65  }
   
   
   serverMaxIIOPMessageSize OBJECT-TYPE
      SYNTAX      INTEGER
      MAX-ACCESS  read-only
      STATUS      current
      DESCRIPTION "Specify the maximum IIOP message size allowable in a message header.
      This attribute attempts to prevent a denial of service attack whereby
      a caller attempts to force the server to allocate more memory than
      is available thereby keeping the server from responding quickly to
      other requests."
      ::= { serverEntry 70  }
   
   
   serverCompleteT3MessageTimeout OBJECT-TYPE
      SYNTAX      INTEGER
      MAX-ACCESS  read-only
      STATUS      current
      DESCRIPTION "Specify the maximum number of seconds spent
      waiting for a complete T3 message to be received.
      This attribute helps guard against denial of
      service attacks in which a caller indicates that
      they will be sending a message of a certain size
      which they never finish sending."
      ::= { serverEntry 75  }
   
   
   serverCompleteHTTPMessageTimeout OBJECT-TYPE
      SYNTAX      INTEGER
      MAX-ACCESS  read-only
      STATUS      current
      DESCRIPTION "Specify the maximum number of seconds spent
      waiting for a complete HTTP message to be received.
      This attribute helps guard against denial of
      service attacks in which a caller indicates that
      they will be sending a message of a certain size
      which they never finish sending."
      ::= { serverEntry 80  }
   
   
   serverCompleteIIOPMessageTimeout OBJECT-TYPE
      SYNTAX      INTEGER
      MAX-ACCESS  read-only
      STATUS      current
      DESCRIPTION "Specify the maximum number of seconds spent
      waiting for a complete IIOP message to be received.
      This attribute helps guard against denial of
      service attacks in which a caller indicates that
      they will be sending a message of a certain size
      which they never finish sending."
      ::= { serverEntry 85  }
   
   
   serverStdoutEnabled OBJECT-TYPE
      SYNTAX      INTEGER
                  {
                     true(1),
                     false(2)
                  }
      
      MAX-ACCESS  read-only
      STATUS      current
      DESCRIPTION "boolean value (true Or false). Determines if log messages should be logged to the standard out
      This property overrides StdoutSeverityLevel and StdoutDebugEnabled."
      ::= { serverEntry 90  }
   
   
   serverStdoutSeverityLevel OBJECT-TYPE
      SYNTAX      INTEGER
      MAX-ACCESS  read-only
      STATUS      current
      DESCRIPTION "The minimum severity of a message which should be logged to the 
      the standard out stream. All messages
      with given severity and higher, qualify."
      ::= { serverEntry 95  }
   
   
   serverLogRemoteExceptionsEnabled OBJECT-TYPE
      SYNTAX      INTEGER
                  {
                     true(1),
                     false(2)
                  }
      
      MAX-ACCESS  read-only
      STATUS      current
      DESCRIPTION "boolean value (true Or false). True if remote exceptions are to be reported to the log."
      ::= { serverEntry 100  }
   
   
   serverInstrumentStackTraceEnabled OBJECT-TYPE
      SYNTAX      INTEGER
                  {
                     true(1),
                     false(2)
                  }
      
      MAX-ACCESS  read-only
      STATUS      current
      DESCRIPTION "boolean value (true Or false). True if exception messages include the server side stack trace."
      ::= { serverEntry 105  }
   
   
   serverRootDirectory OBJECT-TYPE
      SYNTAX      DisplayString (SIZE (1..256))
      MAX-ACCESS  read-only
      STATUS      current
      DESCRIPTION "The root directory for the WebLogic installation for this server."
      ::= { serverEntry 110  }
   
   
   serverMachine OBJECT-TYPE
      SYNTAX      DisplayString (SIZE (1..256))
      MAX-ACCESS  read-only
      STATUS      current
      DESCRIPTION "The machine on which this machine is intended to run or is
      running. If this returns null, it means that this server is not
      assigned to run on any machine and will not be started by the
      infrastructure."
      ::= { serverEntry 115  }
   
   
   serverListenPort OBJECT-TYPE
      SYNTAX      INTEGER
      MAX-ACCESS  read-only
      STATUS      current
      DESCRIPTION "The server's listen port."
      ::= { serverEntry 120  }
   
   
   serverLoginTimeout OBJECT-TYPE
      SYNTAX      INTEGER
      MAX-ACCESS  read-only
      STATUS      current
      DESCRIPTION "The login timeout for the server."
      ::= { serverEntry 125  }
   
   
   serverCluster OBJECT-TYPE
      SYNTAX      DisplayString (SIZE (1..256))
      MAX-ACCESS  read-only
      STATUS      current
      DESCRIPTION "The cluster to which this server belongs."
      ::= { serverEntry 130  }
   
   
   serverClusterWeight OBJECT-TYPE
      SYNTAX      INTEGER
      MAX-ACCESS  read-only
      STATUS      current
      DESCRIPTION "The weight of this server in the cluster it belongs to, if any."
      ::= { serverEntry 135  }
   
   
   serverReplicationGroup OBJECT-TYPE
      SYNTAX      DisplayString (SIZE (1..64))
      MAX-ACCESS  read-only
      STATUS      current
      DESCRIPTION "The server's replication group."
      ::= { serverEntry 140  }
   
   
   serverPreferredSecondaryGroup OBJECT-TYPE
      SYNTAX      DisplayString (SIZE (1..64))
      MAX-ACCESS  read-only
      STATUS      current
      DESCRIPTION "The preferred replication group for the server's secondaries"
      ::= { serverEntry 145  }
   
   
   serverWebServer OBJECT-TYPE
      SYNTAX      DisplayString (SIZE (1..256))
      MAX-ACCESS  read-only
      STATUS      current
      DESCRIPTION "The web server for this server. A server has exactly one
      WebServer. A server may also have one or more VirtualHosts. A
      VirtualHost is a subclass of WebServer."
      ::= { serverEntry 150  }
   
   
   serverExpectedToRun OBJECT-TYPE
      SYNTAX      INTEGER
                  {
                     true(1),
                     false(2)
                  }
      
      MAX-ACCESS  read-only
      STATUS      current
      DESCRIPTION "A boolean value (true Or false).Is this server expected to run if the domain is started."
      ::= { serverEntry 155  }
   
   
   serverJDBCLoggingEnabled OBJECT-TYPE
      SYNTAX      INTEGER
                  {
                     true(1),
                     false(2)
                  }
      
      MAX-ACCESS  read-only
      STATUS      current
      DESCRIPTION "A boolean value (true Or false).Whether or not logging of JDBC logstream is enabled."
      ::= { serverEntry 165  }
   
   
   serverJDBCLogFileName OBJECT-TYPE
      SYNTAX      DisplayString (SIZE (1..256))
      MAX-ACCESS  read-only
      STATUS      current
      DESCRIPTION "The name of the JDBC log file if JDBC logging is enabled."
      ::= { serverEntry 170  }
   
   
   serverIIOPEnabled OBJECT-TYPE
      SYNTAX      INTEGER
                  {
                     true(1),
                     false(2)
                  }
      
      MAX-ACCESS  read-only
      STATUS      current
      DESCRIPTION "A boolean value (true Or false). Whether or not IIOP support is enabled."
      ::= { serverEntry 185  }
   
   
   serverDefaultIIOPUser OBJECT-TYPE
      SYNTAX      DisplayString (SIZE (1..64))
      MAX-ACCESS  read-only
      STATUS      current
      DESCRIPTION "The default IIOP user."
      ::= { serverEntry 190  }
   
   
   serverHttpdEnabled OBJECT-TYPE
      SYNTAX      INTEGER
                  {
                     true(1),
                     false(2)
                  }
      
      MAX-ACCESS  read-only
      STATUS      current
      DESCRIPTION "A boolean value (true Or false). Enables HTTP access"
      ::= { serverEntry 195  }
   
   
   serverConsoleInputEnabled OBJECT-TYPE
      SYNTAX      INTEGER
                  {
                     true(1),
                     false(2)
                  }
      
      MAX-ACCESS  read-only
      STATUS      current
      DESCRIPTION "A boolean value (true Or false). True if commands can be typed at console."
      ::= { serverEntry 210  }
   
   
   serverListenThreadStartDelaySecs OBJECT-TYPE
      SYNTAX      INTEGER
      MAX-ACCESS  read-only
      STATUS      current
      DESCRIPTION "Propeties to consider for removal"
      ::= { serverEntry 215  }
   
   
   serverListenAddress OBJECT-TYPE
      SYNTAX      DisplayString (SIZE (1..256))
      MAX-ACCESS  read-only
      STATUS      current
      DESCRIPTION ""
      ::= { serverEntry 220  }
   
   
   serverLoginTimeoutMillis OBJECT-TYPE
      SYNTAX      INTEGER
      MAX-ACCESS  read-only
      STATUS      current
      DESCRIPTION "Interval to wait for a read to fail on login; 0 to disable"
      ::= { serverEntry 225  }
   
   
   serverAdministrationPort OBJECT-TYPE
      SYNTAX      INTEGER
      MAX-ACCESS  read-only
      STATUS      current
      DESCRIPTION ""
      ::= { serverEntry 230  }
   
   
   serverJavaCompiler OBJECT-TYPE
      SYNTAX      DisplayString (SIZE (1..32))
      MAX-ACCESS  read-only
      STATUS      current
      DESCRIPTION "The Java Compiler for all applications that need to
      compile Java code."
      ::= { serverEntry 235  }
   
   
   serverJavaCompilerPreClassPath OBJECT-TYPE
      SYNTAX      DisplayString (SIZE (1..256))
      MAX-ACCESS  read-only
      STATUS      current
      DESCRIPTION "The options to prepend to the Java compiler classpath for when
      we need to compile Java code."
      ::= { serverEntry 240  }
   
   
   serverJavaCompilerPostClassPath OBJECT-TYPE
      SYNTAX      DisplayString (SIZE (1..256))
      MAX-ACCESS  read-only
      STATUS      current
      DESCRIPTION "The options to append to the Java compiler classpath for when we
      need to compile Java code."
      ::= { serverEntry 245  }
   
   
   serverExtraRmicOptions OBJECT-TYPE
      SYNTAX      DisplayString (SIZE (1..256))
      MAX-ACCESS  read-only
      STATUS      current
      DESCRIPTION "The extra options passed to rmic during server-side generation."
      ::= { serverEntry 250  }
   
   
   serverTransactionLogFilePrefix OBJECT-TYPE
      SYNTAX      DisplayString (SIZE (1..32))
      MAX-ACCESS  read-only
      STATUS      current
      DESCRIPTION "The environment settings for the server. This includes things
      like what compiler to use for EJBs and JSPs."
      ::= { serverEntry 255  }
   
   
   serverEnabledForDomainLog OBJECT-TYPE
      SYNTAX      INTEGER
                  {
                     true(1),
                     false(2)
                  }
      
      MAX-ACCESS  read-only
      STATUS      current
      DESCRIPTION "A boolean value (true Or false). This determines, if messages from this server are sent to the domain wide
      logfile."
      ::= { serverEntry 260  }
   
   
   serverTunnelingEnabled OBJECT-TYPE
      SYNTAX      INTEGER
                  {
                     true(1),
                     false(2)
                  }
      
      MAX-ACCESS  read-only
      STATUS      current
      DESCRIPTION "A boolean value (true Or false). Enables tunneling via http"
      ::= { serverEntry 265  }
   
   
   serverTunnelingClientTimeoutSecs OBJECT-TYPE
      SYNTAX      INTEGER
      MAX-ACCESS  read-only
      STATUS      current
      DESCRIPTION "Duration (in seconds) after which a missing http-tunneled client is considered dead."
      ::= { serverEntry 270  }
   
   
   serverTunnelingClientPingSecs OBJECT-TYPE
      SYNTAX      INTEGER
      MAX-ACCESS  read-only
      STATUS      current
      DESCRIPTION "Interval (in seconds) at which to ping an http-tunneled client to see 
      if its still alive."
      ::= { serverEntry 275  }
   
   
   serverJMSDefaultConnectionFactoriesEnabled OBJECT-TYPE
      SYNTAX      INTEGER
                  {
                     true(1),
                     false(2)
                  }
      
      MAX-ACCESS  read-only
      STATUS      current
      DESCRIPTION "A boolean value (true Or false). Enables JMS default connection factories"
      ::= { serverEntry 280  }
   
   
   serverDomainLogFilter OBJECT-TYPE
      SYNTAX      DisplayString (SIZE (1..256))
      MAX-ACCESS  read-only
      STATUS      current
      DESCRIPTION "Domain log filter to use for log messages of this server.
      If none, is specified, all messages of severity ERROR and above are
      forwarded to the domain logfile. To disable this behaviour use
      'EnabledForDomainLog' attribute."
      ::= { serverEntry 285  }
   
   
   serverAcceptBacklog OBJECT-TYPE
      SYNTAX      INTEGER
      MAX-ACCESS  read-only
      STATUS      current
      DESCRIPTION "Allowed backlog of new TCP connection requests for both the plaintext and SSL port."
      ::= { serverEntry 286  }
   
   
   serverListenPortEnabled OBJECT-TYPE
      SYNTAX      OCTET STRING
      MAX-ACCESS  read-only
      STATUS      current
      DESCRIPTION "Specifies whether this server can be reached through the default plain-text (non-SSL) listen port.  If you disable this listen port, you must enable the default SSL listen port.  You can define additional listen ports for this server by configuring network channels."
      ::= { serverEntry 287  }
   
   
   serverUse81StyleExecuteQueues OBJECT-TYPE
      SYNTAX      OCTET STRING
      MAX-ACCESS  read-only
      STATUS      current
      DESCRIPTION "Backward compatibility mode to switch to 8.1 execute queues instead of WorkManagers. Each of the WorkManagers is converted to an individual execute queue. Setting this attribute requires a server restart."
      ::= { serverEntry 288  }
   
   
   serverStagingMode OBJECT-TYPE
      SYNTAX      OCTET STRING
      MAX-ACCESS  read-only
      STATUS      current
      DESCRIPTION "The mode that specifies whether an application's files are copied from a source on the Administration Server to the Managed Server's staging area during application preparation.  During application preparation, the application's files are copied from the source on the Administration Server to the Managed Server's staging area. If you specify nostage or external_stage, the copy will not occur. This is useful when the staging area is a shared directory, already containing the application files, or if this is a single server domain. The administrator must ensure that the Managed Server's staging directory is set appropriately. Deployment errors will result if the application is not available during the preparation or activation of the application. Each application can override the staging mode specified here."
      ::= { serverEntry 289  }
   
   
   serverLowMemoryGCThreshold OBJECT-TYPE
      SYNTAX      INTEGER
      MAX-ACCESS  read-only
      STATUS      current
      DESCRIPTION "The threshold level (in percent) that this server uses for logging low memory conditions and changing the server health state to Warning.  For example, if you specify 5, the server logs a low memory warning in the log file and changes the server health state to Warning after the average free memory reaches 5% of the initial free memory measured at the server's boot time."
      ::= { serverEntry 290  }
   
   
   serverStagingDirectoryName OBJECT-TYPE
      SYNTAX      OCTET STRING
      MAX-ACCESS  read-only
      STATUS      current
      DESCRIPTION "The directory path on the Managed Server where all staged (prepared) applications are placed.  If an absolute directory name is not specified, the path is relative to rootdirectory/ Once configured, you cannot change the staging directory name. Remove all applications from the server prior to changing this attribute. The default staging directory is 'stage', relative to the server root."
      ::= { serverEntry 291  }
   
   
   serverGracefulShutdownTimeout OBJECT-TYPE
      SYNTAX      INTEGER
      MAX-ACCESS  read-only
      STATUS      current
      DESCRIPTION "Number of seconds a graceful shutdown operation waits before forcing a shut down. A graceful shutdown gives WebLogic Server subsystems time to complete certain application processing currently in progress. If subsystems are unable to complete processing within the number of seconds that you specify here, then the server will force shutdown automatically.  A value of 0 means that the server will wait indefinitely for graceful shutdown to complete.  The graceful shutdown timeout applies only to graceful shutdown operations."
      ::= { serverEntry 292  }
   
   
   serverManagedServerIndependenceEnabled OBJECT-TYPE
      SYNTAX      OCTET STRING
      MAX-ACCESS  read-only
      STATUS      current
      DESCRIPTION "Specifies whether this Managed Server can be started when the Administration Server is unavailable.  In such a case, the Managed Server retrieves its configuration by reading a configuration file and other files directly."
      ::= { serverEntry 293  }
   
   
   serverStartupTimeout OBJECT-TYPE
      SYNTAX      INTEGER
      MAX-ACCESS  read-only
      STATUS      current
      DESCRIPTION "Timeout value for server start and resume operations. If the server fails to start in the timeout period, it will force shutdown.  A value of 0 means that the server will wait indefinitely for the operation to complete."
      ::= { serverEntry 294  }
   
   
   serverSocketBufferSizeAsChunkSize OBJECT-TYPE
      SYNTAX      OCTET STRING
      MAX-ACCESS  read-only
      STATUS      current
      DESCRIPTION "Specifies whether the server's buffer size for sending or receiving data through a raw socket should be set to 4KB.  Otherwise, the server does not impose a limit to the buffer size and defers to the operating system. This option is useful only on some operating systems for improving performance. It should be disabled in most environments."
      ::= { serverEntry 295  }
   
   
   serverRestartMax OBJECT-TYPE
      SYNTAX      INTEGER
      MAX-ACCESS  read-only
      STATUS      current
      DESCRIPTION "The number of times that the Node Manager can restart this server within the interval specified in RestartInterval."
      ::= { serverEntry 296  }
   
   
   serverCompleteMessageTimeout OBJECT-TYPE
      SYNTAX      INTEGER
      MAX-ACCESS  read-only
      STATUS      current
      DESCRIPTION "The maximum number of seconds that this server waits for a complete message to be received. If you configure network channels for this server, each channel can override this message timeout.  This timeout helps guard against a denial of service attack in which a caller indicates that it will be sending a message of a certain size which it never finishes sending."
      ::= { serverEntry 297  }
   
   
   serverServerLifeCycleTimeoutVal OBJECT-TYPE
      SYNTAX      INTEGER
      MAX-ACCESS  read-only
      STATUS      current
      DESCRIPTION "Number of seconds a force shutdown operation waits before timing out and killing itself. If the operation does not complete within the configured timeout seconds, the server will shutdown automatically if the state of the server at that time was SHUTTING_DOWN.  A value of 0 means that the server will wait indefinitely for life cycle operation to complete."
      ::= { serverEntry 298  }
   
   
   serverVerboseEJBDeploymentEnabled OBJECT-TYPE
      SYNTAX      OCTET STRING
      MAX-ACCESS  read-only
      STATUS      current
      DESCRIPTION "Whether or not verbose deployment of EJBs is enabled."
      ::= { serverEntry 299  }
   
   
   serverAdminReconnectIntervalSeconds OBJECT-TYPE
      SYNTAX      INTEGER
      MAX-ACCESS  read-only
      STATUS      current
      DESCRIPTION "The number of seconds between reconnection attempts to the admin server. When the admin server fails the managed server will periodically try to connect back to it."
      ::= { serverEntry 300  }
   
   
   serverClientCertProxyEnabled OBJECT-TYPE
      SYNTAX      OCTET STRING
      MAX-ACCESS  read-only
      STATUS      current
      DESCRIPTION "Specifies whether the HttpClusterServlet proxies the client certificate in a special header.  By default (or if you specify false), the weblogic.xml deployment descriptor for each web application that is deployed on this server determines whether the web application trusts certificates sent from the proxy server plugin. By default (or if the deployment descriptor specifies false), users cannot log in to the web application from a proxy server plugin.  A value of true causes proxy-server plugins to pass identity certifications from clients to all web applications that are deployed on this server instance. A proxy-server plugin encodes each identify certification in the WL-Proxy-Client-Cert header and passes the header to WebLogic Server instances. A WebLogic Server instance takes the certificate information from the header, trusting that it came from a secure source, and uses that information to authenticate the user.  If you specify true, use a weblogic.security.net.ConnectionFilter to ensure that this WebLogic Server instance accepts connections only from the machine on which the proxy-server plugin is running. Specifying true without using a connection filter creates a security vulnerability because the WL-Proxy-Client-Cert header can be spoofed.  A cluster can also specify whether the HttpClusterServlet proxies the client certificate in a special header. The cluster-level setting overrides the setting in individual servers that are part of the cluster."
      ::= { serverEntry 301  }
   
   
   serverRestartDelaySeconds OBJECT-TYPE
      SYNTAX      INTEGER
      MAX-ACCESS  read-only
      STATUS      current
      DESCRIPTION "The number of seconds the Node Manager should wait before restarting this server.  After killing a server process, the system might need several seconds to release the TCP port(s) the server was using. If Node Manager attempts to restart the Managed Server while its ports are still active, the startup attempt fails.  If AutoMigration is enabled and RestartDelaySeconds is 0, the RestartDelaySeconds is automatically set to the lease time. This prevents the server from failing to restart after migration when the previous lease is still valid."
      ::= { serverEntry 302  }
   
   
   serverLowMemoryGranularityLevel OBJECT-TYPE
      SYNTAX      INTEGER
      MAX-ACCESS  read-only
      STATUS      current
      DESCRIPTION "The granularity level (in percent) that this server uses for logging low memory conditions and changing the server health state to Warning.  For example, if you specify 5 and the average free memory drops by 5% or more over two measured intervals, the server logs a low memory warning in the log file and changes the server health state to Warning."
      ::= { serverEntry 303  }
   
   
   serverSocketReaders OBJECT-TYPE
      SYNTAX      INTEGER
      MAX-ACCESS  read-only
      STATUS      current
      DESCRIPTION "The number of socket reader threads"
      ::= { serverEntry 304  }
   
   
   serverOutboundEnabled OBJECT-TYPE
      SYNTAX      OCTET STRING
      MAX-ACCESS  read-only
      STATUS      current
      DESCRIPTION "Specifies whether new server-to-server connections may consider the default server channel when initiating a connection. This is only relevant if the connection needs to be bound to the default listen address. This will only work for binary protocols that support both outbound and inbound traffic.  When this feature is not enabled, connections are initiated using a local address selected by the underlying hardware. For the default channel this is usually what is wanted for IP-routing to be effective. Note that since the default is false, other outbound channels will be considered in preference to the default channel.  Default administration channels, created when the domain-wide administration port is turned on, are always considered and bound when initiating an administrative connection. To allow IP-routing for administration traffic create custom admin with {@link NetworkAccessPointMBean#isOutboundEnabled isOutboundEnabled} set to false instead of enabling the domain-wide ADMIN port."
      ::= { serverEntry 305  }
   
   
   serverJDBCLLRTableName OBJECT-TYPE
      SYNTAX      OCTET STRING
      MAX-ACCESS  read-only
      STATUS      current
      DESCRIPTION "The table name for this server's Logging Last Resource (LLR) database table(s). WebLogic Server creates the table(s) and then uses them during transaction processing for the LLR transaction optimization. This setting must be unique for each server. The default table name is WL_LLR_SERVERNAME.  This setting only applies if this server hosts one or more LLR-enabled JDBC data sources.  The format for the tables that WebLogic Server creates is [[[catalog.]schema.]name. Each '.' in the table name is significant, and schema generally corresponds to username in many databases.  IMPORTANT: If this value is changed but the LLR table already exists in the database, you must preserve the existing table's data. Consequently, when changing the table name, the existing database table must be renamed by a database administrator to match the new configured table name. Otherwise, transaction records may be lost, resulting in heuristic failures that aren't logged.  IMPORTANT: Each server's table name must be unique. Multiple LLR-enabled data sources within the same server may share the same table, but multiple servers must not share the same table. If multiple same-named servers share a table, the behavior is undefined and it is likely that transactions will not recover properly after a crash, creating heuristic hazards."
      ::= { serverEntry 306  }
   
   
   serverInterfaceAddress OBJECT-TYPE
      SYNTAX      OCTET STRING
      MAX-ACCESS  read-only
      STATUS      current
      DESCRIPTION "The IP address of the NIC that this server should use for multicast traffic."
      ::= { serverEntry 307  }
   
   
   serverExtraEjbcOptions OBJECT-TYPE
      SYNTAX      OCTET STRING
      MAX-ACCESS  read-only
      STATUS      current
      DESCRIPTION "The options passed to the EJB compiler during server-side generation.  Each EJB component can override the compiler options that you specify here. The following options are valid:   -forcegeneration Forces generation of wrapper classes. Without this flag the classes may not be regenerated if it is determined to be unnecessary.  -disableHotCodeGen Generate ejb stub and skel as part of ejbc. Avoid HotCodeGen to have better performance.   -keepgenerated Keep the generated .java files.   -compiler javac Java compiler to exec.  If not specified, the -compilerclass option will be used.  -compilerclass com.sun.tools.javac.Main Specifies the compiler class to invoke.  -g Compile debugging info into class file.  -normi Passed through to Symantec's sj.  -classpath path Classpath to use.  -source source Source version.  -Joption Flags passed through to java runtime."
      ::= { serverEntry 308  }
   
   
   serverCOMEnabled OBJECT-TYPE
      SYNTAX      OCTET STRING
      MAX-ACCESS  read-only
      STATUS      current
      DESCRIPTION "Specifies whether COM support is enabled on the regular (non-SSL) port. COM is not supported on the SSL port. (The remaining fields on this page are relevant only if you check this box.)"
      ::= { serverEntry 309  }
   
   
   serverMessageIdPrefixEnabled OBJECT-TYPE
      SYNTAX      OCTET STRING
      MAX-ACCESS  read-only
      STATUS      current
      DESCRIPTION "Indicates whether message IDs in logged messages will include a prefix. Message ids are 6 digit numeric strings that can be optionally presented in a log entry with a prefix. The prefix used by server messages is 'BEA-'."
      ::= { serverEntry 310  }
   
   
   serverAutoRestart OBJECT-TYPE
      SYNTAX      OCTET STRING
      MAX-ACCESS  read-only
      STATUS      current
      DESCRIPTION "Specifies whether the Node Manager can automatically restart this server if it crashes or otherwise or goes down unexpectedly."
      ::= { serverEntry 311  }
   
   
   serverIgnoreSessionsDuringShutdown OBJECT-TYPE
      SYNTAX      OCTET STRING
      MAX-ACCESS  read-only
      STATUS      current
      DESCRIPTION "Indicates whether a graceful shutdown operation drops all HTTP sessions immediately. If this is set to false, a graceful shutdown operation waits for HTTP sessions to complete or timeout."
      ::= { serverEntry 312  }
   
   
   serverDefaultTGIOPUser OBJECT-TYPE
      SYNTAX      OCTET STRING
      MAX-ACCESS  read-only
      STATUS      current
      DESCRIPTION "The default user associated with the Tuxedo GIOP (TGIOP) protocol. (Requires you to configure WebLogic Tuxedo Connector (WTC) for this server.)"
      ::= { serverEntry 313  }
   
   
   serverMaxOpenSockCount OBJECT-TYPE
      SYNTAX      INTEGER
      MAX-ACCESS  read-only
      STATUS      current
      DESCRIPTION "The maximum number of open sockets allowed in server at a given point of time.  When the maximum threshold is reached, the server stops accepting new requests until the number of sockets drops below the threshold.  A value less than 0 indicates an unlimited size."
      ::= { serverEntry 314  }
   
   
   serverLowMemorySampleSize OBJECT-TYPE
      SYNTAX      INTEGER
      MAX-ACCESS  read-only
      STATUS      current
      DESCRIPTION "The number of times this server samples free memory during the time period specified by LowMemoryTimeInterval.  Increasing the sample size can improve the accuracy of the reading."
      ::= { serverEntry 315  }
   
   
   serverAutoKillIfFailed OBJECT-TYPE
      SYNTAX      OCTET STRING
      MAX-ACCESS  read-only
      STATUS      current
      DESCRIPTION "Specifies whether the Node Manager should automatically kill this server if its health state is failed."
      ::= { serverEntry 316  }
   
   
   serverCustomIdentityKeyStoreFileName OBJECT-TYPE
      SYNTAX      OCTET STRING
      MAX-ACCESS  read-only
      STATUS      current
      DESCRIPTION "The path and file name of the identity keystore.  The path name must either be absolute or relative to where the server was booted. The custom identity key store file name is only used if KeyStores is CUSTOM_IDENTITY_AND_JAVA_STANDARD_TRUST, CUSTOM_IDENTITY_AND_CUSTOM_TRUST or CUSTOM_IDENTITY_AND_COMMAND_LINE_TRUST."
      ::= { serverEntry 317  }
   
   
   serverTGIOPEnabled OBJECT-TYPE
      SYNTAX      OCTET STRING
      MAX-ACCESS  read-only
      STATUS      current
      DESCRIPTION "Specifies whether this server supports Tuxedo GIOP (TGIOP) requests. (Requires you to configure WebLogic Tuxedo Connector (WTC) for this server.)"
      ::= { serverEntry 318  }
   
   
   serverHealthCheckStartDelaySeconds OBJECT-TYPE
      SYNTAX      INTEGER
      MAX-ACCESS  read-only
      STATUS      current
      DESCRIPTION "The number of seconds the Node Manager should wait before starting to monitor the server."
      ::= { serverEntry 319  }
   
   
   serverUploadDirectoryName OBJECT-TYPE
      SYNTAX      OCTET STRING
      MAX-ACCESS  read-only
      STATUS      current
      DESCRIPTION "The directory path on the Administration Server where all uploaded applications are placed.  If an absolute directory name is not specified, the path is relative to rootdirectory/ The default staging directory is 'stage', relative to the server root.. On the Managed Server this returns null, and is not configurable."
      ::= { serverEntry 320  }
   
   
   serverWeblogicPluginEnabled OBJECT-TYPE
      SYNTAX      OCTET STRING
      MAX-ACCESS  read-only
      STATUS      current
      DESCRIPTION "Specifies whether this server uses the proprietary WL-Proxy-Client-IP header, which is recommended if the server instance will receive requests from a proxy plug-in.  If the server instance is a member of a cluster that will receive proxied requests, enable the WebLogic plugin at the cluster level. For servers that are members of a cluster, the setting at the cluster level overrides the server's setting.  When the WebLogic plugin is enabled, a call to getRemoteAddr will return the address of the browser client from the proprietary WL-Proxy-Client-IP header instead of the web server."
      ::= { serverEntry 321  }
   
   
   serverJDBCLoginTimeoutSeconds OBJECT-TYPE
      SYNTAX      INTEGER
      MAX-ACCESS  read-only
      STATUS      current
      DESCRIPTION "Get the JDBC Login Timeout value. Specified value is passed into java.sql.DriverManager.setLoginTimeout(). Note that this DriverManager setting will impact *all* JDBC drivers loaded into this JVM. Feature is disabled by default."
      ::= { serverEntry 322  }
   
   
   serverClasspathServletDisabled OBJECT-TYPE
      SYNTAX      OCTET STRING
      MAX-ACCESS  read-only
      STATUS      current
      DESCRIPTION "The ClasspathServlet will serve any class file in the classpath and is registered by default in every Web application (including management). It does not need to be turned on for many applications though, and represents a security hole if unchecked."
      ::= { serverEntry 323  }
   
   
   serverIdleConnectionTimeout OBJECT-TYPE
      SYNTAX      INTEGER
      MAX-ACCESS  read-only
      STATUS      current
      DESCRIPTION "The maximum number of seconds that a connection is allowed to be idle before it is closed by the server. The T3 and T3S protocols ignore this attribute. If you configure network channels for this server, each channel can override this idle connection message timeout.  This timeout helps guard against server deadlock through too many open connections."
      ::= { serverEntry 324  }
   
   
   serverDefaultInternalServletsDisabled OBJECT-TYPE
      SYNTAX      OCTET STRING
      MAX-ACCESS  read-only
      STATUS      current
      DESCRIPTION "Specifies whether all default servlets in the servlet engine are disabled.  This includes: weblogic.servlet.ClasspathServlet weblogic.servlet.utils.iiop.GetIORServlet weblogic.rjvm.http.TunnelSendServlet weblogic.rjvm.http.TunnelRecvServlet weblogic.rjvm.http.TunnelLoginServlet weblogic.rjvm.http.TunnelCloseServlet If set to true, this property overrides the ClasspathServletDisabled property."
      ::= { serverEntry 325  }
   
   
   serverMaxMessageSize OBJECT-TYPE
      SYNTAX      INTEGER
      MAX-ACCESS  read-only
      STATUS      current
      DESCRIPTION "The maximum number of bytes allowed in messages that are received over all supported protocols, unless overridden by a protocol-specific setting or a custom channel setting.  The order of precedence for setting message size maximums is as follows:    A channel-wide maximum in a custom network channel.    A protocol-specific setting in the default network channel. See {@link #MaxCOMMessageSize MaxCOMMessageSize} {@link #MaxHTTPMessageSize MaxHTTPMessageSize} {@link #MaxIIOPMessageSize MaxIIOPessageSize} {@link #MaxT3MessageSize MaxT3MessageSize}     The message maximum in this attribute.    This maximum message size helps guard against a denial of service attack in which a caller attempts to force the server to allocate more memory than is available thereby keeping the server from responding quickly to other requests."
      ::= { serverEntry 326  }
   
   
   serverCustomTrustKeyStoreType OBJECT-TYPE
      SYNTAX      OCTET STRING
      MAX-ACCESS  read-only
      STATUS      current
      DESCRIPTION "The type of the keystore. Generally, this is JKS.  If empty or null, then the JDK's default keystore type (specified in java.security) is used. This keystore type is only used if KeyStores is CUSTOM_IDENTITY_AND_CUSTOM_TRUST."
      ::= { serverEntry 327  }
   
   
   serverListenersBindEarly OBJECT-TYPE
      SYNTAX      OCTET STRING
      MAX-ACCESS  read-only
      STATUS      current
      DESCRIPTION "Determines whether the server should bind server sockets early. Early binding detects port conflicts quickly and also gives user feedback on the default listen port as to the server state."
      ::= { serverEntry 328  }
   
   
   serverLowMemoryTimeInterval OBJECT-TYPE
      SYNTAX      INTEGER
      MAX-ACCESS  read-only
      STATUS      current
      DESCRIPTION "The amount of time (in seconds) that defines the interval over which this server determines average free memory values.  By default, the server obtains an average free memory value every 3600 seconds. This interval is not used if the JRockit VM is used, as the memory samples are collected immediately after a VM-scheduled garbage collection. Taking memory samples after a garbage collection gives a more accurate average value of the free memory."
      ::= { serverEntry 329  }
   
   
   serverTransactionLogFileWritePolicy OBJECT-TYPE
      SYNTAX      OCTET STRING
      MAX-ACCESS  read-only
      STATUS      current
      DESCRIPTION "The policy that determines how transaction log file entries are written to disk. This policy can affect transaction performance. (Note: To be transactionally safe, the Direct-Write policy may require additional OS or environment changes on some Windows systems.)  WebLogic Server supports the following policies:    Cache-Flush. Flushes operating system and on-disk caches after each write.    Direct-Write. Tells the operating system to write directly to disk with each write. Direct-Write performs better than Cache-Flush and is available on Windows, HP-UX, and Solaris.    If Direct-Write is not supported on the host platform, the policy becomes Cache-Flush and a log message is printed.  Note: On Windows, unlike Solaris and HP, the 'Direct-Write' policy may leave transaction data in the on-disk cache without writing it to disk immediately. This is not transactionally safe because a power failure can cause loss of on-disk cache data. For transactionally safe writes using 'Direct-Write' on Windows, either disable all write caching for the disk (enabled by default), or use a disk with a battery-backed cache.  The on-disk cache for a hard-drive on Windows can be disabled through system administration: Control-Panel -&gt; System -&gt; Hardware-tab -&gt; Device-Manager-button -&gt; Disk-Drives -&gt; name-of-drive -&gt; Policies-tab -&gt; 'Enable write caching on the disk' check-box. Some file systems do not allow this value to be changed. For example, a RAID system that has a reliable cache."
      ::= { serverEntry 330  }
   
   
   serverHttpTraceSupportEnabled OBJECT-TYPE
      SYNTAX      OCTET STRING
      MAX-ACCESS  read-only
      STATUS      current
      DESCRIPTION "Returns the HttpTraceSupportEnabled value"
      ::= { serverEntry 331  }
   
   
   serverKeyStores OBJECT-TYPE
      SYNTAX      OCTET STRING
      MAX-ACCESS  read-only
      STATUS      current
      DESCRIPTION "Which configuration rules should be used for finding the server's identity and trust keystores?"
      ::= { serverEntry 332  }
   
   
   serverAutoMigrationEnabled OBJECT-TYPE
      SYNTAX      OCTET STRING
      MAX-ACCESS  read-only
      STATUS      current
      DESCRIPTION "Specifies whether Node Manager can automatically restart this server and its services on another machine if the server fails."
      ::= { serverEntry 333  }
   
   
   serverPeriodLength OBJECT-TYPE
      SYNTAX      INTEGER
      MAX-ACCESS  read-only
      STATUS      current
      DESCRIPTION "The time interval in milliseconds of the heartbeat period. A value of 0 indicates that heartbeats are turned off."
      ::= { serverEntry 334  }
   
   
   serverStuckThreadTimerInterval OBJECT-TYPE
      SYNTAX      INTEGER
      MAX-ACCESS  read-only
      STATUS      current
      DESCRIPTION "The number of seconds after which WebLogic Server periodically scans threads to see if they have been continually working for the configured maximum length of time."
      ::= { serverEntry 335  }
   
   
   serverDGCIdlePeriodsUntilTimeout OBJECT-TYPE
      SYNTAX      INTEGER
      MAX-ACCESS  read-only
      STATUS      current
      DESCRIPTION "The number of idle periods allowed before object is collected."
      ::= { serverEntry 336  }
   
   
   serverMuxerClass OBJECT-TYPE
      SYNTAX      OCTET STRING
      MAX-ACCESS  read-only
      STATUS      current
      DESCRIPTION "The muxer class name."
      ::= { serverEntry 337  }
   
   
   serverHealthCheckIntervalSeconds OBJECT-TYPE
      SYNTAX      INTEGER
      MAX-ACCESS  read-only
      STATUS      current
      DESCRIPTION "The number of seconds that defines the frequency of this server's self-health monitoring. The server monitors the health of it's subsystems every HealthCheckIntervalSeconds and changes the Server's overall state if required."
      ::= { serverEntry 338  }
   
   
   serverRestartIntervalSeconds OBJECT-TYPE
      SYNTAX      INTEGER
      MAX-ACCESS  read-only
      STATUS      current
      DESCRIPTION "The number of seconds during which this server can be restarted, up to the number of times specified in RestartMax."
      ::= { serverEntry 339  }
   
   
   serverIdlePeriodsUntilTimeout OBJECT-TYPE
      SYNTAX      INTEGER
      MAX-ACCESS  read-only
      STATUS      current
      DESCRIPTION "The number of idle periods until peer is considered unreachable"
      ::= { serverEntry 340  }
   
   
   serverCustomTrustKeyStoreFileName OBJECT-TYPE
      SYNTAX      OCTET STRING
      MAX-ACCESS  read-only
      STATUS      current
      DESCRIPTION "The path and file name of the custom trust keystore.  The path name must either be absolute or relative to where the server was booted. This file name is only used if KeyStores is CUSTOM_IDENTITY_AND_CUSTOM_TRUST."
      ::= { serverEntry 341  }
   
   
   serverHostsMigratableServices OBJECT-TYPE
      SYNTAX      OCTET STRING
      MAX-ACCESS  read-only
      STATUS      current
      DESCRIPTION "Gets the hostsMigratableServices attribute of the ServerMBean object"
      ::= { serverEntry 342  }
   
   
   serverExternalDNSName OBJECT-TYPE
      SYNTAX      OCTET STRING
      MAX-ACCESS  read-only
      STATUS      current
      DESCRIPTION "The external IP address or DNS name for this server.  This address will be sent with HTTP session cookies and with dynamic server lists to HTTP proxies. It will also be used by external application clients to enable the propagation of RMI traffic through network address translating (NAT) firewalls.  You must specify an external DNS name for configurations in which a firewall is performing network address translation, unless clients are accessing WebLogic Server using t3 and the default channel. For example, define the external DNS name for configurations in which a firewall is performing network address translation, and clients are accessing WebLogic Server using HTTP via a proxy plug-in."
      ::= { serverEntry 343  }
   
   
   serverOutboundPrivateKeyEnabled OBJECT-TYPE
      SYNTAX      OCTET STRING
      MAX-ACCESS  read-only
      STATUS      current
      DESCRIPTION "Specifies whether the SSL identity specified by {@link SSLMBean#ServerPrivateKeyAlias SSLMBean#ServerPrivateKeyAlias} for this server should be used for outbound SSL connections on the default server channel. In normal circumstances the outbound identity is determined by the caller's environment."
      ::= { serverEntry 344  }
   
   
   serverAdministrationProtocol OBJECT-TYPE
      SYNTAX      OCTET STRING
      MAX-ACCESS  read-only
      STATUS      current
      DESCRIPTION "Returns the protocol to be used for administrative connections when none is specified."
      ::= { serverEntry 345  }
   
   
   serverCustomIdentityKeyStoreType OBJECT-TYPE
      SYNTAX      OCTET STRING
      MAX-ACCESS  read-only
      STATUS      current
      DESCRIPTION "The type of the keystore. Generally, this is JKS.  If empty or null, then the JDK's default keystore type (specified in java.security) is used. The custom identity key store type is only used if KeyStores is CUSTOM_IDENTITY_AND_JAVA_STANDARD_TRUST, CUSTOM_IDENTITY_AND_CUSTOM_TRUST or CUSTOM_IDENTITY_AND_COMMAND_LINE_TRUST."
      ::= { serverEntry 346  }
   
   
   serverStartupMode OBJECT-TYPE
      SYNTAX      OCTET STRING
      MAX-ACCESS  read-only
      STATUS      current
      DESCRIPTION "The state in which this server should be started. If you specify STANDBY, you must also enable the domain-wide administration port.  In the RUNNING state, a server offers its services to clients and can operate as a full member of a cluster. In the ADMIN state, the server is up and running, but available only for administration operations, allowing you to perform server and application-level administration tasks without risk to running applications. In the STANDBY state, a server instance does not process any request; its regular Listen Port is closed. The Administration Port is open. It only accepts life cycle commands that transition the server instance to either the RUNNING or the SHUTDOWN state. Other Administration requests are not accepted. A STANDBYserver's only purpose is to resume into the RUNNING state quickly; it saves server startup time."
      ::= { serverEntry 347  }
   
   
   serverNMSocketCreateTimeoutInMillis OBJECT-TYPE
      SYNTAX      INTEGER
      MAX-ACCESS  read-only
      STATUS      current
      DESCRIPTION "Returns the timeout value to be used by NodeManagerRuntime when creating a a socket connection to the agent. "
      ::= { serverEntry 348  }
   
   
   serverStartTable OBJECT-TYPE
      SYNTAX      SEQUENCE OF ServerStartEntry
      MAX-ACCESS  not-accessible
      STATUS      current
      DESCRIPTION "This table represents a serverStart in the domain."
      ::= { wls 735  }
      
   
   serverStartEntry OBJECT-TYPE
      SYNTAX      ServerStartEntry
      MAX-ACCESS  not-accessible
      STATUS      current
      DESCRIPTION "Entry of serverStartTable"
      INDEX { serverStartIndex}
      ::= { serverStartTable 1 }
      
   ServerStartEntry ::=
      SEQUENCE
      {
         serverStartIndex     DisplayString (SIZE (1..16)),
         serverStartObjectName DisplayString (SIZE (1..256)),
         serverStartType      DisplayString (SIZE (1..64)),
         serverStartName      DisplayString (SIZE (1..64)),
         serverStartParent    DisplayString (SIZE (1..256)),
         serverStartArguments DisplayString (SIZE (1..256)),
         serverStartBeaHome   DisplayString (SIZE (1..256)),
         serverStartClassPath DisplayString (SIZE (1..256)),
         serverStartJavaHome  DisplayString (SIZE (1..256)),
         serverStartRootDirectory DisplayString (SIZE (1..256)),
         serverStartSecurityPolicyFile DisplayString (SIZE (1..256)),
         serverStartUsername  DisplayString (SIZE (1..256)),
         serverStartJavaVendor OCTET STRING
      }
      
   
   serverStartIndex OBJECT-TYPE
      SYNTAX      DisplayString (SIZE (1..16))
      MAX-ACCESS  read-only
      STATUS      current
      DESCRIPTION "Unique value directed from ObjectName which is used as table index"
      ::= { serverStartEntry 1  }
   
   
   serverStartObjectName OBJECT-TYPE
      SYNTAX      DisplayString (SIZE (1..256))
      MAX-ACCESS  read-only
      STATUS      current
      DESCRIPTION "JMX-standard MBean name"
      ::= { serverStartEntry 5  }
   
   
   serverStartType OBJECT-TYPE
      SYNTAX      DisplayString (SIZE (1..64))
      MAX-ACCESS  read-only
      STATUS      current
      DESCRIPTION "BEA-proprietary MBean type"
      ::= { serverStartEntry 10  }
   
   
   serverStartName OBJECT-TYPE
      SYNTAX      DisplayString (SIZE (1..64))
      MAX-ACCESS  read-only
      STATUS      current
      DESCRIPTION "BEA-proprietary MBean name"
      ::= { serverStartEntry 15  }
   
   
   serverStartParent OBJECT-TYPE
      SYNTAX      DisplayString (SIZE (1..256))
      MAX-ACCESS  read-only
      STATUS      current
      DESCRIPTION "BEA-proprietary Parent object's identification, with syntax
      <type>:<name>"
      ::= { serverStartEntry 20  }
   
   
   serverStartArguments OBJECT-TYPE
      SYNTAX      DisplayString (SIZE (1..256))
      MAX-ACCESS  read-only
      STATUS      current
      DESCRIPTION "The startup arguments to use when starting this server."
      ::= { serverStartEntry 25  }
   
   
   serverStartBeaHome OBJECT-TYPE
      SYNTAX      DisplayString (SIZE (1..256))
      MAX-ACCESS  read-only
      STATUS      current
      DESCRIPTION "Returns the BEA home to be used to start this server. Note that this
      * path is on the remote machine."
      ::= { serverStartEntry 30  }
   
   
   serverStartClassPath OBJECT-TYPE
      SYNTAX      DisplayString (SIZE (1..256))
      MAX-ACCESS  read-only
      STATUS      current
      DESCRIPTION "Set the classpath to be used to start this server. Note that this path
      * is on the remote machine."
      ::= { serverStartEntry 35  }
   
   
   serverStartJavaHome OBJECT-TYPE
      SYNTAX      DisplayString (SIZE (1..256))
      MAX-ACCESS  read-only
      STATUS      current
      DESCRIPTION "The Java home directory (on the remote machine) to use when starting 
      * this server. The java binary (or java.exe executable in Windows) is 
      * taken from the Java home /bin directory to start the managed server."
      ::= { serverStartEntry 40  }
   
   
   serverStartRootDirectory OBJECT-TYPE
      SYNTAX      DisplayString (SIZE (1..256))
      MAX-ACCESS  read-only
      STATUS      current
      DESCRIPTION "Returns the RootDirectory to be used to start this server. Note that this
      * path is on the remote machine."
      ::= { serverStartEntry 45  }
   
   
   serverStartSecurityPolicyFile OBJECT-TYPE
      SYNTAX      DisplayString (SIZE (1..256))
      MAX-ACCESS  read-only
      STATUS      current
      DESCRIPTION "The security policy file to use when starting this 
      * server. Note that the directory and filename refer to a path on 
      * the remote machine."
      ::= { serverStartEntry 50  }
   
   
   serverStartUsername OBJECT-TYPE
      SYNTAX      DisplayString (SIZE (1..256))
      MAX-ACCESS  read-only
      STATUS      current
      DESCRIPTION "The username to use when booting the server and performing server 
      * health monitoring."
      ::= { serverStartEntry 55  }
   
   
   serverStartJavaVendor OBJECT-TYPE
      SYNTAX      OCTET STRING
      MAX-ACCESS  read-only
      STATUS      current
      DESCRIPTION "The Java Vendor value to use when starting this server For example, BEA, Sun, HP etc    If the server is part of a cluster and configured for automatic migration across possibly different platforms with different vendors providing the JDKs, then, both JavaVendor and JavaHome should be set in the generated configuration file instead."
      ::= { serverStartEntry 56  }
   
   
   snmpAgentTable OBJECT-TYPE
      SYNTAX      SEQUENCE OF SnmpAgentEntry
      MAX-ACCESS  not-accessible
      STATUS      current
      DESCRIPTION "This table represents a snmpAgent in the domain."
      ::= { wls 740  }
      
   
   snmpAgentEntry OBJECT-TYPE
      SYNTAX      SnmpAgentEntry
      MAX-ACCESS  not-accessible
      STATUS      current
      DESCRIPTION "Entry of snmpAgentTable"
      INDEX { snmpAgentIndex}
      ::= { snmpAgentTable 1 }
      
   SnmpAgentEntry ::=
      SEQUENCE
      {
         snmpAgentIndex       DisplayString (SIZE (1..16)),
         snmpAgentObjectName  DisplayString (SIZE (1..256)),
         snmpAgentType        DisplayString (SIZE (1..64)),
         snmpAgentName        DisplayString (SIZE (1..64)),
         snmpAgentParent      DisplayString (SIZE (1..256)),
         snmpAgentCommunityPrefix DisplayString,
         snmpAgentDebugLevel  INTEGER,
         snmpAgentMibDataRefreshInterval INTEGER,
         snmpAgentServerStatusCheckIntervalFactor INTEGER,
         snmpAgentSNMPPort    INTEGER,
         snmpAgentSNMPTrapVersion INTEGER,
         snmpAgentEnabled     INTEGER,
         snmpAgentSendAutomaticTrapsEnabled INTEGER
      }
      
   
   snmpAgentIndex OBJECT-TYPE
      SYNTAX      DisplayString (SIZE (1..16))
      MAX-ACCESS  read-only
      STATUS      current
      DESCRIPTION "Unique value directed from ObjectName which is used as table index"
      ::= { snmpAgentEntry 1  }
   
   
   snmpAgentObjectName OBJECT-TYPE
      SYNTAX      DisplayString (SIZE (1..256))
      MAX-ACCESS  read-only
      STATUS      current
      DESCRIPTION "JMX-standard MBean name"
      ::= { snmpAgentEntry 5  }
   
   
   snmpAgentType OBJECT-TYPE
      SYNTAX      DisplayString (SIZE (1..64))
      MAX-ACCESS  read-only
      STATUS      current
      DESCRIPTION "BEA-proprietary MBean type"
      ::= { snmpAgentEntry 10  }
   
   
   snmpAgentName OBJECT-TYPE
      SYNTAX      DisplayString (SIZE (1..64))
      MAX-ACCESS  read-only
      STATUS      current
      DESCRIPTION "BEA-proprietary MBean name"
      ::= { snmpAgentEntry 15  }
   
   
   snmpAgentParent OBJECT-TYPE
      SYNTAX      DisplayString (SIZE (1..256))
      MAX-ACCESS  read-only
      STATUS      current
      DESCRIPTION "BEA-proprietary Parent object's identification, with syntax
      <type>:<name>"
      ::= { snmpAgentEntry 20  }
   
   
   snmpAgentCommunityPrefix OBJECT-TYPE
      SYNTAX      DisplayString
      MAX-ACCESS  read-only
      STATUS      current
      DESCRIPTION "Generated Object."
      ::= { snmpAgentEntry 21  }
   
   
   snmpAgentDebugLevel OBJECT-TYPE
      SYNTAX      INTEGER
      MAX-ACCESS  read-only
      STATUS      current
      DESCRIPTION "Generated Object."
      ::= { snmpAgentEntry 22  }
   
   
   snmpAgentMibDataRefreshInterval OBJECT-TYPE
      SYNTAX      INTEGER
      MAX-ACCESS  read-only
      STATUS      current
      DESCRIPTION "Generated Object."
      ::= { snmpAgentEntry 23  }
   
   
   snmpAgentServerStatusCheckIntervalFactor OBJECT-TYPE
      SYNTAX      INTEGER
      MAX-ACCESS  read-only
      STATUS      current
      DESCRIPTION "Generated Object."
      ::= { snmpAgentEntry 24  }
   
   
   snmpAgentSNMPPort OBJECT-TYPE
      SYNTAX      INTEGER
      MAX-ACCESS  read-only
      STATUS      current
      DESCRIPTION "Generated Object."
      ::= { snmpAgentEntry 25  }
   
   
   snmpAgentSNMPTrapVersion OBJECT-TYPE
      SYNTAX      INTEGER
      MAX-ACCESS  read-only
      STATUS      current
      DESCRIPTION "Generated Object."
      ::= { snmpAgentEntry 26  }
   
   
   snmpAgentEnabled OBJECT-TYPE
      SYNTAX      INTEGER
      MAX-ACCESS  read-only
      STATUS      current
      DESCRIPTION "Generated Object."
      ::= { snmpAgentEntry 27  }
   
   
   snmpAgentSendAutomaticTrapsEnabled OBJECT-TYPE
      SYNTAX      INTEGER
      MAX-ACCESS  read-only
      STATUS      current
      DESCRIPTION "Generated Object."
      ::= { snmpAgentEntry 28  }
   
   
   sslTable OBJECT-TYPE
      SYNTAX      SEQUENCE OF SslEntry
      MAX-ACCESS  not-accessible
      STATUS      current
      DESCRIPTION "This table represents a ssl in the domain."
      ::= { wls 745  }
      
   
   sslEntry OBJECT-TYPE
      SYNTAX      SslEntry
      MAX-ACCESS  not-accessible
      STATUS      current
      DESCRIPTION "Entry of sslTable"
      INDEX { sslIndex}
      ::= { sslTable 1 }
      
   SslEntry ::=
      SEQUENCE
      {
         sslIndex             DisplayString (SIZE (1..16)),
         sslObjectName        DisplayString (SIZE (1..256)),
         sslType              DisplayString (SIZE (1..64)),
         sslName              DisplayString (SIZE (1..64)),
         sslParent            DisplayString (SIZE (1..256)),
         sslExportKeyLifespan INTEGER,
         sslHostnameVerifier  DisplayString,
         sslIdentityAndTrustLocations DisplayString,
         sslListenPort        INTEGER,
         sslLoginTimeoutMillis INTEGER,
         sslServerCertificateChainFileName DisplayString,
         sslServerCertificateFileName DisplayString,
         sslServerPrivateKeyAlias DisplayString,
         sslClientCertificateEnforced INTEGER,
         sslEnabled           INTEGER,
         sslHostnameVerificationIgnored INTEGER,
         sslSSLRejectionLoggingEnabled INTEGER,
         sslTwoWaySSLEnabled  INTEGER,
         sslOutboundCertificateValidation OCTET STRING,
         sslInboundCertificateValidation OCTET STRING,
         sslCertAuthenticator OCTET STRING,
         sslUseServerCerts    OCTET STRING,
         sslAllowUnencryptedNullCipher OCTET STRING
      }
      
   
   sslIndex OBJECT-TYPE
      SYNTAX      DisplayString (SIZE (1..16))
      MAX-ACCESS  read-only
      STATUS      current
      DESCRIPTION "Unique value directed from ObjectName which is used as table index"
      ::= { sslEntry 1  }
   
   
   sslObjectName OBJECT-TYPE
      SYNTAX      DisplayString (SIZE (1..256))
      MAX-ACCESS  read-only
      STATUS      current
      DESCRIPTION "JMX-standard MBean name"
      ::= { sslEntry 5  }
   
   
   sslType OBJECT-TYPE
      SYNTAX      DisplayString (SIZE (1..64))
      MAX-ACCESS  read-only
      STATUS      current
      DESCRIPTION "BEA-proprietary MBean type"
      ::= { sslEntry 10  }
   
   
   sslName OBJECT-TYPE
      SYNTAX      DisplayString (SIZE (1..64))
      MAX-ACCESS  read-only
      STATUS      current
      DESCRIPTION "BEA-proprietary MBean name"
      ::= { sslEntry 15  }
   
   
   sslParent OBJECT-TYPE
      SYNTAX      DisplayString (SIZE (1..256))
      MAX-ACCESS  read-only
      STATUS      current
      DESCRIPTION "BEA-proprietary Parent object's identification, with syntax
      <type>:<name>"
      ::= { sslEntry 20  }
   
   
   sslExportKeyLifespan OBJECT-TYPE
      SYNTAX      INTEGER
      MAX-ACCESS  read-only
      STATUS      current
      DESCRIPTION "Generated Object."
      ::= { sslEntry 23  }
   
   
   sslHostnameVerifier OBJECT-TYPE
      SYNTAX      DisplayString
      MAX-ACCESS  read-only
      STATUS      current
      DESCRIPTION "Generated Object."
      ::= { sslEntry 24  }
   
   
   sslIdentityAndTrustLocations OBJECT-TYPE
      SYNTAX      DisplayString
      MAX-ACCESS  read-only
      STATUS      current
      DESCRIPTION "Generated Object."
      ::= { sslEntry 25  }
   
   
   sslListenPort OBJECT-TYPE
      SYNTAX      INTEGER
      MAX-ACCESS  read-only
      STATUS      current
      DESCRIPTION "Generated Object."
      ::= { sslEntry 26  }
   
   
   sslLoginTimeoutMillis OBJECT-TYPE
      SYNTAX      INTEGER
      MAX-ACCESS  read-only
      STATUS      current
      DESCRIPTION "Generated Object."
      ::= { sslEntry 27  }
   
   
   sslServerCertificateChainFileName OBJECT-TYPE
      SYNTAX      DisplayString
      MAX-ACCESS  read-only
      STATUS      current
      DESCRIPTION "Generated Object."
      ::= { sslEntry 28  }
   
   
   sslServerCertificateFileName OBJECT-TYPE
      SYNTAX      DisplayString
      MAX-ACCESS  read-only
      STATUS      current
      DESCRIPTION "Generated Object."
      ::= { sslEntry 29  }
   
   
   sslServerPrivateKeyAlias OBJECT-TYPE
      SYNTAX      DisplayString
      MAX-ACCESS  read-only
      STATUS      current
      DESCRIPTION "Generated Object."
      ::= { sslEntry 30  }
   
   
   sslClientCertificateEnforced OBJECT-TYPE
      SYNTAX      INTEGER
      MAX-ACCESS  read-only
      STATUS      current
      DESCRIPTION "Generated Object."
      ::= { sslEntry 31  }
   
   
   sslEnabled OBJECT-TYPE
      SYNTAX      INTEGER
      MAX-ACCESS  read-only
      STATUS      current
      DESCRIPTION "Generated Object."
      ::= { sslEntry 32  }
   
   
   sslHostnameVerificationIgnored OBJECT-TYPE
      SYNTAX      INTEGER
      MAX-ACCESS  read-only
      STATUS      current
      DESCRIPTION "Generated Object."
      ::= { sslEntry 33  }
   
   
   sslSSLRejectionLoggingEnabled OBJECT-TYPE
      SYNTAX      INTEGER
      MAX-ACCESS  read-only
      STATUS      current
      DESCRIPTION "Generated Object."
      ::= { sslEntry 35  }
   
   
   sslTwoWaySSLEnabled OBJECT-TYPE
      SYNTAX      INTEGER
      MAX-ACCESS  read-only
      STATUS      current
      DESCRIPTION "Generated Object."
      ::= { sslEntry 36  }
   
   
   sslOutboundCertificateValidation OBJECT-TYPE
      SYNTAX      OCTET STRING
      MAX-ACCESS  read-only
      STATUS      current
      DESCRIPTION "Indicates the server certificate validation rules for outbound SSL.  This attribute always applies to outbound SSL that is part of WebLogic Server (that is, an Administration Server talking to the Node Manager). It does not apply to application code in the server that is using outbound SSL unless the application code uses a weblogic.security.SSL.ServerTrustManager that is configured to use outbound SSL validation."
      ::= { sslEntry 37  }
   
   
   sslInboundCertificateValidation OBJECT-TYPE
      SYNTAX      OCTET STRING
      MAX-ACCESS  read-only
      STATUS      current
      DESCRIPTION "Indicates the client certificate validation rules for inbound SSL.  This attribute only applies to ports and network channels using 2-way SSL."
      ::= { sslEntry 38  }
   
   
   sslCertAuthenticator OBJECT-TYPE
      SYNTAX      OCTET STRING
      MAX-ACCESS  read-only
      STATUS      current
      DESCRIPTION "The name of the Java class that implements the weblogic.security.acl.CertAuthenticator class, which is deprecated in this release of WebLogic Server. This field is for Compatibility security only, and is only used when the Realm Adapter Authentication provider is configured.  The weblogic.security.acl.CertAuthenticator class maps the digital certificate of a client to a WebLogic Server user. The class has an authenticate() method that WebLogic Server calls after validating the digital certificate presented by the client."
      ::= { sslEntry 39  }
   
   
   sslUseServerCerts OBJECT-TYPE
      SYNTAX      OCTET STRING
      MAX-ACCESS  read-only
      STATUS      current
      DESCRIPTION "Sets whether the client should use the server certificates/key as the client identity when initiating a connection over https. "
      ::= { sslEntry 40  }
   
   
   sslAllowUnencryptedNullCipher OBJECT-TYPE
      SYNTAX      OCTET STRING
      MAX-ACCESS  read-only
      STATUS      current
      DESCRIPTION "Test if the AllowUnEncryptedNullCipher is enabled see setAllowUnencryptedNullCipher(boolean enable) for the NullCipher feature. "
      ::= { sslEntry 41  }
   
   
   startupClassTable OBJECT-TYPE
      SYNTAX      SEQUENCE OF StartupClassEntry
      MAX-ACCESS  not-accessible
      STATUS      current
      DESCRIPTION "Generated SNMP Table."
      ::= { wls 750  }
      
   
   startupClassEntry OBJECT-TYPE
      SYNTAX      StartupClassEntry
      MAX-ACCESS  not-accessible
      STATUS      current
      DESCRIPTION "Entry of startupClassTable"
      INDEX { startupClassIndex}
      ::= { startupClassTable 1 }
      
   StartupClassEntry ::=
      SEQUENCE
      {
         startupClassIndex    DisplayString (SIZE (1..16)),
         startupClassObjectName DisplayString (SIZE (1..256)),
         startupClassType     DisplayString (SIZE (1..64)),
         startupClassName     DisplayString (SIZE (1..64)),
         startupClassParent   DisplayString (SIZE (1..256)),
         startupClassFailureIsFatal INTEGER
                     {
                        true(1),
                        false(2)
                     }
         ,
         startupClassDeploymentOrder INTEGER,
         startupClassLoadBeforeAppDeployments OCTET STRING,
         startupClassArguments OCTET STRING,
         startupClassClassName OCTET STRING,
         startupClassLoadBeforeAppActivation OCTET STRING
      }
      
   
   startupClassIndex OBJECT-TYPE
      SYNTAX      DisplayString (SIZE (1..16))
      MAX-ACCESS  read-only
      STATUS      current
      DESCRIPTION "Unique value directed from ObjectName which is used as table index"
      ::= { startupClassEntry 1  }
   
   
   startupClassObjectName OBJECT-TYPE
      SYNTAX      DisplayString (SIZE (1..256))
      MAX-ACCESS  read-only
      STATUS      current
      DESCRIPTION "JMX-standard MBean name"
      ::= { startupClassEntry 5  }
   
   
   startupClassType OBJECT-TYPE
      SYNTAX      DisplayString (SIZE (1..64))
      MAX-ACCESS  read-only
      STATUS      current
      DESCRIPTION "BEA-proprietary MBean type"
      ::= { startupClassEntry 10  }
   
   
   startupClassName OBJECT-TYPE
      SYNTAX      DisplayString (SIZE (1..64))
      MAX-ACCESS  read-only
      STATUS      current
      DESCRIPTION "BEA-proprietary MBean name"
      ::= { startupClassEntry 15  }
   
   
   startupClassParent OBJECT-TYPE
      SYNTAX      DisplayString (SIZE (1..256))
      MAX-ACCESS  read-only
      STATUS      current
      DESCRIPTION "BEA-proprietary Parent object's identification, with syntax
      <type>:<name>"
      ::= { startupClassEntry 20  }
   
   
   startupClassFailureIsFatal OBJECT-TYPE
      SYNTAX      INTEGER
                  {
                     true(1),
                     false(2)
                  }
      
      MAX-ACCESS  read-only
      STATUS      current
      DESCRIPTION "A boolean value (true Or false)."
      ::= { startupClassEntry 25  }
   
   
   startupClassDeploymentOrder OBJECT-TYPE
      SYNTAX      INTEGER
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { startupClassEntry 26  }
   
   
   startupClassLoadBeforeAppDeployments OBJECT-TYPE
      SYNTAX      OCTET STRING
      MAX-ACCESS  read-only
      STATUS      current
      DESCRIPTION "Specifies whether the targeted servers load and run this startup class before activating JMS and JDBC services and before starting deployment for applications and EJBs.  If you enable this feature for a startup class, a server loads and runs the startup class before the deployment prepare phase. At this point, JMS and JDBC services are not yet available. (Deployment for applications and EJBs consists of two phases: prepare and activate.)  If you do not enable this feature, a server instance loads the startup class after it activates JMS and JDBC services, EJBs, and applications."
      ::= { startupClassEntry 27  }
   
   
   startupClassArguments OBJECT-TYPE
      SYNTAX      OCTET STRING
      MAX-ACCESS  read-only
      STATUS      current
      DESCRIPTION "Arguments that a server uses to initialize a class.  Separate multiple arguments with a comma. For example: first=MyFirstName,last=MyLastName"
      ::= { startupClassEntry 28  }
   
   
   startupClassClassName OBJECT-TYPE
      SYNTAX      OCTET STRING
      MAX-ACCESS  read-only
      STATUS      current
      DESCRIPTION "The fully qualified name of a class to load and run. The class must be on the server's classpath.  For example, mycompany.mypackage.myclass"
      ::= { startupClassEntry 29  }
   
   
   startupClassLoadBeforeAppActivation OBJECT-TYPE
      SYNTAX      OCTET STRING
      MAX-ACCESS  read-only
      STATUS      current
      DESCRIPTION "Specifies whether the targeted servers load and run this startup class after activating JMS and JDBC services and before activating applications and EJBs.  If you enable this feature for a startup class, a server loads and runs the startup class before the activate phase. At this point, JMS and JDBC services are available. (Deployment for applications and EJBs consists of two phases: prepare and activate.)  Enable this feature if the startup class needs to be invoked after JDBC connection pools are available but before the applications are activated and ready to service client requests.  If you do not enable this feature, a server instance loads startup classes after it activates JMS and JDBC services, EJBs, and applications."
      ::= { startupClassEntry 30  }
   
   
   webAppComponentTable OBJECT-TYPE
      SYNTAX      SEQUENCE OF WebAppComponentEntry
      MAX-ACCESS  not-accessible
      STATUS      current
      DESCRIPTION "This table describes web module of an application."
      ::= { wls 760  }
      
   
   webAppComponentEntry OBJECT-TYPE
      SYNTAX      WebAppComponentEntry
      MAX-ACCESS  not-accessible
      STATUS      current
      DESCRIPTION "Entry of webAppComponentTable"
      INDEX { webAppComponentIndex}
      ::= { webAppComponentTable 1 }
      
   WebAppComponentEntry ::=
      SEQUENCE
      {
         webAppComponentIndex DisplayString (SIZE (1..16)),
         webAppComponentObjectName DisplayString (SIZE (1..256)),
         webAppComponentType  DisplayString (SIZE (1..64)),
         webAppComponentName  DisplayString (SIZE (1..64)),
         webAppComponentParent DisplayString (SIZE (1..256)),
         webAppComponentApplication DisplayString (SIZE (1..256)),
         webAppComponentURI   DisplayString (SIZE (1..256)),
         webAppComponentWebServers DisplayString (SIZE (1..256)),
         webAppComponentIndexDirectoryEnabled INTEGER
                     {
                        true(1),
                        false(2)
                     }
         ,
         webAppComponentServletExtensionCaseSensitive INTEGER
                     {
                        true(1),
                        false(2)
                     }
         ,
         webAppComponentServletReloadCheckSecs INTEGER,
         webAppComponentSingleThreadedServletPoolSize INTEGER,
         webAppComponentAuthRealmName DisplayString (SIZE (1..64))
      }
      
   
   webAppComponentIndex OBJECT-TYPE
      SYNTAX      DisplayString (SIZE (1..16))
      MAX-ACCESS  read-only
      STATUS      current
      DESCRIPTION "Unique value directed from ObjectName which is used as table index"
      ::= { webAppComponentEntry 1  }
   
   
   webAppComponentObjectName OBJECT-TYPE
      SYNTAX      DisplayString (SIZE (1..256))
      MAX-ACCESS  read-only
      STATUS      current
      DESCRIPTION "JMX-standard MBean name"
      ::= { webAppComponentEntry 5  }
   
   
   webAppComponentType OBJECT-TYPE
      SYNTAX      DisplayString (SIZE (1..64))
      MAX-ACCESS  read-only
      STATUS      current
      DESCRIPTION "BEA-proprietary MBean type"
      ::= { webAppComponentEntry 10  }
   
   
   webAppComponentName OBJECT-TYPE
      SYNTAX      DisplayString (SIZE (1..64))
      MAX-ACCESS  read-only
      STATUS      current
      DESCRIPTION "BEA-proprietary MBean name"
      ::= { webAppComponentEntry 15  }
   
   
   webAppComponentParent OBJECT-TYPE
      SYNTAX      DisplayString (SIZE (1..256))
      MAX-ACCESS  read-only
      STATUS      current
      DESCRIPTION "BEA-proprietary Parent object's identification, with syntax
      <type>:<name>"
      ::= { webAppComponentEntry 20  }
   
   
   webAppComponentApplication OBJECT-TYPE
      SYNTAX      DisplayString (SIZE (1..256))
      MAX-ACCESS  read-only
      STATUS      current
      DESCRIPTION "The application this component is a part of. 
      This is guaranteed to never be null."
      ::= { webAppComponentEntry 25  }
   
   
   webAppComponentURI OBJECT-TYPE
      SYNTAX      DisplayString (SIZE (1..256))
      MAX-ACCESS  read-only
      STATUS      current
      DESCRIPTION "A URI pointing to the application component, usually on the Admin Server."
      ::= { webAppComponentEntry 30  }
   
   
   webAppComponentWebServers OBJECT-TYPE
      SYNTAX      DisplayString (SIZE (1..256))
      MAX-ACCESS  read-only
      STATUS      current
      DESCRIPTION "targets on which this deployment is deployed."
      ::= { webAppComponentEntry 35  }
   
   
   webAppComponentIndexDirectoryEnabled OBJECT-TYPE
      SYNTAX      INTEGER
                  {
                     true(1),
                     false(2)
                  }
      
      MAX-ACCESS  read-only
      STATUS      current
      DESCRIPTION "boolean value (true Or false). Return whether or not to automatically generate an HTML
      directory listing if false suitable index file is found"
      ::= { webAppComponentEntry 40  }
   
   
   webAppComponentServletExtensionCaseSensitive OBJECT-TYPE
      SYNTAX      INTEGER
                  {
                     true(1),
                     false(2)
                  }
      
      MAX-ACCESS  read-only
      STATUS      current
      DESCRIPTION "boolean value (true Or false)."
      ::= { webAppComponentEntry 45  }
   
   
   webAppComponentServletReloadCheckSecs OBJECT-TYPE
      SYNTAX      INTEGER
      MAX-ACCESS  read-only
      STATUS      current
      DESCRIPTION "How often WebLogic checks whether a servlet has been
      modified, and if so reloads it. -1                                is never reload, 0 is 
      always reload"
      ::= { webAppComponentEntry 50  }
   
   
   webAppComponentSingleThreadedServletPoolSize OBJECT-TYPE
      SYNTAX      INTEGER
      MAX-ACCESS  read-only
      STATUS      current
      DESCRIPTION "The size of the pool used for SingleThreadModle instance
      pools."
      ::= { webAppComponentEntry 55  }
   
   
   webAppComponentAuthRealmName OBJECT-TYPE
      SYNTAX      DisplayString (SIZE (1..64))
      MAX-ACCESS  read-only
      STATUS      current
      DESCRIPTION "The Realm in the Basic Authentication 
      HTTP dialog box which pops up on the browsers"
      ::= { webAppComponentEntry 60  }
   
   
   webServerTable OBJECT-TYPE
      SYNTAX      SEQUENCE OF WebServerEntry
      MAX-ACCESS  not-accessible
      STATUS      current
      DESCRIPTION "This table epresents the configuration of virtual web server within
      a WebLogic server. Note that a server may define multiple web
      servers to support virtual hosts."
      ::= { wls 770  }
      
   
   webServerEntry OBJECT-TYPE
      SYNTAX      WebServerEntry
      MAX-ACCESS  not-accessible
      STATUS      current
      DESCRIPTION "Entry of webServerTable"
      INDEX { webServerIndex}
      ::= { webServerTable 1 }
      
   WebServerEntry ::=
      SEQUENCE
      {
         webServerIndex       DisplayString (SIZE (1..16)),
         webServerObjectName  DisplayString (SIZE (1..256)),
         webServerType        DisplayString (SIZE (1..64)),
         webServerName        DisplayString (SIZE (1..64)),
         webServerParent      DisplayString (SIZE (1..256)),
         webServerTargets     DisplayString (SIZE (1..2048)),
         webServerLoggingEnabled INTEGER
                     {
                        true(1),
                        false(2)
                     }
         ,
         webServerLogFileFormat DisplayString (SIZE (1..32)),
         webServerLogFileBufferKBytes INTEGER,
         webServerMaxLogFileSizeKBytes INTEGER,
         webServerLogRotationPeriodMins INTEGER,
         webServerLogFileFlushSecs INTEGER,
         webServerLogRotationTimeBegin DisplayString (SIZE (1..32)),
         webServerKeepAliveEnabled INTEGER
                     {
                        true(1),
                        false(2)
                     }
         ,
         webServerKeepAliveSecs INTEGER,
         webServerHttpsKeepAliveSecs INTEGER,
         webServerPostTimeoutSecs INTEGER,
         webServerMaxPostTimeSecs INTEGER,
         webServerMaxPostSize INTEGER,
         webServerDefaultWebApp DisplayString (SIZE (1..256)),
         webServerCharsets    DisplayString (SIZE (1..2048)),
         webServerWAPEnabled  INTEGER
                     {
                        true(1),
                        false(2)
                     }
         ,
         webServerURLResource DisplayString (SIZE (1..256))
      }
      
   
   webServerIndex OBJECT-TYPE
      SYNTAX      DisplayString (SIZE (1..16))
      MAX-ACCESS  read-only
      STATUS      current
      DESCRIPTION "Unique value directed from ObjectName which is used as table index"
      ::= { webServerEntry 1  }
   
   
   webServerObjectName OBJECT-TYPE
      SYNTAX      DisplayString (SIZE (1..256))
      MAX-ACCESS  read-only
      STATUS      current
      DESCRIPTION "JMX-standard MBean name"
      ::= { webServerEntry 5  }
   
   
   webServerType OBJECT-TYPE
      SYNTAX      DisplayString (SIZE (1..64))
      MAX-ACCESS  read-only
      STATUS      current
      DESCRIPTION "BEA-proprietary MBean type"
      ::= { webServerEntry 10  }
   
   
   webServerName OBJECT-TYPE
      SYNTAX      DisplayString (SIZE (1..64))
      MAX-ACCESS  read-only
      STATUS      current
      DESCRIPTION "BEA-proprietary MBean name"
      ::= { webServerEntry 15  }
   
   
   webServerParent OBJECT-TYPE
      SYNTAX      DisplayString (SIZE (1..256))
      MAX-ACCESS  read-only
      STATUS      current
      DESCRIPTION "BEA-proprietary Parent object's identification, with syntax
      <type>:<name>"
      ::= { webServerEntry 20  }
   
   
   webServerTargets OBJECT-TYPE
      SYNTAX      DisplayString (SIZE (1..2048))
      MAX-ACCESS  read-only
      STATUS      current
      DESCRIPTION "targets on which this deployment is deployed."
      ::= { webServerEntry 25  }
   
   
   webServerLoggingEnabled OBJECT-TYPE
      SYNTAX      INTEGER
                  {
                     true(1),
                     false(2)
                  }
      
      MAX-ACCESS  read-only
      STATUS      current
      DESCRIPTION "A boolean value (true Or false). Enables logging of HTTP requests."
      ::= { webServerEntry 30  }
   
   
   webServerLogFileFormat OBJECT-TYPE
      SYNTAX      DisplayString (SIZE (1..32))
      MAX-ACCESS  read-only
      STATUS      current
      DESCRIPTION "The format of HTTP log file (common or extended)"
      ::= { webServerEntry 35  }
   
   
   webServerLogFileBufferKBytes OBJECT-TYPE
      SYNTAX      INTEGER
      MAX-ACCESS  read-only
      STATUS      current
      DESCRIPTION "HTTP request log buffer size"
      ::= { webServerEntry 45  }
   
   
   webServerMaxLogFileSizeKBytes OBJECT-TYPE
      SYNTAX      INTEGER
      MAX-ACCESS  read-only
      STATUS      current
      DESCRIPTION "maximum access logfile size in K before rotation. 0 means false limit."
      ::= { webServerEntry 50  }
   
   
   webServerLogRotationPeriodMins OBJECT-TYPE
      SYNTAX      INTEGER
      MAX-ACCESS  read-only
      STATUS      current
      DESCRIPTION "Defines the period in minutes when the access.log will be rotated."
      ::= { webServerEntry 60  }
   
   
   webServerLogFileFlushSecs OBJECT-TYPE
      SYNTAX      INTEGER
      MAX-ACCESS  read-only
      STATUS      current
      DESCRIPTION "Frequency (seconds) with which the log file should be flushed"
      ::= { webServerEntry 65  }
   
   
   webServerLogRotationTimeBegin OBJECT-TYPE
      SYNTAX      DisplayString (SIZE (1..32))
      MAX-ACCESS  read-only
      STATUS      current
      DESCRIPTION "Defines the date when the first rotation of access.log will
      begin.  The format follows java.text.SimpleDateFormat,
      MM-dd-yyyy-k:mm:ss"
      ::= { webServerEntry 70  }
   
   
   webServerKeepAliveEnabled OBJECT-TYPE
      SYNTAX      INTEGER
                  {
                     true(1),
                     false(2)
                  }
      
      MAX-ACCESS  read-only
      STATUS      current
      DESCRIPTION "A boolean value (true Or false). Returns whether or not HTTP keep-alive is enabled"
      ::= { webServerEntry 75  }
   
   
   webServerKeepAliveSecs OBJECT-TYPE
      SYNTAX      INTEGER
      MAX-ACCESS  read-only
      STATUS      current
      DESCRIPTION "Number of seconds to maintain HTTP keep-alive before timing out the 
      request."
      ::= { webServerEntry 80  }
   
   
   webServerHttpsKeepAliveSecs OBJECT-TYPE
      SYNTAX      INTEGER
      MAX-ACCESS  read-only
      STATUS      current
      DESCRIPTION "Number of seconds to maintain HTTPS keep-alive before timing out the
      request."
      ::= { webServerEntry 85  }
   
   
   webServerPostTimeoutSecs OBJECT-TYPE
      SYNTAX      INTEGER
      MAX-ACCESS  read-only
      STATUS      current
      DESCRIPTION "Timeout (in seconds) for reading HTTP POST data in a servlet request."
      ::= { webServerEntry 90  }
   
   
   webServerMaxPostTimeSecs OBJECT-TYPE
      SYNTAX      INTEGER
      MAX-ACCESS  read-only
      STATUS      current
      DESCRIPTION "Max Post Time (in seconds) for reading HTTP POST data in a servlet request."
      ::= { webServerEntry 95  }
   
   
   webServerMaxPostSize OBJECT-TYPE
      SYNTAX      INTEGER
      MAX-ACCESS  read-only
      STATUS      current
      DESCRIPTION "Max Post Size for reading HTTP POST data in a servlet request."
      ::= { webServerEntry 100  }
   
   
   webServerDefaultWebApp OBJECT-TYPE
      SYNTAX      DisplayString (SIZE (1..256))
      MAX-ACCESS  read-only
      STATUS      current
      DESCRIPTION "Servlet 2.2 Web Application that maps to the default servlet
      context (where ContextPath = /)"
      ::= { webServerEntry 105  }
   
   
   webServerCharsets OBJECT-TYPE
      SYNTAX      DisplayString (SIZE (1..2048))
      MAX-ACCESS  read-only
      STATUS      current
      DESCRIPTION "User defined mapping between internet and Java charset names"
      ::= { webServerEntry 110  }
   
   
   webServerWAPEnabled OBJECT-TYPE
      SYNTAX      INTEGER
                  {
                     true(1),
                     false(2)
                  }
      
      MAX-ACCESS  read-only
      STATUS      current
      DESCRIPTION "is WAP Enabled."
      ::= { webServerEntry 115  }
   
   
   webServerURLResource OBJECT-TYPE
      SYNTAX      DisplayString (SIZE (1..256))
      MAX-ACCESS  read-only
      STATUS      current
      DESCRIPTION "A URL connection factory resource into JNDI"
      ::= { webServerEntry 125  }
   
   
   wlecConnectionPoolTable OBJECT-TYPE
      SYNTAX      SEQUENCE OF WlecConnectionPoolEntry
      MAX-ACCESS  not-accessible
      STATUS      current
      DESCRIPTION "This table defines a WLEC connection pool."
      ::= { wls 780  }
      
   
   wlecConnectionPoolEntry OBJECT-TYPE
      SYNTAX      WlecConnectionPoolEntry
      MAX-ACCESS  not-accessible
      STATUS      current
      DESCRIPTION "Entry of wlecConnectionPoolTable"
      INDEX { wlecConnectionPoolIndex}
      ::= { wlecConnectionPoolTable 1 }
      
   WlecConnectionPoolEntry ::=
      SEQUENCE
      {
         wlecConnectionPoolIndex DisplayString (SIZE (1..16)),
         wlecConnectionPoolObjectName DisplayString (SIZE (1..256)),
         wlecConnectionPoolType DisplayString (SIZE (1..64)),
         wlecConnectionPoolName DisplayString (SIZE (1..64)),
         wlecConnectionPoolParent DisplayString (SIZE (1..256)),
         wlecConnectionPoolPrimaryAddresses DisplayString (SIZE (1..2048)),
         wlecConnectionPoolFailoverAddresses DisplayString (SIZE (1..2048)),
         wlecConnectionPoolMinimumPoolSize INTEGER,
         wlecConnectionPoolMaximumPoolSize INTEGER,
         wlecConnectionPoolUserName DisplayString (SIZE (1..32)),
         wlecConnectionPoolUserRole DisplayString (SIZE (1..32)),
         wlecConnectionPoolWLEDomain DisplayString (SIZE (1..32)),
         wlecConnectionPoolMinimumEncryptionLevel INTEGER,
         wlecConnectionPoolMaximumEncryptionLevel INTEGER,
         wlecConnectionPoolCertificateAuthenticationEnabled INTEGER
                     {
                        true(1),
                        false(2)
                     }
         ,
         wlecConnectionPoolSecurityContextEnabled INTEGER
                     {
                        true(1),
                        false(2)
                     }
         ,
         wlecConnectionPoolTargets DisplayString (SIZE (1..2048)),
         wlecConnectionPoolDeploymentOrder INTEGER
      }
      
   
   wlecConnectionPoolIndex OBJECT-TYPE
      SYNTAX      DisplayString (SIZE (1..16))
      MAX-ACCESS  read-only
      STATUS      current
      DESCRIPTION "Unique value directed from ObjectName which is used as table index"
      ::= { wlecConnectionPoolEntry 1  }
   
   
   wlecConnectionPoolObjectName OBJECT-TYPE
      SYNTAX      DisplayString (SIZE (1..256))
      MAX-ACCESS  read-only
      STATUS      current
      DESCRIPTION "JMX-standard MBean name"
      ::= { wlecConnectionPoolEntry 5  }
   
   
   wlecConnectionPoolType OBJECT-TYPE
      SYNTAX      DisplayString (SIZE (1..64))
      MAX-ACCESS  read-only
      STATUS      current
      DESCRIPTION "BEA-proprietary MBean type"
      ::= { wlecConnectionPoolEntry 10  }
   
   
   wlecConnectionPoolName OBJECT-TYPE
      SYNTAX      DisplayString (SIZE (1..64))
      MAX-ACCESS  read-only
      STATUS      current
      DESCRIPTION "BEA-proprietary MBean name"
      ::= { wlecConnectionPoolEntry 15  }
   
   
   wlecConnectionPoolParent OBJECT-TYPE
      SYNTAX      DisplayString (SIZE (1..256))
      MAX-ACCESS  read-only
      STATUS      current
      DESCRIPTION "BEA-proprietary Parent object's identification, with syntax
      <type>:<name>"
      ::= { wlecConnectionPoolEntry 20  }
   
   
   wlecConnectionPoolPrimaryAddresses OBJECT-TYPE
      SYNTAX      DisplayString (SIZE (1..2048))
      MAX-ACCESS  read-only
      STATUS      current
      DESCRIPTION "The list of primary ISL addresses."
      ::= { wlecConnectionPoolEntry 25  }
   
   
   wlecConnectionPoolFailoverAddresses OBJECT-TYPE
      SYNTAX      DisplayString (SIZE (1..2048))
      MAX-ACCESS  read-only
      STATUS      current
      DESCRIPTION "The list of failover ISL addresses."
      ::= { wlecConnectionPoolEntry 30  }
   
   
   wlecConnectionPoolMinimumPoolSize OBJECT-TYPE
      SYNTAX      INTEGER
      MAX-ACCESS  read-only
      STATUS      current
      DESCRIPTION "initial number of IIOP connections."
      ::= { wlecConnectionPoolEntry 35  }
   
   
   wlecConnectionPoolMaximumPoolSize OBJECT-TYPE
      SYNTAX      INTEGER
      MAX-ACCESS  read-only
      STATUS      current
      DESCRIPTION "maximum number of IIOP connections."
      ::= { wlecConnectionPoolEntry 40  }
   
   
   wlecConnectionPoolUserName OBJECT-TYPE
      SYNTAX      DisplayString (SIZE (1..32))
      MAX-ACCESS  read-only
      STATUS      current
      DESCRIPTION "WebLogic Enterprise username."
      ::= { wlecConnectionPoolEntry 45  }
   
   
   wlecConnectionPoolUserRole OBJECT-TYPE
      SYNTAX      DisplayString (SIZE (1..32))
      MAX-ACCESS  read-only
      STATUS      current
      DESCRIPTION "WebLogic Enterprise user role."
      ::= { wlecConnectionPoolEntry 50  }
   
   
   wlecConnectionPoolWLEDomain OBJECT-TYPE
      SYNTAX      DisplayString (SIZE (1..32))
      MAX-ACCESS  read-only
      STATUS      current
      DESCRIPTION "name of the WebLogic Enterprise domain."
      ::= { wlecConnectionPoolEntry 55  }
   
   
   wlecConnectionPoolMinimumEncryptionLevel OBJECT-TYPE
      SYNTAX      INTEGER
      MAX-ACCESS  read-only
      STATUS      current
      DESCRIPTION "minimum encryption level."
      ::= { wlecConnectionPoolEntry 60  }
   
   
   wlecConnectionPoolMaximumEncryptionLevel OBJECT-TYPE
      SYNTAX      INTEGER
      MAX-ACCESS  read-only
      STATUS      current
      DESCRIPTION "maximum encryption level."
      ::= { wlecConnectionPoolEntry 65  }
   
   
   wlecConnectionPoolCertificateAuthenticationEnabled OBJECT-TYPE
      SYNTAX      INTEGER
                  {
                     true(1),
                     false(2)
                  }
      
      MAX-ACCESS  read-only
      STATUS      current
      DESCRIPTION "boolean value (true Or false).  Set to true to enable certificate based authentication"
      ::= { wlecConnectionPoolEntry 70  }
   
   
   wlecConnectionPoolSecurityContextEnabled OBJECT-TYPE
      SYNTAX      INTEGER
                  {
                     true(1),
                     false(2)
                  }
      
      MAX-ACCESS  read-only
      STATUS      current
      DESCRIPTION "boolean value (true Or false). Set to true to enable security context propagation."
      ::= { wlecConnectionPoolEntry 75  }
   
   
   wlecConnectionPoolTargets OBJECT-TYPE
      SYNTAX      DisplayString (SIZE (1..2048))
      MAX-ACCESS  read-only
      STATUS      current
      DESCRIPTION "targets on which this deployment is deployed."
      ::= { wlecConnectionPoolEntry 80  }
   
   
   wlecConnectionPoolDeploymentOrder OBJECT-TYPE
      SYNTAX      INTEGER
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { wlecConnectionPoolEntry 81  }
   
   
   bridgeDestinationTable OBJECT-TYPE
      SYNTAX      SEQUENCE OF BridgeDestinationEntry
      MAX-ACCESS  not-accessible
      STATUS      current
      DESCRIPTION "This table defines a Bridge destination."
      ::= { wls 782  }
      
   
   bridgeDestinationEntry OBJECT-TYPE
      SYNTAX      BridgeDestinationEntry
      MAX-ACCESS  not-accessible
      STATUS      current
      DESCRIPTION "Entry of BridgeDestinationTable"
      INDEX { bridgeDestinationIndex}
      ::= { bridgeDestinationTable 1 }
      
   BridgeDestinationEntry ::=
      SEQUENCE
      {
         bridgeDestinationIndex DisplayString (SIZE (1..16)),
         bridgeDestinationObjectName DisplayString (SIZE (1..256)),
         bridgeDestinationType DisplayString (SIZE (1..64)),
         bridgeDestinationName DisplayString (SIZE (1..64)),
         bridgeDestinationParent DisplayString (SIZE (1..256)),
         bridgeDestinationAdapterJNDIName DisplayString (SIZE (1..256))
      }
      
   
   bridgeDestinationIndex OBJECT-TYPE
      SYNTAX      DisplayString (SIZE (1..16))
      MAX-ACCESS  read-only
      STATUS      current
      DESCRIPTION "Unique value directed from ObjectName which is used as table index"
      ::= { bridgeDestinationEntry 1  }
   
   
   bridgeDestinationObjectName OBJECT-TYPE
      SYNTAX      DisplayString (SIZE (1..256))
      MAX-ACCESS  read-only
      STATUS      current
      DESCRIPTION "JMX-standard MBean name"
      ::= { bridgeDestinationEntry 5  }
   
   
   bridgeDestinationType OBJECT-TYPE
      SYNTAX      DisplayString (SIZE (1..64))
      MAX-ACCESS  read-only
      STATUS      current
      DESCRIPTION "BEA-proprietary MBean type"
      ::= { bridgeDestinationEntry 10  }
   
   
   bridgeDestinationName OBJECT-TYPE
      SYNTAX      DisplayString (SIZE (1..64))
      MAX-ACCESS  read-only
      STATUS      current
      DESCRIPTION "BEA-proprietary MBean name"
      ::= { bridgeDestinationEntry 15  }
   
   
   bridgeDestinationParent OBJECT-TYPE
      SYNTAX      DisplayString (SIZE (1..256))
      MAX-ACCESS  read-only
      STATUS      current
      DESCRIPTION "BEA-proprietary Parent object's identification, with syntax
      <type>:<name>"
      ::= { bridgeDestinationEntry 20  }
   
   
   bridgeDestinationAdapterJNDIName OBJECT-TYPE
      SYNTAX      DisplayString (SIZE (1..256))
      MAX-ACCESS  read-only
      STATUS      current
      DESCRIPTION "Get the JNDI name of the adapter."
      ::= { bridgeDestinationEntry 30  }
   
   
   messagingBridgeTable OBJECT-TYPE
      SYNTAX      SEQUENCE OF MessagingBridgeEntry
      MAX-ACCESS  not-accessible
      STATUS      current
      DESCRIPTION "This table defines defines a Messaging Bridge."
      ::= { wls 786  }
      
   
   messagingBridgeEntry OBJECT-TYPE
      SYNTAX      MessagingBridgeEntry
      MAX-ACCESS  not-accessible
      STATUS      current
      DESCRIPTION "Entry of MessagingBridgeTable"
      INDEX { messagingBridgeIndex}
      ::= { messagingBridgeTable 1 }
      
   MessagingBridgeEntry ::=
      SEQUENCE
      {
         messagingBridgeIndex DisplayString (SIZE (1..16)),
         messagingBridgeObjectName DisplayString (SIZE (1..256)),
         messagingBridgeType  DisplayString (SIZE (1..64)),
         messagingBridgeName  DisplayString (SIZE (1..64)),
         messagingBridgeParent DisplayString (SIZE (1..256)),
         messagingBridgeTargets DisplayString (SIZE (1..2048)),
         messagingBridgeSourceDestination DisplayString (SIZE (1..256)),
         messagingBridgeTargetDestination DisplayString (SIZE (1..256)),
         messagingBridgeSelector DisplayString (SIZE (1..256)),
         messagingBridgeForwardingPolicy DisplayString (SIZE (1..256)),
         messagingBridgeScheduleTime DisplayString (SIZE (1..256)),
         messagingBridgeQualityOfService DisplayString (SIZE (1..256)),
         messagingBridgeIdleTimeMaximum INTEGER,
         messagingBridgeTransactionTimeout INTEGER,
         messagingBridgeAsyncDisabled INTEGER
                     {
                        true(1),
                        false(2)
                     }
         ,
         messagingBridgeQOSDegradationAllowed INTEGER
                     {
                        true(1),
                        false(2)
                     }
         ,
         messagingBridgeDurabilityEnabled OCTET STRING,
         messagingBridgeReconnectDelayMinimum INTEGER,
         messagingBridgePreserveMsgProperty OCTET STRING,
         messagingBridgeBatchSize INTEGER,
         messagingBridgeReconnectDelayMaximum INTEGER,
         messagingBridgeDeploymentOrder INTEGER,
         messagingBridgeAsyncEnabled OCTET STRING,
         messagingBridgeBatchInterval Counter64,
         messagingBridgeStarted OCTET STRING,
         messagingBridgeReconnectDelayIncrease INTEGER
      }
      
   
   messagingBridgeIndex OBJECT-TYPE
      SYNTAX      DisplayString (SIZE (1..16))
      MAX-ACCESS  read-only
      STATUS      current
      DESCRIPTION "Unique value directed from ObjectName which is used as table index"
      ::= { messagingBridgeEntry 1  }
   
   
   messagingBridgeObjectName OBJECT-TYPE
      SYNTAX      DisplayString (SIZE (1..256))
      MAX-ACCESS  read-only
      STATUS      current
      DESCRIPTION "JMX-standard MBean name"
      ::= { messagingBridgeEntry 5  }
   
   
   messagingBridgeType OBJECT-TYPE
      SYNTAX      DisplayString (SIZE (1..64))
      MAX-ACCESS  read-only
      STATUS      current
      DESCRIPTION "BEA-proprietary MBean type"
      ::= { messagingBridgeEntry 10  }
   
   
   messagingBridgeName OBJECT-TYPE
      SYNTAX      DisplayString (SIZE (1..64))
      MAX-ACCESS  read-only
      STATUS      current
      DESCRIPTION "BEA-proprietary MBean name"
      ::= { messagingBridgeEntry 15  }
   
   
   messagingBridgeParent OBJECT-TYPE
      SYNTAX      DisplayString (SIZE (1..256))
      MAX-ACCESS  read-only
      STATUS      current
      DESCRIPTION "BEA-proprietary Parent object's identification, with syntax
      <type>:<name>"
      ::= { messagingBridgeEntry 20  }
   
   
   messagingBridgeTargets OBJECT-TYPE
      SYNTAX      DisplayString (SIZE (1..2048))
      MAX-ACCESS  read-only
      STATUS      current
      DESCRIPTION "targets on which this deployment is deployed."
      ::= { messagingBridgeEntry 25  }
   
   
   messagingBridgeSourceDestination OBJECT-TYPE
      SYNTAX      DisplayString (SIZE (1..256))
      MAX-ACCESS  read-only
      STATUS      current
      DESCRIPTION "The source destination defined for the JMS bridge."
      ::= { messagingBridgeEntry 30  }
   
   
   messagingBridgeTargetDestination OBJECT-TYPE
      SYNTAX      DisplayString (SIZE (1..256))
      MAX-ACCESS  read-only
      STATUS      current
      DESCRIPTION "The target destination defined for the JMS bridge."
      ::= { messagingBridgeEntry 35  }
   
   
   messagingBridgeSelector OBJECT-TYPE
      SYNTAX      DisplayString (SIZE (1..256))
      MAX-ACCESS  read-only
      STATUS      current
      DESCRIPTION "The selector defined for the JMS bridge."
      ::= { messagingBridgeEntry 50  }
   
   
   messagingBridgeForwardingPolicy OBJECT-TYPE
      SYNTAX      DisplayString (SIZE (1..256))
      MAX-ACCESS  read-only
      STATUS      current
      DESCRIPTION "The forwarding policy defined for the JMS bridge."
      ::= { messagingBridgeEntry 55  }
   
   
   messagingBridgeScheduleTime OBJECT-TYPE
      SYNTAX      DisplayString (SIZE (1..256))
      MAX-ACCESS  read-only
      STATUS      current
      DESCRIPTION "The schedule time defined for the JMS bridge."
      ::= { messagingBridgeEntry 60  }
   
   
   messagingBridgeQualityOfService OBJECT-TYPE
      SYNTAX      DisplayString (SIZE (1..256))
      MAX-ACCESS  read-only
      STATUS      current
      DESCRIPTION "The quality of service defined for the JMS bridge."
      ::= { messagingBridgeEntry 70  }
   
   
   messagingBridgeIdleTimeMaximum OBJECT-TYPE
      SYNTAX      INTEGER
      MAX-ACCESS  read-only
      STATUS      current
      DESCRIPTION "The maximum wait time defined for the JMS bridge."
      ::= { messagingBridgeEntry 85  }
   
   
   messagingBridgeTransactionTimeout OBJECT-TYPE
      SYNTAX      INTEGER
      MAX-ACCESS  read-only
      STATUS      current
      DESCRIPTION "The transaction timeout defined for the JMS bridge."
      ::= { messagingBridgeEntry 90  }
   
   
   messagingBridgeAsyncDisabled OBJECT-TYPE
      SYNTAX      INTEGER
                  {
                     true(1),
                     false(2)
                  }
      
      MAX-ACCESS  read-only
      STATUS      current
      DESCRIPTION "Return true, if the Async is Disabled."
      ::= { messagingBridgeEntry 95  }
   
   
   messagingBridgeQOSDegradationAllowed OBJECT-TYPE
      SYNTAX      INTEGER
                  {
                     true(1),
                     false(2)
                  }
      
      MAX-ACCESS  read-only
      STATUS      current
      DESCRIPTION "treu, if QOSDegradation is Allowed."
      ::= { messagingBridgeEntry 100  }
   
   
   messagingBridgeDurabilityEnabled OBJECT-TYPE
      SYNTAX      OCTET STRING
      MAX-ACCESS  read-only
      STATUS      current
      DESCRIPTION "Specifies whether or not the messaging bridge allows durable messages.  When enabled and the source destination is a JMS topic, a messaging bridge instance uses a durable subscription to ensure that no messages are lost in the event of a failure. DurabilityEnabled ignored if the source destination is a JMS queue.    When enabled and the source destination uses durable subscriptions, the source JMS implementation saves messages that are sent when a messaging bridge instance is not running. When the bridge instance is restarted, these messages are forwarded to the target destination. The administrator can choose not to be durable.    When not enabled, messages that are sent to the source JMS implementation while the bridge instance is down cannot be forwarded to the target destination."
      ::= { messagingBridgeEntry 101  }
   
   
   messagingBridgeReconnectDelayMinimum OBJECT-TYPE
      SYNTAX      INTEGER
      MAX-ACCESS  read-only
      STATUS      current
      DESCRIPTION "The minimum amount of time, in seconds, that a messaging bridge instance waits before it tries to reconnect to the source or target destination after a failure.    Use with ReconnectDelayMaximum and ReconnectDelayIncrease. After the first failure to connect to a destination, the bridge instance waits for the number of seconds defined by ReconnectDelayMinimum. Each time a reconnect attempt fails, the bridge instance increases its waiting time by the number of seconds defined by ReconnectDelayIncrease. The maximum delay time is defined by ReconnectDelayMaximum. Once the waiting time is increased to the maximum value, the bridge instance stops increase its waiting time. Once the bridge instance successfully connects to the destination, the bridge instance resets its waiting time to the initial value defined by ReconnectDelayMinimum."
      ::= { messagingBridgeEntry 102  }
   
   
   messagingBridgePreserveMsgProperty OBJECT-TYPE
      SYNTAX      OCTET STRING
      MAX-ACCESS  read-only
      STATUS      current
      DESCRIPTION "Specifies if message properties are preserved when messages are forwarded by a bridge instance.  If the target bridge destination is on wls 9.0 or higher, the following message properties are preserved:    message ID    message timestamp    user ID    delivery mode    priority    expiration time    redelivery limit    unit of order name    If the target bridge destination is on wls between 6.0 and 8.1 or on a foreign JMS server, the following message properties are preserved:    delivery mode    priority    expiration time    If the target bridge destination is on wls 5.1 or older, no properties are preserved."
      ::= { messagingBridgeEntry 103  }
   
   
   messagingBridgeBatchSize OBJECT-TYPE
      SYNTAX      INTEGER
      MAX-ACCESS  read-only
      STATUS      current
      DESCRIPTION "The number of messages that are processed within one transaction.  Batch Size only applies to a messaging bridge instance forwarding messages in synchronous mode and has a QOS (quality of service) that requires two-phase transactions."
      ::= { messagingBridgeEntry 104  }
   
   
   messagingBridgeReconnectDelayMaximum OBJECT-TYPE
      SYNTAX      INTEGER
      MAX-ACCESS  read-only
      STATUS      current
      DESCRIPTION "The longest time, in seconds, that a messaging bridge instance waits between one failed attempt to connect to the source or target, and the next retry.    Use with ReconnectDelayMinimum and ReconnectDelayIncrease. After the first failure to connect to a destination, a bridge instance waits for the number of seconds defined by ReconnectDelayMinimum. Each time a reconnect attempt fails, the bridge instance increases its waiting time by the number of seconds defined by ReconnectDelayIncrease. The maximum delay time is defined by ReconnectDelayMaximum. Once the waiting time is increased to the maximum value, the bridge instance stops increase its waiting time. Once the bridge instance successfully connects to the destination, the bridge instance resets its waiting time to the initial value defined by ReconnectDelayMinimum."
      ::= { messagingBridgeEntry 105  }
   
   
   messagingBridgeDeploymentOrder OBJECT-TYPE
      SYNTAX      INTEGER
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { messagingBridgeEntry 106  }
   
   
   messagingBridgeAsyncEnabled OBJECT-TYPE
      SYNTAX      OCTET STRING
      MAX-ACCESS  read-only
      STATUS      current
      DESCRIPTION "Specifies if a messaging bridge instance forwards in asynchronous messaging mode.  AsyncEnabled only applies to messaging bridge instances whose source destination supports asynchronous receiving. Messaging bridges instances that forward in asynchronous mode are driven by the source destination. A messaging bridge instance listens for messages and forwards them as they arrive. When AsyncEnabled is not selected, a bridge instance is forced to work in synchronous mode, even if the source supports asynchronous receiving.  Note: For a messaging bridge instance with a QOS of Exactly-once to work in asynchronous mode, the source destination has to support the MDBTransaction interface. Otherwise, the bridge automatically switches to synchronous mode if it detects that MDBTransaction is not supported by the source destination."
      ::= { messagingBridgeEntry 107  }
   
   
   messagingBridgeBatchInterval OBJECT-TYPE
      SYNTAX      Counter64
      MAX-ACCESS  read-only
      STATUS      current
      DESCRIPTION "The maximum amount of time, in milliseconds, that a messaging bridge instance waits before sending a batch of messages in one transaction, regardless of whether the Batch Size has been reached or not.    Only applies to a messaging bridge instance forwarding messages in synchronous mode and has a QOS (quality of service) that requires two-phase transactions.    The default value of -1 indicates that the bridge instance waits until the number of messages reaches the Batch Size before it completes a transaction."
      ::= { messagingBridgeEntry 108  }
   
   
   messagingBridgeStarted OBJECT-TYPE
      SYNTAX      OCTET STRING
      MAX-ACCESS  read-only
      STATUS      current
      DESCRIPTION "Specifies the initial operating state of a targetted messaging bridge instance.    If enabled, the messaging bridge instance forwards messages (running).    If not enabled, the messaging bridge instance does not forward messages (temporarily stopped).    After a messaging bridge has started forwarding messages (running), use Started to temporarily suspend an active messaging bridge instance or restart an stopped messaging bridge instance.    Select the Started checkbox to start a messaging bridge instance that has been temporarily stopped.    Clear the Started checkbox to temporarily stop a messaging bridge instance that was running.    This value does not indicate the run-time state of a messaging bridge instance."
      ::= { messagingBridgeEntry 109  }
   
   
   messagingBridgeReconnectDelayIncrease OBJECT-TYPE
      SYNTAX      INTEGER
      MAX-ACCESS  read-only
      STATUS      current
      DESCRIPTION "The incremental delay time, in seconds, that a messaging bridge instance increases its waiting time between one failed reconnection attempt and the next retry.    Use with ReconnectDelayMinimum and ReconnectDelayMaximum. After the first failure to connect to a destination, the bridge instance waits for the number of seconds defined by ReconnectDelayMinimum. Each time a reconnect attempt fails, the bridge instance increases its waiting time by the number of seconds defined by ReconnectDelayIncrease. The maximum delay time is defined by ReconnectDelayMaximum. Once the waiting time is increased to the maximum value, the bridge instance stops increase its waiting time. Once the bridge instance successfully connects to the destination, the bridge instance resets its waiting time to the initial value defined by ReconnectDelayMinimum."
      ::= { messagingBridgeEntry 110  }
   
   
   virtualHostTable OBJECT-TYPE
      SYNTAX      SEQUENCE OF VirtualHostEntry
      MAX-ACCESS  not-accessible
      STATUS      current
      DESCRIPTION "This table epresents the configuration of virtual web server within
      a WebLogic server. Note that a server may define multiple web
      servers to support virtual hosts."
      ::= { wls 790  }
      
   
   virtualHostEntry OBJECT-TYPE
      SYNTAX      VirtualHostEntry
      MAX-ACCESS  not-accessible
      STATUS      current
      DESCRIPTION "Entry of virtualHostTable"
      INDEX { virtualHostIndex}
      ::= { virtualHostTable 1 }
      
   VirtualHostEntry ::=
      SEQUENCE
      {
         virtualHostIndex     DisplayString (SIZE (1..16)),
         virtualHostObjectName DisplayString (SIZE (1..256)),
         virtualHostType      DisplayString (SIZE (1..64)),
         virtualHostName      DisplayString (SIZE (1..64)),
         virtualHostParent    DisplayString (SIZE (1..256)),
         virtualHostTargets   DisplayString (SIZE (1..2048)),
         virtualHostLoggingEnabled INTEGER
                     {
                        true(1),
                        false(2)
                     }
         ,
         virtualHostLogFileFormat DisplayString (SIZE (1..32)),
         virtualHostLogFileName DisplayString (SIZE (1..64)),
         virtualHostLogFileBufferKBytes INTEGER,
         virtualHostMaxLogFileSizeKBytes INTEGER,
         virtualHostLogRotationType DisplayString (SIZE (1..32)),
         virtualHostLogRotationPeriodMins INTEGER,
         virtualHostLogFileFlushSecs INTEGER,
         virtualHostLogRotationTimeBegin DisplayString (SIZE (1..32)),
         virtualHostKeepAliveEnabled INTEGER
                     {
                        true(1),
                        false(2)
                     }
         ,
         virtualHostKeepAliveSecs INTEGER,
         virtualHostHttpsKeepAliveSecs INTEGER,
         virtualHostPostTimeoutSecs INTEGER,
         virtualHostMaxPostTimeSecs INTEGER,
         virtualHostMaxPostSize INTEGER,
         virtualHostDefaultWebApp DisplayString (SIZE (1..256)),
         virtualHostCharsets  DisplayString (SIZE (1..2048)),
         virtualHostWAPEnabled INTEGER
                     {
                        true(1),
                        false(2)
                     }
         ,
         virtualHostURLResource DisplayString (SIZE (1..256)),
         virtualHostVirtualHostNames DisplayString (SIZE (1..256)),
         virtualHostFrontendHTTPPort INTEGER,
         virtualHostAuthCookieEnabled OCTET STRING,
         virtualHostSingleSignonDisabled OCTET STRING,
         virtualHostChunkedTransferDisabled OCTET STRING,
         virtualHostAcceptContextPathInGetRealPath OCTET STRING,
         virtualHostOverloadResponseCode INTEGER,
         virtualHostDeploymentOrder INTEGER,
         virtualHostNetworkAccessPoint OCTET STRING,
         virtualHostSendServerHeaderEnabled OCTET STRING,
         virtualHostFrontendHost OCTET STRING,
         virtualHostWriteChunkBytes INTEGER,
         virtualHostFrontendHTTPSPort INTEGER,
         virtualHostUseHeaderEncoding OCTET STRING,
         virtualHostUseHighestCompatibleHTTPVersion OCTET STRING,
         virtualHostDefaultWebAppContextRoot OCTET STRING
      }
      
   
   virtualHostIndex OBJECT-TYPE
      SYNTAX      DisplayString (SIZE (1..16))
      MAX-ACCESS  read-only
      STATUS      current
      DESCRIPTION "Unique value directed from ObjectName which is used as table index"
      ::= { virtualHostEntry 1  }
   
   
   virtualHostObjectName OBJECT-TYPE
      SYNTAX      DisplayString (SIZE (1..256))
      MAX-ACCESS  read-only
      STATUS      current
      DESCRIPTION "JMX-standard MBean name"
      ::= { virtualHostEntry 5  }
   
   
   virtualHostType OBJECT-TYPE
      SYNTAX      DisplayString (SIZE (1..64))
      MAX-ACCESS  read-only
      STATUS      current
      DESCRIPTION "BEA-proprietary MBean type"
      ::= { virtualHostEntry 10  }
   
   
   virtualHostName OBJECT-TYPE
      SYNTAX      DisplayString (SIZE (1..64))
      MAX-ACCESS  read-only
      STATUS      current
      DESCRIPTION "BEA-proprietary MBean name"
      ::= { virtualHostEntry 15  }
   
   
   virtualHostParent OBJECT-TYPE
      SYNTAX      DisplayString (SIZE (1..256))
      MAX-ACCESS  read-only
      STATUS      current
      DESCRIPTION "BEA-proprietary Parent object's identification, with syntax
      <type>:<name>"
      ::= { virtualHostEntry 20  }
   
   
   virtualHostTargets OBJECT-TYPE
      SYNTAX      DisplayString (SIZE (1..2048))
      MAX-ACCESS  read-only
      STATUS      current
      DESCRIPTION "targets on which this deployment is deployed."
      ::= { virtualHostEntry 25  }
   
   
   virtualHostLoggingEnabled OBJECT-TYPE
      SYNTAX      INTEGER
                  {
                     true(1),
                     false(2)
                  }
      
      MAX-ACCESS  read-only
      STATUS      current
      DESCRIPTION "A boolean value (true Or false). Enables logging of HTTP requests."
      ::= { virtualHostEntry 30  }
   
   
   virtualHostLogFileFormat OBJECT-TYPE
      SYNTAX      DisplayString (SIZE (1..32))
      MAX-ACCESS  read-only
      STATUS      current
      DESCRIPTION "Defines the format of HTTP log file (common or extended)"
      ::= { virtualHostEntry 35  }
   
   
   virtualHostLogFileName OBJECT-TYPE
      SYNTAX      DisplayString (SIZE (1..64))
      MAX-ACCESS  read-only
      STATUS      current
      DESCRIPTION "Sets the HTTP request log file"
      ::= { virtualHostEntry 40  }
   
   
   virtualHostLogFileBufferKBytes OBJECT-TYPE
      SYNTAX      INTEGER
      MAX-ACCESS  read-only
      STATUS      current
      DESCRIPTION "Sets HTTP request log buffer size"
      ::= { virtualHostEntry 45  }
   
   
   virtualHostMaxLogFileSizeKBytes OBJECT-TYPE
      SYNTAX      INTEGER
      MAX-ACCESS  read-only
      STATUS      current
      DESCRIPTION "Set maximum access logfile size in K before rotation. 0 means false limit."
      ::= { virtualHostEntry 50  }
   
   
   virtualHostLogRotationType OBJECT-TYPE
      SYNTAX      DisplayString (SIZE (1..32))
      MAX-ACCESS  read-only
      STATUS      current
      DESCRIPTION "Defines how the HTTP log file is rotated [size|date]."
      ::= { virtualHostEntry 55  }
   
   
   virtualHostLogRotationPeriodMins OBJECT-TYPE
      SYNTAX      INTEGER
      MAX-ACCESS  read-only
      STATUS      current
      DESCRIPTION "Defines the period in minutes when the access.log will be rotated."
      ::= { virtualHostEntry 60  }
   
   
   virtualHostLogFileFlushSecs OBJECT-TYPE
      SYNTAX      INTEGER
      MAX-ACCESS  read-only
      STATUS      current
      DESCRIPTION "Frequency (seconds) with which the log file should be flushed"
      ::= { virtualHostEntry 65  }
   
   
   virtualHostLogRotationTimeBegin OBJECT-TYPE
      SYNTAX      DisplayString (SIZE (1..32))
      MAX-ACCESS  read-only
      STATUS      current
      DESCRIPTION "Defines the date when the first rotation of access.log will
      begin.  The format follows java.text.SimpleDateFormat,
      MM-dd-yyyy-k:mm:ss"
      ::= { virtualHostEntry 70  }
   
   
   virtualHostKeepAliveEnabled OBJECT-TYPE
      SYNTAX      INTEGER
                  {
                     true(1),
                     false(2)
                  }
      
      MAX-ACCESS  read-only
      STATUS      current
      DESCRIPTION "A boolean value (true Or false). Returns whether or not HTTP keep-alive is enabled"
      ::= { virtualHostEntry 75  }
   
   
   virtualHostKeepAliveSecs OBJECT-TYPE
      SYNTAX      INTEGER
      MAX-ACCESS  read-only
      STATUS      current
      DESCRIPTION "Number of seconds to maintain HTTP keep-alive before timing out the 
      request."
      ::= { virtualHostEntry 80  }
   
   
   virtualHostHttpsKeepAliveSecs OBJECT-TYPE
      SYNTAX      INTEGER
      MAX-ACCESS  read-only
      STATUS      current
      DESCRIPTION "Number of seconds to maintain HTTPS keep-alive before timing out the
      request."
      ::= { virtualHostEntry 85  }
   
   
   virtualHostPostTimeoutSecs OBJECT-TYPE
      SYNTAX      INTEGER
      MAX-ACCESS  read-only
      STATUS      current
      DESCRIPTION "Timeout (in seconds) for reading HTTP POST data in a servlet request."
      ::= { virtualHostEntry 90  }
   
   
   virtualHostMaxPostTimeSecs OBJECT-TYPE
      SYNTAX      INTEGER
      MAX-ACCESS  read-only
      STATUS      current
      DESCRIPTION "Max Post Time (in seconds) for reading HTTP POST data in a servlet request."
      ::= { virtualHostEntry 95  }
   
   
   virtualHostMaxPostSize OBJECT-TYPE
      SYNTAX      INTEGER
      MAX-ACCESS  read-only
      STATUS      current
      DESCRIPTION "Max Post Size for reading HTTP POST data in a servlet request."
      ::= { virtualHostEntry 100  }
   
   
   virtualHostDefaultWebApp OBJECT-TYPE
      SYNTAX      DisplayString (SIZE (1..256))
      MAX-ACCESS  read-only
      STATUS      current
      DESCRIPTION "Servlet 2.2 Web Application that maps to the default servlet
      context (where ContextPath = /)"
      ::= { virtualHostEntry 105  }
   
   
   virtualHostCharsets OBJECT-TYPE
      SYNTAX      DisplayString (SIZE (1..2048))
      MAX-ACCESS  read-only
      STATUS      current
      DESCRIPTION "User defined mapping between internet and Java charset names"
      ::= { virtualHostEntry 110  }
   
   
   virtualHostWAPEnabled OBJECT-TYPE
      SYNTAX      INTEGER
                  {
                     true(1),
                     false(2)
                  }
      
      MAX-ACCESS  read-only
      STATUS      current
      DESCRIPTION "is WAP Enabled."
      ::= { virtualHostEntry 115  }
   
   
   virtualHostURLResource OBJECT-TYPE
      SYNTAX      DisplayString (SIZE (1..256))
      MAX-ACCESS  read-only
      STATUS      current
      DESCRIPTION "A URL connection factory resource into JNDI"
      ::= { virtualHostEntry 125  }
   
   
   virtualHostVirtualHostNames OBJECT-TYPE
      SYNTAX      DisplayString (SIZE (1..256))
      MAX-ACCESS  read-only
      STATUS      current
      DESCRIPTION "The host name for which this web server will serve requests."
      ::= { virtualHostEntry 130  }
   
   
   virtualHostFrontendHTTPPort OBJECT-TYPE
      SYNTAX      INTEGER
      MAX-ACCESS  read-only
      STATUS      current
      DESCRIPTION "The name of the HTTP port to which all redirected URLs will be sent. If specified, WebLogic Server will use this value rather than the one in the HOST header.  Sets the frontendHTTPPort Provides a method to ensure that the webapp will always have the correct PORT information, even when the request is coming through a firewall or a proxy. If this parameter is configured, the HOST header will be ignored and the information in this parameter will be used in its place."
      ::= { virtualHostEntry 131  }
   
   
   virtualHostAuthCookieEnabled OBJECT-TYPE
      SYNTAX      OCTET STRING
      MAX-ACCESS  read-only
      STATUS      current
      DESCRIPTION "Whether authcookie feature is enabled or not."
      ::= { virtualHostEntry 132  }
   
   
   virtualHostSingleSignonDisabled OBJECT-TYPE
      SYNTAX      OCTET STRING
      MAX-ACCESS  read-only
      STATUS      current
      DESCRIPTION "Indicates whether the singleSignonDisabled attribute is enabled"
      ::= { virtualHostEntry 133  }
   
   
   virtualHostChunkedTransferDisabled OBJECT-TYPE
      SYNTAX      OCTET STRING
      MAX-ACCESS  read-only
      STATUS      current
      DESCRIPTION "Indicates whether the use of Chunk Transfer-Encoding in HTTP/1.1 is enabled."
      ::= { virtualHostEntry 134  }
   
   
   virtualHostAcceptContextPathInGetRealPath OBJECT-TYPE
      SYNTAX      OCTET STRING
      MAX-ACCESS  read-only
      STATUS      current
      DESCRIPTION "Indicates whether this server allows the inclusion of the context path in the virtual path to context.getRealPath(). (If checked, you cannot use sub directories with the same name as contextPath). This is a compatibility switch that will be deprecated 9.0.0.0 in future releases.  Gets the acceptContextPathInGetRealPath attribute of the WebServerMBean object"
      ::= { virtualHostEntry 135  }
   
   
   virtualHostOverloadResponseCode OBJECT-TYPE
      SYNTAX      INTEGER
      MAX-ACCESS  read-only
      STATUS      current
      DESCRIPTION "Get the response code to be used when an application is overloaded. An application can get overloaded when the number of pending requests has reached the max capacity specified in the WorkManager or when the server is low on memory. The low memory condition is determined using {@link OverloadProtectionMBean#getFreeMemoryPercentLowThreshold()}."
      ::= { virtualHostEntry 136  }
   
   
   virtualHostDeploymentOrder OBJECT-TYPE
      SYNTAX      INTEGER
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { virtualHostEntry 137  }
   
   
   virtualHostNetworkAccessPoint OBJECT-TYPE
      SYNTAX      OCTET STRING
      MAX-ACCESS  read-only
      STATUS      current
      DESCRIPTION "The dedicated server channel name (NetworkAccessPoint) for which this virtual host will serve http request. If the NetworkAccessPoint for a given http request doesn't match any virtual host's NetworkAccessPoint, incoming HOST header will be matched with the VirtualHostNames in order to resolve the right virtual host."
      ::= { virtualHostEntry 138  }
   
   
   virtualHostSendServerHeaderEnabled OBJECT-TYPE
      SYNTAX      OCTET STRING
      MAX-ACCESS  read-only
      STATUS      current
      DESCRIPTION "Indicates whether this server name is sent with the HTTP response. (This is useful for wireless applications where there is limited space for headers.)  Indicates whether this server instance includes its name and WebLogic Server version number in HTTP response headers."
      ::= { virtualHostEntry 139  }
   
   
   virtualHostFrontendHost OBJECT-TYPE
      SYNTAX      OCTET STRING
      MAX-ACCESS  read-only
      STATUS      current
      DESCRIPTION "The name of the host to which all redirected URLs will be sent. If specified, WebLogic Server will use this value rather than the one in the HOST header.  Sets the HTTP frontendHost Provides a method to ensure that the webapp will always have the correct HOST information, even when the request is coming through a firewall or a proxy. If this parameter is configured, the HOST header will be ignored and the information in this parameter will be used in its place."
      ::= { virtualHostEntry 140  }
   
   
   virtualHostWriteChunkBytes OBJECT-TYPE
      SYNTAX      INTEGER
      MAX-ACCESS  read-only
      STATUS      current
      DESCRIPTION "The default size of the blocks to be written to the network layer.  Gets the writeChunkBytes attribute of the WebServerMBean object"
      ::= { virtualHostEntry 141  }
   
   
   virtualHostFrontendHTTPSPort OBJECT-TYPE
      SYNTAX      INTEGER
      MAX-ACCESS  read-only
      STATUS      current
      DESCRIPTION "The name of the secure HTTP port to which all redirected URLs will be sent. If specified, WebLogic Server will use this value rather than the one in the HOST header.  Sets the frontendHTTPSPort Provides a method to ensure that the webapp will always have the correct PORT information, even when the request is coming through a firewall or a proxy. If this parameter is configured, the HOST header will be ignored and the information in this parameter will be used in its place."
      ::= { virtualHostEntry 142  }
   
   
   virtualHostUseHeaderEncoding OBJECT-TYPE
      SYNTAX      OCTET STRING
      MAX-ACCESS  read-only
      STATUS      current
      DESCRIPTION ""
      ::= { virtualHostEntry 143  }
   
   
   virtualHostUseHighestCompatibleHTTPVersion OBJECT-TYPE
      SYNTAX      OCTET STRING
      MAX-ACCESS  read-only
      STATUS      current
      DESCRIPTION "Enables use of the highest compatible HTTP protocol version-string in the response. E.g. HTTP spec suggests that HTTP/1.1 version-string should be used in response to a request using HTTP/1.0. This does not necessarily affect the response format."
      ::= { virtualHostEntry 144  }
   
   
   virtualHostDefaultWebAppContextRoot OBJECT-TYPE
      SYNTAX      OCTET STRING
      MAX-ACCESS  read-only
      STATUS      current
      DESCRIPTION "Returns the original context-root for the default Web application for this Web server. Alternatively, you can use the context-root attributes in application.xml or weblogic.xml to set a default Web application. The context-root for a default Web application is /. If '' (empty string) is specified, the Web server defaults to /."
      ::= { virtualHostEntry 145  }
   
   
   xmlEntityCacheTable OBJECT-TYPE
      SYNTAX      SEQUENCE OF XmlEntityCacheEntry
      MAX-ACCESS  not-accessible
      STATUS      current
      DESCRIPTION "Configures the behavior of JAXP (Java API for XML Parsing) in the server."
      ::= { wls 794  }
      
   
   xmlEntityCacheEntry OBJECT-TYPE
      SYNTAX      XmlEntityCacheEntry
      MAX-ACCESS  not-accessible
      STATUS      current
      DESCRIPTION "Entry of XmlEntityCacheTable"
      INDEX { xmlEntityCacheIndex}
      ::= { xmlEntityCacheTable 1 }
      
   XmlEntityCacheEntry ::=
      SEQUENCE
      {
         xmlEntityCacheIndex  DisplayString (SIZE (1..16)),
         xmlEntityCacheObjectName DisplayString (SIZE (1..256)),
         xmlEntityCacheType   DisplayString (SIZE (1..64)),
         xmlEntityCacheName   DisplayString (SIZE (1..64)),
         xmlEntityCacheParent DisplayString (SIZE (1..256)),
         xmlEntityCacheCacheMemorySize INTEGER,
         xmlEntityCacheCacheDiskSize INTEGER,
         xmlEntityCacheCacheTimeoutInterval INTEGER,
         xmlEntityCacheCacheLocation OCTET STRING,
         xmlEntityCacheMaxSize INTEGER
      }
      
   
   xmlEntityCacheIndex OBJECT-TYPE
      SYNTAX      DisplayString (SIZE (1..16))
      MAX-ACCESS  read-only
      STATUS      current
      DESCRIPTION "Unique value directed from ObjectName which is used as table index"
      ::= { xmlEntityCacheEntry 1  }
   
   
   xmlEntityCacheObjectName OBJECT-TYPE
      SYNTAX      DisplayString (SIZE (1..256))
      MAX-ACCESS  read-only
      STATUS      current
      DESCRIPTION "JMX-standard MBean name"
      ::= { xmlEntityCacheEntry 5  }
   
   
   xmlEntityCacheType OBJECT-TYPE
      SYNTAX      DisplayString (SIZE (1..64))
      MAX-ACCESS  read-only
      STATUS      current
      DESCRIPTION "BEA-proprietary MBean type"
      ::= { xmlEntityCacheEntry 10  }
   
   
   xmlEntityCacheName OBJECT-TYPE
      SYNTAX      DisplayString (SIZE (1..64))
      MAX-ACCESS  read-only
      STATUS      current
      DESCRIPTION "BEA-proprietary MBean name"
      ::= { xmlEntityCacheEntry 15  }
   
   
   xmlEntityCacheParent OBJECT-TYPE
      SYNTAX      DisplayString (SIZE (1..256))
      MAX-ACCESS  read-only
      STATUS      current
      DESCRIPTION "BEA-proprietary Parent object's identification, with syntax
      <type>:<name>"
      ::= { xmlEntityCacheEntry 20  }
   
   
   xmlEntityCacheCacheMemorySize OBJECT-TYPE
      SYNTAX      INTEGER
      MAX-ACCESS  read-only
      STATUS      current
      DESCRIPTION "The memory size in KBytes of the cache."
      ::= { xmlEntityCacheEntry 25  }
   
   
   xmlEntityCacheCacheDiskSize OBJECT-TYPE
      SYNTAX      INTEGER
      MAX-ACCESS  read-only
      STATUS      current
      DESCRIPTION "The disk size in MBytes of the cache."
      ::= { xmlEntityCacheEntry 30  }
   
   
   xmlEntityCacheCacheTimeoutInterval OBJECT-TYPE
      SYNTAX      INTEGER
      MAX-ACCESS  read-only
      STATUS      current
      DESCRIPTION "Return the default timeout interval in seconds for the cache."
      ::= { xmlEntityCacheEntry 35  }
   
   
   xmlEntityCacheCacheLocation OBJECT-TYPE
      SYNTAX      OCTET STRING
      MAX-ACCESS  read-only
      STATUS      current
      DESCRIPTION "Provides the path name for the persistent cache files."
      ::= { xmlEntityCacheEntry 36  }
   
   
   xmlEntityCacheMaxSize OBJECT-TYPE
      SYNTAX      INTEGER
      MAX-ACCESS  read-only
      STATUS      current
      DESCRIPTION "Provides the maximum number of entries that can be stored in the cache at any given time."
      ::= { xmlEntityCacheEntry 37  }
   
   
   xmlEntitySpecRegistryTable OBJECT-TYPE
      SYNTAX      SEQUENCE OF XmlEntitySpecRegistryEntry
      MAX-ACCESS  not-accessible
      STATUS      current
      DESCRIPTION "This is an entry in the XML registry. An XML registry entry is configuration 
      information associated with a particular XML document type. Entries accessed 
      through this interface are used to specify a local instance for a remote 
      entity reference."
      ::= { wls 796  }
      
   
   xmlEntitySpecRegistryEntry OBJECT-TYPE
      SYNTAX      XmlEntitySpecRegistryEntry
      MAX-ACCESS  not-accessible
      STATUS      current
      DESCRIPTION "Entry of XmlEntitySpecRegistryTable"
      INDEX { xmlEntitySpecRegistryIndex}
      ::= { xmlEntitySpecRegistryTable 1 }
      
   XmlEntitySpecRegistryEntry ::=
      SEQUENCE
      {
         xmlEntitySpecRegistryIndex DisplayString (SIZE (1..16)),
         xmlEntitySpecRegistryObjectName DisplayString (SIZE (1..256)),
         xmlEntitySpecRegistryType DisplayString (SIZE (1..64)),
         xmlEntitySpecRegistryName DisplayString (SIZE (1..64)),
         xmlEntitySpecRegistryParent DisplayString (SIZE (1..256)),
         xmlEntitySpecRegistryPublicId DisplayString (SIZE (1..256)),
         xmlEntitySpecRegistrySystemId DisplayString (SIZE (1..256)),
         xmlEntitySpecRegistryEntityURI DisplayString (SIZE (1..256)),
         xmlEntitySpecRegistryWhenToCache DisplayString (SIZE (1..256)),
         xmlEntitySpecRegistryCacheTimeoutInterval INTEGER,
         xmlEntitySpecRegistryHandleEntityInvalidation OCTET STRING
      }
      
   
   xmlEntitySpecRegistryIndex OBJECT-TYPE
      SYNTAX      DisplayString (SIZE (1..16))
      MAX-ACCESS  read-only
      STATUS      current
      DESCRIPTION "Unique value directed from ObjectName which is used as table index"
      ::= { xmlEntitySpecRegistryEntry 1  }
   
   
   xmlEntitySpecRegistryObjectName OBJECT-TYPE
      SYNTAX      DisplayString (SIZE (1..256))
      MAX-ACCESS  read-only
      STATUS      current
      DESCRIPTION "JMX-standard MBean name"
      ::= { xmlEntitySpecRegistryEntry 5  }
   
   
   xmlEntitySpecRegistryType OBJECT-TYPE
      SYNTAX      DisplayString (SIZE (1..64))
      MAX-ACCESS  read-only
      STATUS      current
      DESCRIPTION "BEA-proprietary MBean type"
      ::= { xmlEntitySpecRegistryEntry 10  }
   
   
   xmlEntitySpecRegistryName OBJECT-TYPE
      SYNTAX      DisplayString (SIZE (1..64))
      MAX-ACCESS  read-only
      STATUS      current
      DESCRIPTION "BEA-proprietary MBean name"
      ::= { xmlEntitySpecRegistryEntry 15  }
   
   
   xmlEntitySpecRegistryParent OBJECT-TYPE
      SYNTAX      DisplayString (SIZE (1..256))
      MAX-ACCESS  read-only
      STATUS      current
      DESCRIPTION "BEA-proprietary Parent object's identification, with syntax
      <type>:<name>"
      ::= { xmlEntitySpecRegistryEntry 20  }
   
   
   xmlEntitySpecRegistryPublicId OBJECT-TYPE
      SYNTAX      DisplayString (SIZE (1..256))
      MAX-ACCESS  read-only
      STATUS      current
      DESCRIPTION "The public id of the document type represented by this registry entry."
      ::= { xmlEntitySpecRegistryEntry 25  }
   
   
   xmlEntitySpecRegistrySystemId OBJECT-TYPE
      SYNTAX      DisplayString (SIZE (1..256))
      MAX-ACCESS  read-only
      STATUS      current
      DESCRIPTION "The system id of the document type represented by this registry entry."
      ::= { xmlEntitySpecRegistryEntry 30  }
   
   
   xmlEntitySpecRegistryEntityURI OBJECT-TYPE
      SYNTAX      DisplayString (SIZE (1..256))
      MAX-ACCESS  read-only
      STATUS      current
      DESCRIPTION "Return the location of a local copy of an external entity (e.g., a DTD) 
      that is associated with this registry entry."
      ::= { xmlEntitySpecRegistryEntry 35  }
   
   
   xmlEntitySpecRegistryWhenToCache OBJECT-TYPE
      SYNTAX      DisplayString (SIZE (1..256))
      MAX-ACCESS  read-only
      STATUS      current
      DESCRIPTION "whether to cache this item as soon as possible or wait until it is referenced."
      ::= { xmlEntitySpecRegistryEntry 40  }
   
   
   xmlEntitySpecRegistryCacheTimeoutInterval OBJECT-TYPE
      SYNTAX      INTEGER
      MAX-ACCESS  read-only
      STATUS      current
      DESCRIPTION "Return the default timeout interval in seconds for the cache. ???delgation"
      ::= { xmlEntitySpecRegistryEntry 45  }
   
   
   xmlEntitySpecRegistryHandleEntityInvalidation OBJECT-TYPE
      SYNTAX      OCTET STRING
      MAX-ACCESS  read-only
      STATUS      current
      DESCRIPTION "Whether cached DTD/schema is invalidated when parsing error is encountered. "
      ::= { xmlEntitySpecRegistryEntry 46  }
   
   
   xmlParserSelectRegistryTable OBJECT-TYPE
      SYNTAX      SEQUENCE OF XmlParserSelectRegistryEntry
      MAX-ACCESS  not-accessible
      STATUS      current
      DESCRIPTION "This is an entry in the XML registry. An XML registry entry is configuration 
      information associated with a particular XML document type. Entries accessed 
      through this interface are used to specify a Sax parser and/or document 
      builder of the provided document type."
      ::= { wls 798  }
      
   
   xmlParserSelectRegistryEntry OBJECT-TYPE
      SYNTAX      XmlParserSelectRegistryEntry
      MAX-ACCESS  not-accessible
      STATUS      current
      DESCRIPTION "Entry of XmlParserSelectRegistryTable"
      INDEX { xmlParserSelectRegistryIndex}
      ::= { xmlParserSelectRegistryTable 1 }
      
   XmlParserSelectRegistryEntry ::=
      SEQUENCE
      {
         xmlParserSelectRegistryIndex DisplayString (SIZE (1..16)),
         xmlParserSelectRegistryObjectName DisplayString (SIZE (1..256)),
         xmlParserSelectRegistryType DisplayString (SIZE (1..64)),
         xmlParserSelectRegistryName DisplayString (SIZE (1..64)),
         xmlParserSelectRegistryParent DisplayString (SIZE (1..256)),
         xmlParserSelectRegistryPublicId DisplayString (SIZE (1..256)),
         xmlParserSelectRegistrySystemId DisplayString (SIZE (1..256)),
         xmlParserSelectRegistryRootElementTag DisplayString (SIZE (1..256)),
         xmlParserSelectRegistryDocumentBuilderFactory DisplayString (SIZE (1..256)),
         xmlParserSelectRegistrySAXParserFactory DisplayString (SIZE (1..256)),
         xmlParserSelectRegistryTransformerFactory DisplayString (SIZE (1..256))
      }
      
   
   xmlParserSelectRegistryIndex OBJECT-TYPE
      SYNTAX      DisplayString (SIZE (1..16))
      MAX-ACCESS  read-only
      STATUS      current
      DESCRIPTION "Unique value directed from ObjectName which is used as table index"
      ::= { xmlParserSelectRegistryEntry 1  }
   
   
   xmlParserSelectRegistryObjectName OBJECT-TYPE
      SYNTAX      DisplayString (SIZE (1..256))
      MAX-ACCESS  read-only
      STATUS      current
      DESCRIPTION "JMX-standard MBean name"
      ::= { xmlParserSelectRegistryEntry 5  }
   
   
   xmlParserSelectRegistryType OBJECT-TYPE
      SYNTAX      DisplayString (SIZE (1..64))
      MAX-ACCESS  read-only
      STATUS      current
      DESCRIPTION "BEA-proprietary MBean type"
      ::= { xmlParserSelectRegistryEntry 10  }
   
   
   xmlParserSelectRegistryName OBJECT-TYPE
      SYNTAX      DisplayString (SIZE (1..64))
      MAX-ACCESS  read-only
      STATUS      current
      DESCRIPTION "BEA-proprietary MBean name"
      ::= { xmlParserSelectRegistryEntry 15  }
   
   
   xmlParserSelectRegistryParent OBJECT-TYPE
      SYNTAX      DisplayString (SIZE (1..256))
      MAX-ACCESS  read-only
      STATUS      current
      DESCRIPTION "BEA-proprietary Parent object's identification, with syntax
      <type>:<name>"
      ::= { xmlParserSelectRegistryEntry 20  }
   
   
   xmlParserSelectRegistryPublicId OBJECT-TYPE
      SYNTAX      DisplayString (SIZE (1..256))
      MAX-ACCESS  read-only
      STATUS      current
      DESCRIPTION "The public id of the document type represented by this registry entry."
      ::= { xmlParserSelectRegistryEntry 25  }
   
   
   xmlParserSelectRegistrySystemId OBJECT-TYPE
      SYNTAX      DisplayString (SIZE (1..256))
      MAX-ACCESS  read-only
      STATUS      current
      DESCRIPTION "The system id of the document type represented by this registry entry."
      ::= { xmlParserSelectRegistryEntry 30  }
   
   
   xmlParserSelectRegistryRootElementTag OBJECT-TYPE
      SYNTAX      DisplayString (SIZE (1..256))
      MAX-ACCESS  read-only
      STATUS      current
      DESCRIPTION "The tag name of the document root element of 
      the document type represented by this registry entry."
      ::= { xmlParserSelectRegistryEntry 35  }
   
   
   xmlParserSelectRegistryDocumentBuilderFactory OBJECT-TYPE
      SYNTAX      DisplayString (SIZE (1..256))
      MAX-ACCESS  read-only
      STATUS      current
      DESCRIPTION "Return the class name of the DocumentBuilderFactory that is associated with the registry entry."
      ::= { xmlParserSelectRegistryEntry 40  }
   
   
   xmlParserSelectRegistrySAXParserFactory OBJECT-TYPE
      SYNTAX      DisplayString (SIZE (1..256))
      MAX-ACCESS  read-only
      STATUS      current
      DESCRIPTION "Return the class name of the SAXParserFactory that is associated with the registry entry."
      ::= { xmlParserSelectRegistryEntry 45  }
   
   
   xmlParserSelectRegistryTransformerFactory OBJECT-TYPE
      SYNTAX      DisplayString (SIZE (1..256))
      MAX-ACCESS  read-only
      STATUS      current
      DESCRIPTION "Return the class name of the default TransformerFactory."
      ::= { xmlParserSelectRegistryEntry 50  }
   
   
   xmlRegistryTable OBJECT-TYPE
      SYNTAX      SEQUENCE OF XmlRegistryEntry
      MAX-ACCESS  not-accessible
      STATUS      current
      DESCRIPTION "Configure the behavior of JAXP (Java API for XML Parsing) in the server."
      ::= { wls 800  }
      
   
   xmlRegistryEntry OBJECT-TYPE
      SYNTAX      XmlRegistryEntry
      MAX-ACCESS  not-accessible
      STATUS      current
      DESCRIPTION "Entry of XmlRegistryTable"
      INDEX { xmlRegistryIndex}
      ::= { xmlRegistryTable 1 }
      
   XmlRegistryEntry ::=
      SEQUENCE
      {
         xmlRegistryIndex     DisplayString (SIZE (1..16)),
         xmlRegistryObjectName DisplayString (SIZE (1..256)),
         xmlRegistryType      DisplayString (SIZE (1..64)),
         xmlRegistryName      DisplayString (SIZE (1..64)),
         xmlRegistryParent    DisplayString (SIZE (1..256)),
         xmlRegistryRegistryEntries DisplayString (SIZE (1..2048)),
         xmlRegistryParserSelectRegistryEntries DisplayString (SIZE (1..2048)),
         xmlRegistryEntitySpecRegistryEntries DisplayString (SIZE (1..2048)),
         xmlRegistryDocumentBuilderFactory DisplayString (SIZE (1..256)),
         xmlRegistrySAXParserFactory DisplayString (SIZE (1..256)),
         xmlRegistryTransformerFactory DisplayString (SIZE (1..256)),
         xmlRegistryWhenToCache DisplayString (SIZE (1..256)),
         xmlRegistryHandleEntityInvalidation OCTET STRING
      }
      
   
   xmlRegistryIndex OBJECT-TYPE
      SYNTAX      DisplayString (SIZE (1..16))
      MAX-ACCESS  read-only
      STATUS      current
      DESCRIPTION "Unique value directed from ObjectName which is used as table index"
      ::= { xmlRegistryEntry 1  }
   
   
   xmlRegistryObjectName OBJECT-TYPE
      SYNTAX      DisplayString (SIZE (1..256))
      MAX-ACCESS  read-only
      STATUS      current
      DESCRIPTION "JMX-standard MBean name"
      ::= { xmlRegistryEntry 5  }
   
   
   xmlRegistryType OBJECT-TYPE
      SYNTAX      DisplayString (SIZE (1..64))
      MAX-ACCESS  read-only
      STATUS      current
      DESCRIPTION "BEA-proprietary MBean type"
      ::= { xmlRegistryEntry 10  }
   
   
   xmlRegistryName OBJECT-TYPE
      SYNTAX      DisplayString (SIZE (1..64))
      MAX-ACCESS  read-only
      STATUS      current
      DESCRIPTION "BEA-proprietary MBean name"
      ::= { xmlRegistryEntry 15  }
   
   
   xmlRegistryParent OBJECT-TYPE
      SYNTAX      DisplayString (SIZE (1..256))
      MAX-ACCESS  read-only
      STATUS      current
      DESCRIPTION "BEA-proprietary Parent object's identification, with syntax
      <type>:<name>"
      ::= { xmlRegistryEntry 20  }
   
   
   xmlRegistryRegistryEntries OBJECT-TYPE
      SYNTAX      DisplayString (SIZE (1..2048))
      MAX-ACCESS  read-only
      STATUS      current
      DESCRIPTION "Return the set of registry entries."
      ::= { xmlRegistryEntry 25  }
   
   
   xmlRegistryParserSelectRegistryEntries OBJECT-TYPE
      SYNTAX      DisplayString (SIZE (1..2048))
      MAX-ACCESS  read-only
      STATUS      current
      DESCRIPTION "Return the set of ParserSelect registry entries."
      ::= { xmlRegistryEntry 30  }
   
   
   xmlRegistryEntitySpecRegistryEntries OBJECT-TYPE
      SYNTAX      DisplayString (SIZE (1..2048))
      MAX-ACCESS  read-only
      STATUS      current
      DESCRIPTION "Return the set of EntitySpec registry entries."
      ::= { xmlRegistryEntry 35  }
   
   
   xmlRegistryDocumentBuilderFactory OBJECT-TYPE
      SYNTAX      DisplayString (SIZE (1..256))
      MAX-ACCESS  read-only
      STATUS      current
      DESCRIPTION "Return the class name of the DocumentBuilderFactory that is associated with the registry entry."
      ::= { xmlRegistryEntry 40  }
   
   
   xmlRegistrySAXParserFactory OBJECT-TYPE
      SYNTAX      DisplayString (SIZE (1..256))
      MAX-ACCESS  read-only
      STATUS      current
      DESCRIPTION "Return the class name of the SAXParserFactory that is associated with the registry entry."
      ::= { xmlRegistryEntry 45  }
   
   
   xmlRegistryTransformerFactory OBJECT-TYPE
      SYNTAX      DisplayString (SIZE (1..256))
      MAX-ACCESS  read-only
      STATUS      current
      DESCRIPTION "The class name of the default TransformerFactory."
      ::= { xmlRegistryEntry 50  }
   
   
   xmlRegistryWhenToCache OBJECT-TYPE
      SYNTAX      DisplayString (SIZE (1..256))
      MAX-ACCESS  read-only
      STATUS      current
      DESCRIPTION "Whether to cache items as soon as possible or wait until referenced."
      ::= { xmlRegistryEntry 55  }
   
   
   xmlRegistryHandleEntityInvalidation OBJECT-TYPE
      SYNTAX      OCTET STRING
      MAX-ACCESS  read-only
      STATUS      current
      DESCRIPTION "Whether cached DTD/schema is invalidated when parsing error is encountered. "
      ::= { xmlRegistryEntry 56  }
   
   
   wtctBridgeGlobalTable OBJECT-TYPE
      SYNTAX      SEQUENCE OF WtctBridgeGlobalEntry
      MAX-ACCESS  not-accessible
      STATUS      current
      DESCRIPTION "This table represents a wtctBridgeGlobal in the domain."
      ::= { wls 805  }
      
   
   wtctBridgeGlobalEntry OBJECT-TYPE
      SYNTAX      WtctBridgeGlobalEntry
      MAX-ACCESS  not-accessible
      STATUS      current
      DESCRIPTION "Entry of wtctBridgeGlobalTable"
      INDEX { wtctBridgeGlobalIndex}
      ::= { wtctBridgeGlobalTable 1 }
      
   WtctBridgeGlobalEntry ::=
      SEQUENCE
      {
         wtctBridgeGlobalIndex DisplayString (SIZE (1..16)),
         wtctBridgeGlobalObjectName DisplayString (SIZE (1..256)),
         wtctBridgeGlobalType DisplayString (SIZE (1..64)),
         wtctBridgeGlobalName DisplayString (SIZE (1..64)),
         wtctBridgeGlobalParent DisplayString (SIZE (1..256)),
         wtctBridgeGlobalAllowNonStandardTypes DisplayString (SIZE (1..256)),
         wtctBridgeGlobalDefaultReplyDeliveryMode DisplayString (SIZE (1..256)),
         wtctBridgeGlobalDeliveryModeOverride DisplayString (SIZE (1..256)),
         wtctBridgeGlobalJmsFactory DisplayString (SIZE (1..256)),
         wtctBridgeGlobalJmsToTuxPriorityMap DisplayString (SIZE (1..256)),
         wtctBridgeGlobalJndiFactory DisplayString (SIZE (1..256)),
         wtctBridgeGlobalRetries INTEGER,
         wtctBridgeGlobalRetryDelay INTEGER,
         wtctBridgeGlobalTimeout INTEGER,
         wtctBridgeGlobalTransactional DisplayString (SIZE (1..256)),
         wtctBridgeGlobalTuxErrorQueue DisplayString (SIZE (1..256)),
         wtctBridgeGlobalTuxFactory DisplayString (SIZE (1..256)),
         wtctBridgeGlobalTuxToJmsPriorityMap DisplayString (SIZE (1..256)),
         wtctBridgeGlobalUserId DisplayString (SIZE (1..256)),
         wtctBridgeGlobalWlsErrorDestination DisplayString (SIZE (1..256))
      }
      
   
   wtctBridgeGlobalIndex OBJECT-TYPE
      SYNTAX      DisplayString (SIZE (1..16))
      MAX-ACCESS  read-only
      STATUS      current
      DESCRIPTION "Unique value directed from ObjectName which is used as table index"
      ::= { wtctBridgeGlobalEntry 1  }
   
   
   wtctBridgeGlobalObjectName OBJECT-TYPE
      SYNTAX      DisplayString (SIZE (1..256))
      MAX-ACCESS  read-only
      STATUS      current
      DESCRIPTION "JMX-standard MBean name"
      ::= { wtctBridgeGlobalEntry 5  }
   
   
   wtctBridgeGlobalType OBJECT-TYPE
      SYNTAX      DisplayString (SIZE (1..64))
      MAX-ACCESS  read-only
      STATUS      current
      DESCRIPTION "BEA-proprietary MBean type"
      ::= { wtctBridgeGlobalEntry 10  }
   
   
   wtctBridgeGlobalName OBJECT-TYPE
      SYNTAX      DisplayString (SIZE (1..64))
      MAX-ACCESS  read-only
      STATUS      current
      DESCRIPTION "BEA-proprietary MBean name"
      ::= { wtctBridgeGlobalEntry 15  }
   
   
   wtctBridgeGlobalParent OBJECT-TYPE
      SYNTAX      DisplayString (SIZE (1..256))
      MAX-ACCESS  read-only
      STATUS      current
      DESCRIPTION "BEA-proprietary Parent object's identification, with syntax
      <type>:<name>"
      ::= { wtctBridgeGlobalEntry 20  }
   
   
   wtctBridgeGlobalAllowNonStandardTypes OBJECT-TYPE
      SYNTAX      DisplayString (SIZE (1..256))
      MAX-ACCESS  read-only
      STATUS      current
      DESCRIPTION "Defines a flag used to specify if non-standard data types are allowed to 
      * pass through the tBridge. Standard types are: type ASCII text (TextMessage, STRING),
      * or type BLOB (BytesMessage, CARRAY)."
      ::= { wtctBridgeGlobalEntry 25  }
   
   
   wtctBridgeGlobalDefaultReplyDeliveryMode OBJECT-TYPE
      SYNTAX      DisplayString (SIZE (1..256))
      MAX-ACCESS  read-only
      STATUS      current
      DESCRIPTION "Defines the reply delivery mode to associate
      with a message when placing messages onto the target location"
      ::= { wtctBridgeGlobalEntry 30  }
   
   
   wtctBridgeGlobalDeliveryModeOverride OBJECT-TYPE
      SYNTAX      DisplayString (SIZE (1..256))
      MAX-ACCESS  read-only
      STATUS      current
      DESCRIPTION "Defines the delivery mode to use when placing messages onto the target location."
      ::= { wtctBridgeGlobalEntry 35  }
   
   
   wtctBridgeGlobalJmsFactory OBJECT-TYPE
      SYNTAX      DisplayString (SIZE (1..256))
      MAX-ACCESS  read-only
      STATUS      current
      DESCRIPTION "Defines the name of the JMS connection factory."
      ::= { wtctBridgeGlobalEntry 40  }
   
   
   wtctBridgeGlobalJmsToTuxPriorityMap OBJECT-TYPE
      SYNTAX      DisplayString (SIZE (1..256))
      MAX-ACCESS  read-only
      STATUS      current
      DESCRIPTION "Defines the mapping of priorities from JMS to Tuxedo."
      ::= { wtctBridgeGlobalEntry 45  }
   
   
   wtctBridgeGlobalJndiFactory OBJECT-TYPE
      SYNTAX      DisplayString (SIZE (1..256))
      MAX-ACCESS  read-only
      STATUS      current
      DESCRIPTION "Defines the name of the JNDI lookup factory."
      ::= { wtctBridgeGlobalEntry 50  }
   
   
   wtctBridgeGlobalRetries OBJECT-TYPE
      SYNTAX      INTEGER
      MAX-ACCESS  read-only
      STATUS      current
      DESCRIPTION "Defines the number of attempts to redirect a message before putting the 
      message in the specified error location and logging an error."
      ::= { wtctBridgeGlobalEntry 55  }
   
   
   wtctBridgeGlobalRetryDelay OBJECT-TYPE
      SYNTAX      INTEGER
      MAX-ACCESS  read-only
      STATUS      current
      DESCRIPTION "Defines the minimum amount of time (milliseconds) to wait
      before redirecting a message after a failure.
      During this time, no other messages are redirected from the thread.
      Other threads may continue to redirect messages."
      ::= { wtctBridgeGlobalEntry 60  }
   
   
   wtctBridgeGlobalTimeout OBJECT-TYPE
      SYNTAX      INTEGER
      MAX-ACCESS  read-only
      STATUS      current
      DESCRIPTION "Defines the effective length of a timeout for an entire redirection (seconds) when
      placing a message on the target location. 0 indicates an infinite wait."
      ::= { wtctBridgeGlobalEntry 65  }
   
   
   wtctBridgeGlobalTransactional OBJECT-TYPE
      SYNTAX      DisplayString (SIZE (1..256))
      MAX-ACCESS  read-only
      STATUS      current
      DESCRIPTION "Defines a flag that specifies the use of transactions when retrieving messages
      from a source location and when placing messages on a target location."
      ::= { wtctBridgeGlobalEntry 70  }
   
   
   wtctBridgeGlobalTuxErrorQueue OBJECT-TYPE
      SYNTAX      DisplayString (SIZE (1..256))
      MAX-ACCESS  read-only
      STATUS      current
      DESCRIPTION "Defines the name of the Tuxedo queue used to store a message that connot be 
      redirected to a Tuxedo/Q source queue. This queue is in the same queue space
      as the source queue."
      ::= { wtctBridgeGlobalEntry 75  }
   
   
   wtctBridgeGlobalTuxFactory OBJECT-TYPE
      SYNTAX      DisplayString (SIZE (1..256))
      MAX-ACCESS  read-only
      STATUS      current
      DESCRIPTION "Defines the name of the Tuxedo connection factory."
      ::= { wtctBridgeGlobalEntry 80  }
   
   
   wtctBridgeGlobalTuxToJmsPriorityMap OBJECT-TYPE
      SYNTAX      DisplayString (SIZE (1..256))
      MAX-ACCESS  read-only
      STATUS      current
      DESCRIPTION "Defines the mapping of priorities to map from Tuxedo to JMS."
      ::= { wtctBridgeGlobalEntry 85  }
   
   
   wtctBridgeGlobalUserId OBJECT-TYPE
      SYNTAX      DisplayString (SIZE (1..256))
      MAX-ACCESS  read-only
      STATUS      current
      DESCRIPTION "Defines a user identity for all messages handled by the
      tBridge for ACL checks when security is configured."
      ::= { wtctBridgeGlobalEntry 90  }
   
   
   wtctBridgeGlobalWlsErrorDestination OBJECT-TYPE
      SYNTAX      DisplayString (SIZE (1..256))
      MAX-ACCESS  read-only
      STATUS      current
      DESCRIPTION "Defines the name of the location used to store WebLogic Server JMS messages when a
      message cannot be redirected."
      ::= { wtctBridgeGlobalEntry 95  }
   
   
   wtcExportTable OBJECT-TYPE
      SYNTAX      SEQUENCE OF WtcExportEntry
      MAX-ACCESS  not-accessible
      STATUS      current
      DESCRIPTION "This table represents a wtcExport in the domain."
      ::= { wls 810  }
      
   
   wtcExportEntry OBJECT-TYPE
      SYNTAX      WtcExportEntry
      MAX-ACCESS  not-accessible
      STATUS      current
      DESCRIPTION "Entry of wtcExportTable"
      INDEX { wtcExportIndex}
      ::= { wtcExportTable 1 }
      
   WtcExportEntry ::=
      SEQUENCE
      {
         wtcExportIndex       DisplayString (SIZE (1..16)),
         wtcExportObjectName  DisplayString (SIZE (1..256)),
         wtcExportType        DisplayString (SIZE (1..64)),
         wtcExportName        DisplayString (SIZE (1..64)),
         wtcExportParent      DisplayString (SIZE (1..256)),
         wtcExportEJBName     DisplayString (SIZE (1..256)),
         wtcExportLocalAccessPoint DisplayString (SIZE (1..256)),
         wtcExportRemoteName  DisplayString (SIZE (1..256)),
         wtcExportResourceName DisplayString (SIZE (1..256))
      }
      
   
   wtcExportIndex OBJECT-TYPE
      SYNTAX      DisplayString (SIZE (1..16))
      MAX-ACCESS  read-only
      STATUS      current
      DESCRIPTION "Unique value directed from ObjectName which is used as table index"
      ::= { wtcExportEntry 1  }
   
   
   wtcExportObjectName OBJECT-TYPE
      SYNTAX      DisplayString (SIZE (1..256))
      MAX-ACCESS  read-only
      STATUS      current
      DESCRIPTION "JMX-standard MBean name"
      ::= { wtcExportEntry 5  }
   
   
   wtcExportType OBJECT-TYPE
      SYNTAX      DisplayString (SIZE (1..64))
      MAX-ACCESS  read-only
      STATUS      current
      DESCRIPTION "BEA-proprietary MBean type"
      ::= { wtcExportEntry 10  }
   
   
   wtcExportName OBJECT-TYPE
      SYNTAX      DisplayString (SIZE (1..64))
      MAX-ACCESS  read-only
      STATUS      current
      DESCRIPTION "BEA-proprietary MBean name"
      ::= { wtcExportEntry 15  }
   
   
   wtcExportParent OBJECT-TYPE
      SYNTAX      DisplayString (SIZE (1..256))
      MAX-ACCESS  read-only
      STATUS      current
      DESCRIPTION "BEA-proprietary Parent object's identification, with syntax
      <type>:<name>"
      ::= { wtcExportEntry 20  }
   
   
   wtcExportEJBName OBJECT-TYPE
      SYNTAX      DisplayString (SIZE (1..256))
      MAX-ACCESS  read-only
      STATUS      current
      DESCRIPTION "Defines the name of the local access point that exports the service."
      ::= { wtcExportEntry 25  }
   
   
   wtcExportLocalAccessPoint OBJECT-TYPE
      SYNTAX      DisplayString (SIZE (1..256))
      MAX-ACCESS  read-only
      STATUS      current
      DESCRIPTION "Defines the name of the local access point that exports the service."
      ::= { wtcExportEntry 30  }
   
   
   wtcExportRemoteName OBJECT-TYPE
      SYNTAX      DisplayString (SIZE (1..256))
      MAX-ACCESS  read-only
      STATUS      current
      DESCRIPTION "Defines the remote name of the service.
      If not specified, the ResourceName attribute is used."
      ::= { wtcExportEntry 35  }
   
   
   wtcExportResourceName OBJECT-TYPE
      SYNTAX      DisplayString (SIZE (1..256))
      MAX-ACCESS  read-only
      STATUS      current
      DESCRIPTION "Defines the name used to identify an exported service."
      ::= { wtcExportEntry 40  }
   
   
   wtcImportTable OBJECT-TYPE
      SYNTAX      SEQUENCE OF WtcImportEntry
      MAX-ACCESS  not-accessible
      STATUS      current
      DESCRIPTION "This table represents a wtcImport in the domain."
      ::= { wls 815  }
      
   
   wtcImportEntry OBJECT-TYPE
      SYNTAX      WtcImportEntry
      MAX-ACCESS  not-accessible
      STATUS      current
      DESCRIPTION "Entry of wtcImportTable"
      INDEX { wtcImportIndex}
      ::= { wtcImportTable 1 }
      
   WtcImportEntry ::=
      SEQUENCE
      {
         wtcImportIndex       DisplayString (SIZE (1..16)),
         wtcImportObjectName  DisplayString (SIZE (1..256)),
         wtcImportType        DisplayString (SIZE (1..64)),
         wtcImportName        DisplayString (SIZE (1..64)),
         wtcImportParent      DisplayString (SIZE (1..256)),
         wtcImportRemoteAccessPointList DisplayString (SIZE (1..256)),
         wtcImportLocalAccessPoint DisplayString (SIZE (1..256)),
         wtcImportRemoteName  DisplayString (SIZE (1..256)),
         wtcImportResourceName DisplayString (SIZE (1..256))
      }
      
   
   wtcImportIndex OBJECT-TYPE
      SYNTAX      DisplayString (SIZE (1..16))
      MAX-ACCESS  read-only
      STATUS      current
      DESCRIPTION "Unique value directed from ObjectName which is used as table index"
      ::= { wtcImportEntry 1  }
   
   
   wtcImportObjectName OBJECT-TYPE
      SYNTAX      DisplayString (SIZE (1..256))
      MAX-ACCESS  read-only
      STATUS      current
      DESCRIPTION "JMX-standard MBean name"
      ::= { wtcImportEntry 5  }
   
   
   wtcImportType OBJECT-TYPE
      SYNTAX      DisplayString (SIZE (1..64))
      MAX-ACCESS  read-only
      STATUS      current
      DESCRIPTION "BEA-proprietary MBean type"
      ::= { wtcImportEntry 10  }
   
   
   wtcImportName OBJECT-TYPE
      SYNTAX      DisplayString (SIZE (1..64))
      MAX-ACCESS  read-only
      STATUS      current
      DESCRIPTION "BEA-proprietary MBean name"
      ::= { wtcImportEntry 15  }
   
   
   wtcImportParent OBJECT-TYPE
      SYNTAX      DisplayString (SIZE (1..256))
      MAX-ACCESS  read-only
      STATUS      current
      DESCRIPTION "BEA-proprietary Parent object's identification, with syntax
      <type>:<name>"
      ::= { wtcImportEntry 20  }
   
   
   wtcImportRemoteAccessPointList OBJECT-TYPE
      SYNTAX      DisplayString (SIZE (1..256))
      MAX-ACCESS  read-only
      STATUS      current
      DESCRIPTION "."
      ::= { wtcImportEntry 25  }
   
   
   wtcImportLocalAccessPoint OBJECT-TYPE
      SYNTAX      DisplayString (SIZE (1..256))
      MAX-ACCESS  read-only
      STATUS      current
      DESCRIPTION "The certificate type used for secure communications with the wtcImport ."
      ::= { wtcImportEntry 30  }
   
   
   wtcImportRemoteName OBJECT-TYPE
      SYNTAX      DisplayString (SIZE (1..256))
      MAX-ACCESS  read-only
      STATUS      current
      DESCRIPTION "."
      ::= { wtcImportEntry 35  }
   
   
   wtcImportResourceName OBJECT-TYPE
      SYNTAX      DisplayString (SIZE (1..256))
      MAX-ACCESS  read-only
      STATUS      current
      DESCRIPTION "The port on which wtcImport listens for connections."
      ::= { wtcImportEntry 40  }
   
   
   wtcLocalTuxDomTable OBJECT-TYPE
      SYNTAX      SEQUENCE OF WtcLocalTuxDomEntry
      MAX-ACCESS  not-accessible
      STATUS      current
      DESCRIPTION "This table represents a wtcLocalTuxDom in the domain."
      ::= { wls 817  }
      
   
   wtcLocalTuxDomEntry OBJECT-TYPE
      SYNTAX      WtcLocalTuxDomEntry
      MAX-ACCESS  not-accessible
      STATUS      current
      DESCRIPTION "Entry of wtcLocalTuxDomTable"
      INDEX { wtcLocalTuxDomIndex}
      ::= { wtcLocalTuxDomTable 1 }
      
   WtcLocalTuxDomEntry ::=
      SEQUENCE
      {
         wtcLocalTuxDomIndex  DisplayString (SIZE (1..16)),
         wtcLocalTuxDomObjectName DisplayString (SIZE (1..256)),
         wtcLocalTuxDomType   DisplayString (SIZE (1..64)),
         wtcLocalTuxDomName   DisplayString (SIZE (1..64)),
         wtcLocalTuxDomParent DisplayString (SIZE (1..256)),
         wtcLocalTuxDomAccessPoint DisplayString (SIZE (1..256)),
         wtcLocalTuxDomAccessPointId DisplayString (SIZE (1..256)),
         wtcLocalTuxDomBlockTime Counter64,
         wtcLocalTuxDomCmpLimit INTEGER,
         wtcLocalTuxDomConnectionPolicy DisplayString (SIZE (1..256)),
         wtcLocalTuxDomConnPrincipalName DisplayString (SIZE (1..256)),
         wtcLocalTuxDomInteroperate DisplayString (SIZE (1..256)),
         wtcLocalTuxDomMaxEncryptBits DisplayString (SIZE (1..256)),
         wtcLocalTuxDomMaxRetries Counter64,
         wtcLocalTuxDomMinEncryptBits DisplayString (SIZE (1..256)),
         wtcLocalTuxDomNWAddr DisplayString (SIZE (1..256)),
         wtcLocalTuxDomRetryInterval Counter64,
         wtcLocalTuxDomSecurity DisplayString (SIZE (1..256)),
         wtcLocalTuxDomKeyStoresLocation OCTET STRING,
         wtcLocalTuxDomSSLRenegotiation INTEGER,
         wtcLocalTuxDomUseSSL OCTET STRING,
         wtcLocalTuxDomKeepAliveWait INTEGER,
         wtcLocalTuxDomTrustKeyStoreFileName OCTET STRING,
         wtcLocalTuxDomKeepAlive INTEGER,
         wtcLocalTuxDomPrivateKeyAlias OCTET STRING,
         wtcLocalTuxDomIdentityKeyStoreFileName OCTET STRING
      }
      
   
   wtcLocalTuxDomIndex OBJECT-TYPE
      SYNTAX      DisplayString (SIZE (1..16))
      MAX-ACCESS  read-only
      STATUS      current
      DESCRIPTION "Unique value directed from ObjectName which is used as table index"
      ::= { wtcLocalTuxDomEntry 1  }
   
   
   wtcLocalTuxDomObjectName OBJECT-TYPE
      SYNTAX      DisplayString (SIZE (1..256))
      MAX-ACCESS  read-only
      STATUS      current
      DESCRIPTION "JMX-standard MBean name"
      ::= { wtcLocalTuxDomEntry 5  }
   
   
   wtcLocalTuxDomType OBJECT-TYPE
      SYNTAX      DisplayString (SIZE (1..64))
      MAX-ACCESS  read-only
      STATUS      current
      DESCRIPTION "BEA-proprietary MBean type"
      ::= { wtcLocalTuxDomEntry 10  }
   
   
   wtcLocalTuxDomName OBJECT-TYPE
      SYNTAX      DisplayString (SIZE (1..64))
      MAX-ACCESS  read-only
      STATUS      current
      DESCRIPTION "BEA-proprietary MBean name"
      ::= { wtcLocalTuxDomEntry 15  }
   
   
   wtcLocalTuxDomParent OBJECT-TYPE
      SYNTAX      DisplayString (SIZE (1..256))
      MAX-ACCESS  read-only
      STATUS      current
      DESCRIPTION "BEA-proprietary Parent object's identification, with syntax
      <type>:<name>"
      ::= { wtcLocalTuxDomEntry 20  }
   
   
   wtcLocalTuxDomAccessPoint OBJECT-TYPE
      SYNTAX      DisplayString (SIZE (1..256))
      MAX-ACCESS  read-only
      STATUS      current
      DESCRIPTION "Defines a unique name within the scope of MBean types
      WTCLocalTuxDom and WTCRemoteTuxDom used to identify the access point or domain."
      ::= { wtcLocalTuxDomEntry 25  }
   
   
   wtcLocalTuxDomAccessPointId OBJECT-TYPE
      SYNTAX      DisplayString (SIZE (1..256))
      MAX-ACCESS  read-only
      STATUS      current
      DESCRIPTION "Defines the domain access point identifier. This identifier is a unique
      name across all local and remote domain access points."
      ::= { wtcLocalTuxDomEntry 30  }
   
   
   wtcLocalTuxDomBlockTime OBJECT-TYPE
      SYNTAX      Counter64
      MAX-ACCESS  read-only
      STATUS      current
      DESCRIPTION "Defines the maximum wait time (seconds) allowed for a blocking call."
      ::= { wtcLocalTuxDomEntry 35  }
   
   
   wtcLocalTuxDomCmpLimit OBJECT-TYPE
      SYNTAX      INTEGER
      MAX-ACCESS  read-only
      STATUS      current
      DESCRIPTION "Defines the compression threshold used when sending data to a remote
      domain. Application buffers larger than this size are compressed."
      ::= { wtcLocalTuxDomEntry 40  }
   
   
   wtcLocalTuxDomConnectionPolicy OBJECT-TYPE
      SYNTAX      DisplayString (SIZE (1..256))
      MAX-ACCESS  read-only
      STATUS      current
      DESCRIPTION "Defines the conditions under which a local domain tries to establish a
      connection to a remote domain."
      ::= { wtcLocalTuxDomEntry 45  }
   
   
   wtcLocalTuxDomConnPrincipalName OBJECT-TYPE
      SYNTAX      DisplayString (SIZE (1..256))
      MAX-ACCESS  read-only
      STATUS      current
      DESCRIPTION "Defines the principal name used to 
      verify the identity of this domain when establishing a connection
      to another domain."
      ::= { wtcLocalTuxDomEntry 50  }
   
   
   wtcLocalTuxDomInteroperate OBJECT-TYPE
      SYNTAX      DisplayString (SIZE (1..256))
      MAX-ACCESS  read-only
      STATUS      current
      DESCRIPTION "Specifies whether the local domain interoperates with
      remote domains that are based upon Tuxedo release 6.5. If Yes, 
      the local domain interoperates with a Tuxedo 6.5 domain."
      ::= { wtcLocalTuxDomEntry 55  }
   
   
   wtcLocalTuxDomMaxEncryptBits OBJECT-TYPE
      SYNTAX      DisplayString (SIZE (1..256))
      MAX-ACCESS  read-only
      STATUS      current
      DESCRIPTION "Defines the maximum encryption key length (in bits) used when 
      establishing a network connection for a local domain."
      ::= { wtcLocalTuxDomEntry 60  }
   
   
   wtcLocalTuxDomMaxRetries OBJECT-TYPE
      SYNTAX      Counter64
      MAX-ACCESS  read-only
      STATUS      current
      DESCRIPTION "Defines the number of times that a domain gateway tries to establish
      connections to remote domain access points. Use only when Connection Policy is 
      set to ON_STARTUP."
      ::= { wtcLocalTuxDomEntry 65  }
   
   
   wtcLocalTuxDomMinEncryptBits OBJECT-TYPE
      SYNTAX      DisplayString (SIZE (1..256))
      MAX-ACCESS  read-only
      STATUS      current
      DESCRIPTION "Defines the minimum encryption key length (in bits) used when 
      establishing a network connection for a local domain."
      ::= { wtcLocalTuxDomEntry 70  }
   
   
   wtcLocalTuxDomNWAddr OBJECT-TYPE
      SYNTAX      DisplayString (SIZE (1..256))
      MAX-ACCESS  read-only
      STATUS      current
      DESCRIPTION "Defines the network address of the local domain gateway. Specify the
      TCP/IP address in one of the following formats"
      ::= { wtcLocalTuxDomEntry 75  }
   
   
   wtcLocalTuxDomRetryInterval OBJECT-TYPE
      SYNTAX      Counter64
      MAX-ACCESS  read-only
      STATUS      current
      DESCRIPTION "Defines the number of seconds between automatic attempts to establish a
      connection to remote domain access points. Use only when Connection Policy is 
      set to ON_STARTUP."
      ::= { wtcLocalTuxDomEntry 80  }
   
   
   wtcLocalTuxDomSecurity OBJECT-TYPE
      SYNTAX      DisplayString (SIZE (1..256))
      MAX-ACCESS  read-only
      STATUS      current
      DESCRIPTION "Defines the type of application security enforced."
      ::= { wtcLocalTuxDomEntry 85  }
   
   
   wtcLocalTuxDomKeyStoresLocation OBJECT-TYPE
      SYNTAX      OCTET STRING
      MAX-ACCESS  read-only
      STATUS      current
      DESCRIPTION "Which configuration rules should be used for finding this Local Tuxedo access point's identity and trust keystores?"
      ::= { wtcLocalTuxDomEntry 86  }
   
   
   wtcLocalTuxDomSSLRenegotiation OBJECT-TYPE
      SYNTAX      INTEGER
      MAX-ACCESS  read-only
      STATUS      current
      DESCRIPTION "The amount of time between session re-negotiations when the SSL protocol is in use.  Range of values: Between 0 and a positive 32-bit integer."
      ::= { wtcLocalTuxDomEntry 87  }
   
   
   wtcLocalTuxDomUseSSL OBJECT-TYPE
      SYNTAX      OCTET STRING
      MAX-ACCESS  read-only
      STATUS      current
      DESCRIPTION "Return value that tells whether connection performed or out of or accepted from this Local Tuxedo access point will use SSL on top of its transport layer."
      ::= { wtcLocalTuxDomEntry 88  }
   
   
   wtcLocalTuxDomKeepAliveWait OBJECT-TYPE
      SYNTAX      INTEGER
      MAX-ACCESS  read-only
      STATUS      current
      DESCRIPTION "Return value that tells whether this local Tuxedo access point requires the acknowledgement of Application Level Keep Alive, and how long it will wait without receiving acknowledgement before declare the connection is inaccessable."
      ::= { wtcLocalTuxDomEntry 89  }
   
   
   wtcLocalTuxDomTrustKeyStoreFileName OBJECT-TYPE
      SYNTAX      OCTET STRING
      MAX-ACCESS  read-only
      STATUS      current
      DESCRIPTION "The path and file name of the trust keystore.  The path name must either be absolute or relative to where the server was booted. This file name is only used if KeyStores is 'Custom Stores'."
      ::= { wtcLocalTuxDomEntry 90  }
   
   
   wtcLocalTuxDomKeepAlive OBJECT-TYPE
      SYNTAX      INTEGER
      MAX-ACCESS  read-only
      STATUS      current
      DESCRIPTION "Return value tells whether this local Tuxedo access point is configured with Application Level Keep Alive, and it maximum idle time value before wait timer start ticking."
      ::= { wtcLocalTuxDomEntry 91  }
   
   
   wtcLocalTuxDomPrivateKeyAlias OBJECT-TYPE
      SYNTAX      OCTET STRING
      MAX-ACCESS  read-only
      STATUS      current
      DESCRIPTION "The string alias used to store and retrieve the Local Tuxedo access point's private key in the keystore. This private key is associated with the Local Tuxedo access point's digital certificate."
      ::= { wtcLocalTuxDomEntry 92  }
   
   
   wtcLocalTuxDomIdentityKeyStoreFileName OBJECT-TYPE
      SYNTAX      OCTET STRING
      MAX-ACCESS  read-only
      STATUS      current
      DESCRIPTION "The path and file name of the identity keystore.  The path name must either be absolute or relative to where the server was booted. The identity key store file name is only used if KeystoreLocation is 'Custom Stores'."
      ::= { wtcLocalTuxDomEntry 93  }
   
   
   wtcRemoteTuxDomTable OBJECT-TYPE
      SYNTAX      SEQUENCE OF WtcRemoteTuxDomEntry
      MAX-ACCESS  not-accessible
      STATUS      current
      DESCRIPTION "This table represents a wtcRemoteTuxDom in the domain."
      ::= { wls 820  }
      
   
   wtcRemoteTuxDomEntry OBJECT-TYPE
      SYNTAX      WtcRemoteTuxDomEntry
      MAX-ACCESS  not-accessible
      STATUS      current
      DESCRIPTION "Entry of wtcRemoteTuxDomTable"
      INDEX { wtcRemoteTuxDomIndex}
      ::= { wtcRemoteTuxDomTable 1 }
      
   WtcRemoteTuxDomEntry ::=
      SEQUENCE
      {
         wtcRemoteTuxDomIndex DisplayString (SIZE (1..16)),
         wtcRemoteTuxDomObjectName DisplayString (SIZE (1..256)),
         wtcRemoteTuxDomType  DisplayString (SIZE (1..64)),
         wtcRemoteTuxDomName  DisplayString (SIZE (1..64)),
         wtcRemoteTuxDomParent DisplayString (SIZE (1..256)),
         wtcRemoteTuxDomAccessPoint DisplayString (SIZE (1..256)),
         wtcRemoteTuxDomAccessPointId DisplayString (SIZE (1..256)),
         wtcRemoteTuxDomAclPolicy DisplayString (SIZE (1..256)),
         wtcRemoteTuxDomCmpLimit INTEGER,
         wtcRemoteTuxDomConnectionPolicy DisplayString (SIZE (1..256)),
         wtcRemoteTuxDomConnPrincipalName DisplayString (SIZE (1..256)),
         wtcRemoteTuxDomCredentialPolicy DisplayString (SIZE (1..256)),
         wtcRemoteTuxDomMaxEncryptBits DisplayString (SIZE (1..256)),
         wtcRemoteTuxDomMaxRetries Counter64,
         wtcRemoteTuxDomMinEncryptBits DisplayString (SIZE (1..256)),
         wtcRemoteTuxDomNWAddr DisplayString (SIZE (1..256)),
         wtcRemoteTuxDomRetryInterval Counter64,
         wtcRemoteTuxDomTpUsrFile DisplayString (SIZE (1..256)),
         wtcRemoteTuxDomFederationName DisplayString (SIZE (1..256)),
         wtcRemoteTuxDomFederationURL DisplayString (SIZE (1..256)),
         wtcRemoteTuxDomLocalAccessPoint DisplayString (SIZE (1..256)),
         wtcRemoteTuxDomDefaultAppKey INTEGER,
         wtcRemoteTuxDomCustomAppKeyClass OCTET STRING,
         wtcRemoteTuxDomTuxedoGidKw OCTET STRING,
         wtcRemoteTuxDomAllowAnonymous OCTET STRING,
         wtcRemoteTuxDomKeepAliveWait INTEGER,
         wtcRemoteTuxDomCustomAppKeyClassParam OCTET STRING,
         wtcRemoteTuxDomTuxedoUidKw OCTET STRING,
         wtcRemoteTuxDomKeepAlive INTEGER,
         wtcRemoteTuxDomAppKey OCTET STRING
      }
      
   
   wtcRemoteTuxDomIndex OBJECT-TYPE
      SYNTAX      DisplayString (SIZE (1..16))
      MAX-ACCESS  read-only
      STATUS      current
      DESCRIPTION "Unique value directed from ObjectName which is used as table index"
      ::= { wtcRemoteTuxDomEntry 1  }
   
   
   wtcRemoteTuxDomObjectName OBJECT-TYPE
      SYNTAX      DisplayString (SIZE (1..256))
      MAX-ACCESS  read-only
      STATUS      current
      DESCRIPTION "JMX-standard MBean name"
      ::= { wtcRemoteTuxDomEntry 5  }
   
   
   wtcRemoteTuxDomType OBJECT-TYPE
      SYNTAX      DisplayString (SIZE (1..64))
      MAX-ACCESS  read-only
      STATUS      current
      DESCRIPTION "BEA-proprietary MBean type"
      ::= { wtcRemoteTuxDomEntry 10  }
   
   
   wtcRemoteTuxDomName OBJECT-TYPE
      SYNTAX      DisplayString (SIZE (1..64))
      MAX-ACCESS  read-only
      STATUS      current
      DESCRIPTION "BEA-proprietary MBean name"
      ::= { wtcRemoteTuxDomEntry 15  }
   
   
   wtcRemoteTuxDomParent OBJECT-TYPE
      SYNTAX      DisplayString (SIZE (1..256))
      MAX-ACCESS  read-only
      STATUS      current
      DESCRIPTION "BEA-proprietary Parent object's identification, with syntax
      <type>:<name>"
      ::= { wtcRemoteTuxDomEntry 20  }
   
   
   wtcRemoteTuxDomAccessPoint OBJECT-TYPE
      SYNTAX      DisplayString (SIZE (1..256))
      MAX-ACCESS  read-only
      STATUS      current
      DESCRIPTION "Defines a unique name within the scope of MBean types
      WTCLocalTuxDom and WTCRemoteTuxDom used to identify the access point or domain."
      ::= { wtcRemoteTuxDomEntry 25  }
   
   
   wtcRemoteTuxDomAccessPointId OBJECT-TYPE
      SYNTAX      DisplayString (SIZE (1..256))
      MAX-ACCESS  read-only
      STATUS      current
      DESCRIPTION "Defines the domain access point identifier. This identifier is unique across
      all local and remote domain access points."
      ::= { wtcRemoteTuxDomEntry 30  }
   
   
   wtcRemoteTuxDomAclPolicy OBJECT-TYPE
      SYNTAX      DisplayString (SIZE (1..256))
      MAX-ACCESS  read-only
      STATUS      current
      DESCRIPTION "Defines the inbound access control list (ACL) policy
      toward requests from a remote domain."
      ::= { wtcRemoteTuxDomEntry 35  }
   
   
   wtcRemoteTuxDomCmpLimit OBJECT-TYPE
      SYNTAX      INTEGER
      MAX-ACCESS  read-only
      STATUS      current
      DESCRIPTION "Defines the compression threshold used when sending data to a remote
      domain. Application buffers larger than this size are compressed."
      ::= { wtcRemoteTuxDomEntry 40  }
   
   
   wtcRemoteTuxDomConnectionPolicy OBJECT-TYPE
      SYNTAX      DisplayString (SIZE (1..256))
      MAX-ACCESS  read-only
      STATUS      current
      DESCRIPTION "Defines the conditions under which a local domain tries to establish a
      connection to a remote domain."
      ::= { wtcRemoteTuxDomEntry 45  }
   
   
   wtcRemoteTuxDomConnPrincipalName OBJECT-TYPE
      SYNTAX      DisplayString (SIZE (1..256))
      MAX-ACCESS  read-only
      STATUS      current
      DESCRIPTION "Defines the principal name used to 
      verify the identity of this domain when establishing a connection
      to another domain."
      ::= { wtcRemoteTuxDomEntry 50  }
   
   
   wtcRemoteTuxDomCredentialPolicy OBJECT-TYPE
      SYNTAX      DisplayString (SIZE (1..256))
      MAX-ACCESS  read-only
      STATUS      current
      DESCRIPTION "Defines the outbound access control list (ACL) policy toward
      requests to a remote domain."
      ::= { wtcRemoteTuxDomEntry 55  }
   
   
   wtcRemoteTuxDomMaxEncryptBits OBJECT-TYPE
      SYNTAX      DisplayString (SIZE (1..256))
      MAX-ACCESS  read-only
      STATUS      current
      DESCRIPTION "Defines the maximum encryption key length (in bits) used when 
      establishing a network connection for a local domain."
      ::= { wtcRemoteTuxDomEntry 60  }
   
   
   wtcRemoteTuxDomMaxRetries OBJECT-TYPE
      SYNTAX      Counter64
      MAX-ACCESS  read-only
      STATUS      current
      DESCRIPTION "Defines the number of times that a domain gateway tries to establish
      connections to remote domain access points. Use only when Connection Policy is 
      set to ON_STARTUP."
      ::= { wtcRemoteTuxDomEntry 65  }
   
   
   wtcRemoteTuxDomMinEncryptBits OBJECT-TYPE
      SYNTAX      DisplayString (SIZE (1..256))
      MAX-ACCESS  read-only
      STATUS      current
      DESCRIPTION "Defines the minimum encryption key length (in bits) used when 
      establishing a network connection for a local domain."
      ::= { wtcRemoteTuxDomEntry 70  }
   
   
   wtcRemoteTuxDomNWAddr OBJECT-TYPE
      SYNTAX      DisplayString (SIZE (1..256))
      MAX-ACCESS  read-only
      STATUS      current
      DESCRIPTION "Defines the network address of the local domain gateway."
      ::= { wtcRemoteTuxDomEntry 75  }
   
   
   wtcRemoteTuxDomRetryInterval OBJECT-TYPE
      SYNTAX      Counter64
      MAX-ACCESS  read-only
      STATUS      current
      DESCRIPTION "Defines the number of seconds between automatic attempts to establish a
      connection to remote domain access points."
      ::= { wtcRemoteTuxDomEntry 80  }
   
   
   wtcRemoteTuxDomTpUsrFile OBJECT-TYPE
      SYNTAX      DisplayString (SIZE (1..256))
      MAX-ACCESS  read-only
      STATUS      current
      DESCRIPTION "Defines the full path to user password file containing
      uid/gid information."
      ::= { wtcRemoteTuxDomEntry 85  }
   
   
   wtcRemoteTuxDomFederationName OBJECT-TYPE
      SYNTAX      DisplayString (SIZE (1..256))
      MAX-ACCESS  read-only
      STATUS      current
      DESCRIPTION "Defines the context at which to federate to a foreign name service."
      ::= { wtcRemoteTuxDomEntry 100  }
   
   
   wtcRemoteTuxDomFederationURL OBJECT-TYPE
      SYNTAX      DisplayString (SIZE (1..256))
      MAX-ACCESS  read-only
      STATUS      current
      DESCRIPTION "Defines the URL for a foreign name service that is federated into JNDI."
      ::= { wtcRemoteTuxDomEntry 105  }
   
   
   wtcRemoteTuxDomLocalAccessPoint OBJECT-TYPE
      SYNTAX      DisplayString (SIZE (1..256))
      MAX-ACCESS  read-only
      STATUS      current
      DESCRIPTION "Defines the local domain name from which a remote domain is reached."
      ::= { wtcRemoteTuxDomEntry 110  }
   
   
   wtcRemoteTuxDomDefaultAppKey OBJECT-TYPE
      SYNTAX      INTEGER
      MAX-ACCESS  read-only
      STATUS      current
      DESCRIPTION "The default AppKey value to be used by the anonymous user and other users who are not defined in the user database if the plug-in allows them to access Tuxedo.  Note: The TpUsrFile and LDAP plug-ins do not allow users that are not defined in user database to access Tuxedo unless Allow Anonymous is enabled."
      ::= { wtcRemoteTuxDomEntry 111  }
   
   
   wtcRemoteTuxDomCustomAppKeyClass OBJECT-TYPE
      SYNTAX      OCTET STRING
      MAX-ACCESS  read-only
      STATUS      current
      DESCRIPTION "The full pathname to the custom AppKey generator class. (This class is only relevant if you specify Custom as the AppKey Generator.)  Note: This class is loaded at runtime if the Custom AppKey generator plug-in is selected."
      ::= { wtcRemoteTuxDomEntry 112  }
   
   
   wtcRemoteTuxDomTuxedoGidKw OBJECT-TYPE
      SYNTAX      OCTET STRING
      MAX-ACCESS  read-only
      STATUS      current
      DESCRIPTION "The keyword for Tuxedo GID (Group ID) used in the WlsUser when using the Tuxedo migration utility tpmigldap. (This field is only relevant if you specify LDAP as the AppKey Generator.)  Note: The keyword is used to find Tuxedo GID in the user record in the embedded LDAP database."
      ::= { wtcRemoteTuxDomEntry 113  }
   
   
   wtcRemoteTuxDomAllowAnonymous OBJECT-TYPE
      SYNTAX      OCTET STRING
      MAX-ACCESS  read-only
      STATUS      current
      DESCRIPTION "Specifies whether the anonymous user is allowed to access remote Tuxedo services.  Note: If the anonymous user is allowed to access Tuxedo, the default AppKey will be used for TpUsrFile and LDAP AppKey plug-ins. Interaction with the Custom AppKey plug-in depends on the design of the Custom AppKey generator."
      ::= { wtcRemoteTuxDomEntry 114  }
   
   
   wtcRemoteTuxDomKeepAliveWait OBJECT-TYPE
      SYNTAX      INTEGER
      MAX-ACCESS  read-only
      STATUS      current
      DESCRIPTION "Return value that tells whether this local Tuxedo access point requires the acknowledgement of Application Level Keep Alive, and how long it will wait without receiving acknowledgement before declare the connection is inaccessable."
      ::= { wtcRemoteTuxDomEntry 115  }
   
   
   wtcRemoteTuxDomCustomAppKeyClassParam OBJECT-TYPE
      SYNTAX      OCTET STRING
      MAX-ACCESS  read-only
      STATUS      current
      DESCRIPTION "The optional parameters to be used by the custom AppKey class at the class initialization time. (This class is only relevant if you specify Custom as the AppKey Generator.)"
      ::= { wtcRemoteTuxDomEntry 116  }
   
   
   wtcRemoteTuxDomTuxedoUidKw OBJECT-TYPE
      SYNTAX      OCTET STRING
      MAX-ACCESS  read-only
      STATUS      current
      DESCRIPTION "The keyword for Tuxedo UID (User ID) used in the WlsUser when using the Tuxedo migration utility tpmigldap. (This keyword is only relevant if you specify LDAP as the AppKey Generator.)  Note: The keyword is used to find Tuxedo UID in the user record in the embedded LDAP database."
      ::= { wtcRemoteTuxDomEntry 117  }
   
   
   wtcRemoteTuxDomKeepAlive OBJECT-TYPE
      SYNTAX      INTEGER
      MAX-ACCESS  read-only
      STATUS      current
      DESCRIPTION "Return value tells whether this local Tuxedo access point is configured with Application Level Keep Alive, and it maximum idle time value before wait timer start ticking."
      ::= { wtcRemoteTuxDomEntry 118  }
   
   
   wtcRemoteTuxDomAppKey OBJECT-TYPE
      SYNTAX      OCTET STRING
      MAX-ACCESS  read-only
      STATUS      current
      DESCRIPTION "Specifies the type of AppKey plug-in used.  The allowed values are:   TpUsrFile - TpUsrFile is the default plug-in. It uses an imported Tuxedo TPUSR file to provide user security information. Previous releases of WebLogic Tuxedo Connector support this option.  LDAP - The LDAP plug-in utilizes an embedded LDAP server to provide user security information. The user record must define the Tuxedo UID and GID information in the description field. This functionality is not supported in previous releases of WebLogic Tuxedo Connector.   Custom - The Custom plug-in provides the ability to write your own AppKey generator class to provide the security information required by Tuxedo. This functionality is not supported in previous releases of WebLogic Tuxedo Connector."
      ::= { wtcRemoteTuxDomEntry 119  }
   
   
   wtctBridgeRedirectTable OBJECT-TYPE
      SYNTAX      SEQUENCE OF WtctBridgeRedirectEntry
      MAX-ACCESS  not-accessible
      STATUS      current
      DESCRIPTION "This table represents a wtctBridgeRedirect in the domain."
      ::= { wls 825  }
      
   
   wtctBridgeRedirectEntry OBJECT-TYPE
      SYNTAX      WtctBridgeRedirectEntry
      MAX-ACCESS  not-accessible
      STATUS      current
      DESCRIPTION "Entry of wtctBridgeRedirectTable"
      INDEX { wtctBridgeRedirectIndex}
      ::= { wtctBridgeRedirectTable 1 }
      
   WtctBridgeRedirectEntry ::=
      SEQUENCE
      {
         wtctBridgeRedirectIndex DisplayString (SIZE (1..16)),
         wtctBridgeRedirectObjectName DisplayString (SIZE (1..256)),
         wtctBridgeRedirectType DisplayString (SIZE (1..64)),
         wtctBridgeRedirectName DisplayString (SIZE (1..64)),
         wtctBridgeRedirectParent DisplayString (SIZE (1..256)),
         wtctBridgeRedirectDirection DisplayString (SIZE (1..256)),
         wtctBridgeRedirectMetaDataFile DisplayString (SIZE (1..256)),
         wtctBridgeRedirectReplyQ DisplayString (SIZE (1..256)),
         wtctBridgeRedirectSourceAccessPoint DisplayString (SIZE (1..256)),
         wtctBridgeRedirectSourceName DisplayString (SIZE (1..256)),
         wtctBridgeRedirectSourceQspace DisplayString (SIZE (1..256)),
         wtctBridgeRedirectTargetAccessPoint DisplayString (SIZE (1..256)),
         wtctBridgeRedirectTargetName DisplayString (SIZE (1..256)),
         wtctBridgeRedirectTargetQspace DisplayString (SIZE (1..256)),
         wtctBridgeRedirectTranslateFML DisplayString (SIZE (1..256))
      }
      
   
   wtctBridgeRedirectIndex OBJECT-TYPE
      SYNTAX      DisplayString (SIZE (1..16))
      MAX-ACCESS  read-only
      STATUS      current
      DESCRIPTION "Unique value directed from ObjectName which is used as table index"
      ::= { wtctBridgeRedirectEntry 1  }
   
   
   wtctBridgeRedirectObjectName OBJECT-TYPE
      SYNTAX      DisplayString (SIZE (1..256))
      MAX-ACCESS  read-only
      STATUS      current
      DESCRIPTION "JMX-standard MBean name"
      ::= { wtctBridgeRedirectEntry 5  }
   
   
   wtctBridgeRedirectType OBJECT-TYPE
      SYNTAX      DisplayString (SIZE (1..64))
      MAX-ACCESS  read-only
      STATUS      current
      DESCRIPTION "BEA-proprietary MBean type"
      ::= { wtctBridgeRedirectEntry 10  }
   
   
   wtctBridgeRedirectName OBJECT-TYPE
      SYNTAX      DisplayString (SIZE (1..64))
      MAX-ACCESS  read-only
      STATUS      current
      DESCRIPTION "BEA-proprietary MBean name"
      ::= { wtctBridgeRedirectEntry 15  }
   
   
   wtctBridgeRedirectParent OBJECT-TYPE
      SYNTAX      DisplayString (SIZE (1..256))
      MAX-ACCESS  read-only
      STATUS      current
      DESCRIPTION "BEA-proprietary Parent object's identification, with syntax
      <type>:<name>"
      ::= { wtctBridgeRedirectEntry 20  }
   
   
   wtctBridgeRedirectDirection OBJECT-TYPE
      SYNTAX      DisplayString (SIZE (1..256))
      MAX-ACCESS  read-only
      STATUS      current
      DESCRIPTION "Defines the direction of data flow. Each defined direction is handled by starting a new thread.
      At least one redirection must be specified in the tBridge configuration or the 
      tBridge will fail to start and an error will be logged."
      ::= { wtctBridgeRedirectEntry 25  }
   
   
   wtctBridgeRedirectMetaDataFile OBJECT-TYPE
      SYNTAX      DisplayString (SIZE (1..256))
      MAX-ACCESS  read-only
      STATUS      current
      DESCRIPTION "Defines the name of the metadataFile URL used to passed to the call WLXT."
      ::= { wtctBridgeRedirectEntry 30  }
   
   
   wtctBridgeRedirectReplyQ OBJECT-TYPE
      SYNTAX      DisplayString (SIZE (1..256))
      MAX-ACCESS  read-only
      STATUS      current
      DESCRIPTION "Defines the name of the JMS queue used specifically for synchronous calls to a
      TUXEDO service. The response is returned to the JMS ReplyQ."
      ::= { wtctBridgeRedirectEntry 35  }
   
   
   wtctBridgeRedirectSourceAccessPoint OBJECT-TYPE
      SYNTAX      DisplayString (SIZE (1..256))
      MAX-ACCESS  read-only
      STATUS      current
      DESCRIPTION "Defines the name of the local or remote access point where the source is located."
      ::= { wtctBridgeRedirectEntry 40  }
   
   
   wtctBridgeRedirectSourceName OBJECT-TYPE
      SYNTAX      DisplayString (SIZE (1..256))
      MAX-ACCESS  read-only
      STATUS      current
      DESCRIPTION "Defines the name of a source queue or service. Specify a 
      JMS queue name, a TUXEDO queue name, or the name of a TUXEDO service."
      ::= { wtctBridgeRedirectEntry 45  }
   
   
   wtctBridgeRedirectSourceQspace OBJECT-TYPE
      SYNTAX      DisplayString (SIZE (1..256))
      MAX-ACCESS  read-only
      STATUS      current
      DESCRIPTION "Defines the name of the Qspace for a source location."
      ::= { wtctBridgeRedirectEntry 50  }
   
   
   wtctBridgeRedirectTargetAccessPoint OBJECT-TYPE
      SYNTAX      DisplayString (SIZE (1..256))
      MAX-ACCESS  read-only
      STATUS      current
      DESCRIPTION "Defines the name of the local or remote access point where the target is located."
      ::= { wtctBridgeRedirectEntry 55  }
   
   
   wtctBridgeRedirectTargetName OBJECT-TYPE
      SYNTAX      DisplayString (SIZE (1..256))
      MAX-ACCESS  read-only
      STATUS      current
      DESCRIPTION "Defines a target queue or service. Specify a JMS queue name, a TUXEDO queue name, 
      or the name of a TUXEDO service."
      ::= { wtctBridgeRedirectEntry 60  }
   
   
   wtctBridgeRedirectTargetQspace OBJECT-TYPE
      SYNTAX      DisplayString (SIZE (1..256))
      MAX-ACCESS  read-only
      STATUS      current
      DESCRIPTION "Defines the name of the Qspace for a target location."
      ::= { wtctBridgeRedirectEntry 65  }
   
   
   wtctBridgeRedirectTranslateFML OBJECT-TYPE
      SYNTAX      DisplayString (SIZE (1..256))
      MAX-ACCESS  read-only
      STATUS      current
      DESCRIPTION "Defines the type of XMl/FML translation."
      ::= { wtctBridgeRedirectEntry 70  }
   
   
   wsReliableDeliveryPolicyTable OBJECT-TYPE
      SYNTAX      SEQUENCE OF WsReliableDeliveryPolicyEntry
      MAX-ACCESS  not-accessible
      STATUS      current
      DESCRIPTION "This table represents a wsReliableDeliveryPolicy in the domain."
      ::= { wls 827  }
      
   
   wsReliableDeliveryPolicyEntry OBJECT-TYPE
      SYNTAX      WsReliableDeliveryPolicyEntry
      MAX-ACCESS  not-accessible
      STATUS      current
      DESCRIPTION "Entry of wsReliableDeliveryPolicyTable"
      INDEX { wsReliableDeliveryPolicyIndex}
      ::= { wsReliableDeliveryPolicyTable 1 }
      
   WsReliableDeliveryPolicyEntry ::=
      SEQUENCE
      {
         wsReliableDeliveryPolicyIndex DisplayString (SIZE (1..16)),
         wsReliableDeliveryPolicyObjectName DisplayString (SIZE (1..256)),
         wsReliableDeliveryPolicyType DisplayString (SIZE (1..64)),
         wsReliableDeliveryPolicyName DisplayString (SIZE (1..64)),
         wsReliableDeliveryPolicyParent DisplayString (SIZE (1..256)),
         wsReliableDeliveryPolicyDefaultRetryCount INTEGER,
         wsReliableDeliveryPolicyDefaultRetryInterval INTEGER,
         wsReliableDeliveryPolicyDefaultTimeToLive INTEGER
      }
      
   
   wsReliableDeliveryPolicyIndex OBJECT-TYPE
      SYNTAX      DisplayString (SIZE (1..16))
      MAX-ACCESS  read-only
      STATUS      current
      DESCRIPTION "Unique value directed from ObjectName which is used as table index"
      ::= { wsReliableDeliveryPolicyEntry 1  }
   
   
   wsReliableDeliveryPolicyObjectName OBJECT-TYPE
      SYNTAX      DisplayString (SIZE (1..256))
      MAX-ACCESS  read-only
      STATUS      current
      DESCRIPTION "JMX-standard MBean name"
      ::= { wsReliableDeliveryPolicyEntry 5  }
   
   
   wsReliableDeliveryPolicyType OBJECT-TYPE
      SYNTAX      DisplayString (SIZE (1..64))
      MAX-ACCESS  read-only
      STATUS      current
      DESCRIPTION "BEA-proprietary MBean type"
      ::= { wsReliableDeliveryPolicyEntry 10  }
   
   
   wsReliableDeliveryPolicyName OBJECT-TYPE
      SYNTAX      DisplayString (SIZE (1..64))
      MAX-ACCESS  read-only
      STATUS      current
      DESCRIPTION "BEA-proprietary MBean name"
      ::= { wsReliableDeliveryPolicyEntry 15  }
   
   
   wsReliableDeliveryPolicyParent OBJECT-TYPE
      SYNTAX      DisplayString (SIZE (1..256))
      MAX-ACCESS  read-only
      STATUS      current
      DESCRIPTION "BEA-proprietary Parent object's identification, with syntax
      <type>:<name>"
      ::= { wsReliableDeliveryPolicyEntry 20  }
   
   
   wsReliableDeliveryPolicyDefaultRetryCount OBJECT-TYPE
      SYNTAX      INTEGER
      MAX-ACCESS  read-only
      STATUS      current
      DESCRIPTION "Generated Object."
      ::= { wsReliableDeliveryPolicyEntry 21  }
   
   
   wsReliableDeliveryPolicyDefaultRetryInterval OBJECT-TYPE
      SYNTAX      INTEGER
      MAX-ACCESS  read-only
      STATUS      current
      DESCRIPTION "Generated Object."
      ::= { wsReliableDeliveryPolicyEntry 22  }
   
   
   wsReliableDeliveryPolicyDefaultTimeToLive OBJECT-TYPE
      SYNTAX      INTEGER
      MAX-ACCESS  read-only
      STATUS      current
      DESCRIPTION "Generated Object."
      ::= { wsReliableDeliveryPolicyEntry 23  }
   
   
   wtcPasswordTable OBJECT-TYPE
      SYNTAX      SEQUENCE OF WtcPasswordEntry
      MAX-ACCESS  not-accessible
      STATUS      current
      DESCRIPTION "This table represents a wtcPassword in the domain."
      ::= { wls 829  }
      
   
   wtcPasswordEntry OBJECT-TYPE
      SYNTAX      WtcPasswordEntry
      MAX-ACCESS  not-accessible
      STATUS      current
      DESCRIPTION "Entry of wtcPasswordTable"
      INDEX { wtcPasswordIndex}
      ::= { wtcPasswordTable 1 }
      
   WtcPasswordEntry ::=
      SEQUENCE
      {
         wtcPasswordIndex     DisplayString (SIZE (1..16)),
         wtcPasswordObjectName DisplayString (SIZE (1..256)),
         wtcPasswordType      DisplayString (SIZE (1..64)),
         wtcPasswordName      DisplayString (SIZE (1..64)),
         wtcPasswordParent    DisplayString (SIZE (1..256)),
         wtcPasswordLocalAccessPoint DisplayString,
         wtcPasswordRemoteAccessPoint DisplayString,
         wtcPasswordRemotePassword OCTET STRING,
         wtcPasswordRemotePasswordIV OCTET STRING,
         wtcPasswordLocalPasswordIV OCTET STRING,
         wtcPasswordLocalPassword OCTET STRING
      }
      
   
   wtcPasswordIndex OBJECT-TYPE
      SYNTAX      DisplayString (SIZE (1..16))
      MAX-ACCESS  read-only
      STATUS      current
      DESCRIPTION "Unique value directed from ObjectName which is used as table index"
      ::= { wtcPasswordEntry 1  }
   
   
   wtcPasswordObjectName OBJECT-TYPE
      SYNTAX      DisplayString (SIZE (1..256))
      MAX-ACCESS  read-only
      STATUS      current
      DESCRIPTION "JMX-standard MBean name"
      ::= { wtcPasswordEntry 5  }
   
   
   wtcPasswordType OBJECT-TYPE
      SYNTAX      DisplayString (SIZE (1..64))
      MAX-ACCESS  read-only
      STATUS      current
      DESCRIPTION "BEA-proprietary MBean type"
      ::= { wtcPasswordEntry 10  }
   
   
   wtcPasswordName OBJECT-TYPE
      SYNTAX      DisplayString (SIZE (1..64))
      MAX-ACCESS  read-only
      STATUS      current
      DESCRIPTION "BEA-proprietary MBean name"
      ::= { wtcPasswordEntry 15  }
   
   
   wtcPasswordParent OBJECT-TYPE
      SYNTAX      DisplayString (SIZE (1..256))
      MAX-ACCESS  read-only
      STATUS      current
      DESCRIPTION "BEA-proprietary Parent object's identification, with syntax
      <type>:<name>"
      ::= { wtcPasswordEntry 20  }
   
   
   wtcPasswordLocalAccessPoint OBJECT-TYPE
      SYNTAX      DisplayString
      MAX-ACCESS  read-only
      STATUS      current
      DESCRIPTION "Generated Object."
      ::= { wtcPasswordEntry 21  }
   
   
   wtcPasswordRemoteAccessPoint OBJECT-TYPE
      SYNTAX      DisplayString
      MAX-ACCESS  read-only
      STATUS      current
      DESCRIPTION "Generated Object."
      ::= { wtcPasswordEntry 22  }
   
   
   wtcPasswordRemotePassword OBJECT-TYPE
      SYNTAX      OCTET STRING
      MAX-ACCESS  read-only
      STATUS      current
      DESCRIPTION "The remote password used to authenticate connections between the local access point and remote access point.  Note: This password is used to authenticate connections between the local Tuxedo access point identified by LocalAccessPoint and the remote Tuxedo access point identified by RemoteAccessPoint."
      ::= { wtcPasswordEntry 23  }
   
   
   wtcPasswordRemotePasswordIV OBJECT-TYPE
      SYNTAX      OCTET STRING
      MAX-ACCESS  read-only
      STATUS      current
      DESCRIPTION "The initialization vector used to encrypt the remote password."
      ::= { wtcPasswordEntry 24  }
   
   
   wtcPasswordLocalPasswordIV OBJECT-TYPE
      SYNTAX      OCTET STRING
      MAX-ACCESS  read-only
      STATUS      current
      DESCRIPTION "The initialization vector used to encrypt the local password."
      ::= { wtcPasswordEntry 25  }
   
   
   wtcPasswordLocalPassword OBJECT-TYPE
      SYNTAX      OCTET STRING
      MAX-ACCESS  read-only
      STATUS      current
      DESCRIPTION "The local password used to authenticate connections between the local access point and the remote access point.  Note: This password is used to authenticate connections between the local Tuxedo access point identified by LocalAccessPoint and the remote Tuxedo access point identified by RemoteAccessPoint."
      ::= { wtcPasswordEntry 26  }
   
   
   wtcResourcesTable OBJECT-TYPE
      SYNTAX      SEQUENCE OF WtcResourcesEntry
      MAX-ACCESS  not-accessible
      STATUS      current
      DESCRIPTION "This table represents a wtcResources in the domain."
      ::= { wls 831  }
      
   
   wtcResourcesEntry OBJECT-TYPE
      SYNTAX      WtcResourcesEntry
      MAX-ACCESS  not-accessible
      STATUS      current
      DESCRIPTION "Entry of wtcResourcesTable"
      INDEX { wtcResourcesIndex}
      ::= { wtcResourcesTable 1 }
      
   WtcResourcesEntry ::=
      SEQUENCE
      {
         wtcResourcesIndex    DisplayString (SIZE (1..16)),
         wtcResourcesObjectName DisplayString (SIZE (1..256)),
         wtcResourcesType     DisplayString (SIZE (1..64)),
         wtcResourcesName     DisplayString (SIZE (1..64)),
         wtcResourcesParent   DisplayString (SIZE (1..256)),
         wtcResourcesFldTbl16Classes DisplayString,
         wtcResourcesFldTbl32Classes DisplayString,
         wtcResourcesTpUsrFile DisplayString,
         wtcResourcesViewTbl16Classes DisplayString,
         wtcResourcesViewTbl32Classes DisplayString,
         wtcResourcesAppPassword OCTET STRING,
         wtcResourcesRemoteMBEncoding OCTET STRING,
         wtcResourcesMBEncodingMapFile OCTET STRING,
         wtcResourcesAppPasswordIV OCTET STRING
      }
      
   
   wtcResourcesIndex OBJECT-TYPE
      SYNTAX      DisplayString (SIZE (1..16))
      MAX-ACCESS  read-only
      STATUS      current
      DESCRIPTION "Unique value directed from ObjectName which is used as table index"
      ::= { wtcResourcesEntry 1  }
   
   
   wtcResourcesObjectName OBJECT-TYPE
      SYNTAX      DisplayString (SIZE (1..256))
      MAX-ACCESS  read-only
      STATUS      current
      DESCRIPTION "JMX-standard MBean name"
      ::= { wtcResourcesEntry 5  }
   
   
   wtcResourcesType OBJECT-TYPE
      SYNTAX      DisplayString (SIZE (1..64))
      MAX-ACCESS  read-only
      STATUS      current
      DESCRIPTION "BEA-proprietary MBean type"
      ::= { wtcResourcesEntry 10  }
   
   
   wtcResourcesName OBJECT-TYPE
      SYNTAX      DisplayString (SIZE (1..64))
      MAX-ACCESS  read-only
      STATUS      current
      DESCRIPTION "BEA-proprietary MBean name"
      ::= { wtcResourcesEntry 15  }
   
   
   wtcResourcesParent OBJECT-TYPE
      SYNTAX      DisplayString (SIZE (1..256))
      MAX-ACCESS  read-only
      STATUS      current
      DESCRIPTION "BEA-proprietary Parent object's identification, with syntax
      <type>:<name>"
      ::= { wtcResourcesEntry 20  }
   
   
   wtcResourcesFldTbl16Classes OBJECT-TYPE
      SYNTAX      DisplayString
      MAX-ACCESS  read-only
      STATUS      current
      DESCRIPTION "Generated Object."
      ::= { wtcResourcesEntry 21  }
   
   
   wtcResourcesFldTbl32Classes OBJECT-TYPE
      SYNTAX      DisplayString
      MAX-ACCESS  read-only
      STATUS      current
      DESCRIPTION "Generated Object."
      ::= { wtcResourcesEntry 22  }
   
   
   wtcResourcesTpUsrFile OBJECT-TYPE
      SYNTAX      DisplayString
      MAX-ACCESS  read-only
      STATUS      current
      DESCRIPTION "Generated Object."
      ::= { wtcResourcesEntry 23  }
   
   
   wtcResourcesViewTbl16Classes OBJECT-TYPE
      SYNTAX      DisplayString
      MAX-ACCESS  read-only
      STATUS      current
      DESCRIPTION "Generated Object."
      ::= { wtcResourcesEntry 24  }
   
   
   wtcResourcesViewTbl32Classes OBJECT-TYPE
      SYNTAX      DisplayString
      MAX-ACCESS  read-only
      STATUS      current
      DESCRIPTION "Generated Object."
      ::= { wtcResourcesEntry 25  }
   
   
   wtcResourcesAppPassword OBJECT-TYPE
      SYNTAX      OCTET STRING
      MAX-ACCESS  read-only
      STATUS      current
      DESCRIPTION "The application password as returned from the genpasswd utility.  Note: This Tuxedo application password is the encrypted password used to authenticate connections."
      ::= { wtcResourcesEntry 26  }
   
   
   wtcResourcesRemoteMBEncoding OBJECT-TYPE
      SYNTAX      OCTET STRING
      MAX-ACCESS  read-only
      STATUS      current
      DESCRIPTION "The default encoding name of sending MBSTRING data."
      ::= { wtcResourcesEntry 27  }
   
   
   wtcResourcesMBEncodingMapFile OBJECT-TYPE
      SYNTAX      OCTET STRING
      MAX-ACCESS  read-only
      STATUS      current
      DESCRIPTION "The encoding name map file between Java and Tuxedo MBSTRING."
      ::= { wtcResourcesEntry 28  }
   
   
   wtcResourcesAppPasswordIV OBJECT-TYPE
      SYNTAX      OCTET STRING
      MAX-ACCESS  read-only
      STATUS      current
      DESCRIPTION "The initialization vector used to encrypt the AppPassword.  Note: This value is returned from the genpasswd utility with the AppPassword."
      ::= { wtcResourcesEntry 29  }
   
   
   adminConsoleTable OBJECT-TYPE
      SYNTAX      SEQUENCE OF AdminConsoleEntry
      MAX-ACCESS  not-accessible
      STATUS      current
      DESCRIPTION "AdminConsoleMBean is a console specific MBean to configure weblogic administration console attributes."
      ::= { wls 840  }
      
   
   adminConsoleEntry OBJECT-TYPE
      SYNTAX      AdminConsoleEntry
      MAX-ACCESS  not-accessible
      STATUS      current
      DESCRIPTION "Generated SNMP Table Entry."
      INDEX { adminConsoleIndex}
      ::= { adminConsoleTable 1 }
      
   AdminConsoleEntry ::=
      SEQUENCE
      {
         adminConsoleIndex    OCTET STRING,
         adminConsoleObjectName OCTET STRING,
         adminConsoleType     OCTET STRING,
         adminConsoleSessionTimeout Integer32,
         adminConsoleCookieName OCTET STRING,
         adminConsoleName     OCTET STRING
      }
      
   
   adminConsoleIndex OBJECT-TYPE
      SYNTAX      OCTET STRING
      MAX-ACCESS  not-accessible
      STATUS      current
      DESCRIPTION "Index column"
      ::= { adminConsoleEntry 1  }
   
   
   adminConsoleObjectName OBJECT-TYPE
      SYNTAX      OCTET STRING
      MAX-ACCESS  read-only
      STATUS      current
      DESCRIPTION "ObjectName column"
      ::= { adminConsoleEntry 2  }
   
   
   adminConsoleType OBJECT-TYPE
      SYNTAX      OCTET STRING
      MAX-ACCESS  read-only
      STATUS      current
      DESCRIPTION "Returns the type of the MBean."
      ::= { adminConsoleEntry 3  }
   
   
   adminConsoleSessionTimeout OBJECT-TYPE
      SYNTAX      Integer32
      MAX-ACCESS  read-only
      STATUS      current
      DESCRIPTION "Returns Session Timeout value (in seconds) for Administration Console."
      ::= { adminConsoleEntry 4  }
   
   
   adminConsoleCookieName OBJECT-TYPE
      SYNTAX      OCTET STRING
      MAX-ACCESS  read-only
      STATUS      current
      DESCRIPTION "Returns the Cookie Name used by the Administration Console."
      ::= { adminConsoleEntry 5  }
   
   
   adminConsoleName OBJECT-TYPE
      SYNTAX      OCTET STRING
      MAX-ACCESS  read-only
      STATUS      current
      DESCRIPTION "The user-specified name of this MBean instance.  This name is included as one of the key properties in the MBean's javax.management.ObjectName: Name=user-specified-name"
      ::= { adminConsoleEntry 6  }
   
   
   adminTable OBJECT-TYPE
      SYNTAX      SEQUENCE OF AdminEntry
      MAX-ACCESS  not-accessible
      STATUS      current
      DESCRIPTION "This class is left here as a tagging interface to support interop as clients of releases earlier than WLS 8.1"
      ::= { wls 845  }
      
   
   adminEntry OBJECT-TYPE
      SYNTAX      AdminEntry
      MAX-ACCESS  not-accessible
      STATUS      current
      DESCRIPTION "Generated SNMP Table Entry."
      INDEX { adminIndex}
      ::= { adminTable 1 }
      
   AdminEntry ::=
      SEQUENCE
      {
         adminIndex           OCTET STRING,
         adminObjectName      OCTET STRING,
         adminType            OCTET STRING,
         adminName            OCTET STRING
      }
      
   
   adminIndex OBJECT-TYPE
      SYNTAX      OCTET STRING
      MAX-ACCESS  not-accessible
      STATUS      current
      DESCRIPTION "Index column"
      ::= { adminEntry 1  }
   
   
   adminObjectName OBJECT-TYPE
      SYNTAX      OCTET STRING
      MAX-ACCESS  read-only
      STATUS      current
      DESCRIPTION "ObjectName column"
      ::= { adminEntry 2  }
   
   
   adminType OBJECT-TYPE
      SYNTAX      OCTET STRING
      MAX-ACCESS  read-only
      STATUS      current
      DESCRIPTION "Returns the type of the MBean."
      ::= { adminEntry 3  }
   
   
   adminName OBJECT-TYPE
      SYNTAX      OCTET STRING
      MAX-ACCESS  read-only
      STATUS      current
      DESCRIPTION "The user-specified name of this MBean instance.  This name is included as one of the key properties in the MBean's javax.management.ObjectName: Name=user-specified-name"
      ::= { adminEntry 4  }
   
   
   capacityTable OBJECT-TYPE
      SYNTAX      SEQUENCE OF CapacityEntry
      MAX-ACCESS  not-accessible
      STATUS      current
      DESCRIPTION "CapacityMBean defines the maximum number of requests that can be enqueued by all the work managers that share it.  The server starts rejecting requests once the capacity threshold is reached. Note that the capacity includes all requests, queued or executing, from the constrained work set. This constraint is independent of the global queue threshold specified by {@link OverloadProtectionMBean#getSharedCapacityForWorkManagers()}.   Requests are rejected by performing overload actions. RMI work is rejected by sending back a recoverable exception to the clients. Servlet requests are rejected by sending back a 503 response.   Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 850  }
      
   
   capacityEntry OBJECT-TYPE
      SYNTAX      CapacityEntry
      MAX-ACCESS  not-accessible
      STATUS      current
      DESCRIPTION "Generated SNMP Table Entry."
      INDEX { capacityIndex}
      ::= { capacityTable 1 }
      
   CapacityEntry ::=
      SEQUENCE
      {
         capacityIndex        OCTET STRING,
         capacityObjectName   OCTET STRING,
         capacityType         OCTET STRING,
         capacityDeploymentOrder Integer32,
         capacityCount        Integer32,
         capacityName         OCTET STRING
      }
      
   
   capacityIndex OBJECT-TYPE
      SYNTAX      OCTET STRING
      MAX-ACCESS  not-accessible
      STATUS      current
      DESCRIPTION "Index column"
      ::= { capacityEntry 1  }
   
   
   capacityObjectName OBJECT-TYPE
      SYNTAX      OCTET STRING
      MAX-ACCESS  read-only
      STATUS      current
      DESCRIPTION "ObjectName column"
      ::= { capacityEntry 2  }
   
   
   capacityType OBJECT-TYPE
      SYNTAX      OCTET STRING
      MAX-ACCESS  read-only
      STATUS      current
      DESCRIPTION "Returns the type of the MBean."
      ::= { capacityEntry 3  }
   
   
   capacityDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { capacityEntry 4  }
   
   
   capacityCount OBJECT-TYPE
      SYNTAX      Integer32
      MAX-ACCESS  read-only
      STATUS      current
      DESCRIPTION "Total number of requests that can be enqueued."
      ::= { capacityEntry 5  }
   
   
   capacityName OBJECT-TYPE
      SYNTAX      OCTET STRING
      MAX-ACCESS  read-only
      STATUS      current
      DESCRIPTION "The user-specified name of this MBean instance.  This name is included as one of the key properties in the MBean's javax.management.ObjectName: Name=user-specified-name"
      ::= { capacityEntry 6  }
   
   
   configurationPropertyTable OBJECT-TYPE
      SYNTAX      SEQUENCE OF ConfigurationPropertyEntry
      MAX-ACCESS  not-accessible
      STATUS      current
      DESCRIPTION "Encapsulates information about a property, such as its value and whether it is encrypted.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 855  }
      
   
   configurationPropertyEntry OBJECT-TYPE
      SYNTAX      ConfigurationPropertyEntry
      MAX-ACCESS  not-accessible
      STATUS      current
      DESCRIPTION "Generated SNMP Table Entry."
      INDEX { configurationPropertyIndex}
      ::= { configurationPropertyTable 1 }
      
   ConfigurationPropertyEntry ::=
      SEQUENCE
      {
         configurationPropertyIndex OCTET STRING,
         configurationPropertyObjectName OCTET STRING,
         configurationPropertyType OCTET STRING,
         configurationPropertyEncryptValueRequired OCTET STRING,
         configurationPropertyValue OCTET STRING,
         configurationPropertyName OCTET STRING
      }
      
   
   configurationPropertyIndex OBJECT-TYPE
      SYNTAX      OCTET STRING
      MAX-ACCESS  not-accessible
      STATUS      current
      DESCRIPTION "Index column"
      ::= { configurationPropertyEntry 1  }
   
   
   configurationPropertyObjectName OBJECT-TYPE
      SYNTAX      OCTET STRING
      MAX-ACCESS  read-only
      STATUS      current
      DESCRIPTION "ObjectName column"
      ::= { configurationPropertyEntry 2  }
   
   
   configurationPropertyType OBJECT-TYPE
      SYNTAX      OCTET STRING
      MAX-ACCESS  read-only
      STATUS      current
      DESCRIPTION "Returns the type of the MBean."
      ::= { configurationPropertyEntry 3  }
   
   
   configurationPropertyEncryptValueRequired OBJECT-TYPE
      SYNTAX      OCTET STRING
      MAX-ACCESS  read-only
      STATUS      current
      DESCRIPTION "Specifies whether the property should be encrypted.   By default, the value of a property is not encrypted and anyone using the Administration Console can view the value of the property. If this attribute is set to true, then the value of the property on the Administration Console will be set to all asterisks."
      ::= { configurationPropertyEntry 4  }
   
   
   configurationPropertyValue OBJECT-TYPE
      SYNTAX      OCTET STRING
      MAX-ACCESS  read-only
      STATUS      current
      DESCRIPTION "Specifies the value of the property.  If the property is encrypted, then attribute is null and one should use the EncryptedValue attribute to get the decrypted value."
      ::= { configurationPropertyEntry 5  }
   
   
   configurationPropertyName OBJECT-TYPE
      SYNTAX      OCTET STRING
      MAX-ACCESS  read-only
      STATUS      current
      DESCRIPTION "The user-specified name of this MBean instance.  This name is included as one of the key properties in the MBean's javax.management.ObjectName: Name=user-specified-name"
      ::= { configurationPropertyEntry 6  }
   
   
   contextCaseTable OBJECT-TYPE
      SYNTAX      SEQUENCE OF ContextCaseEntry
      MAX-ACCESS  not-accessible
      STATUS      current
      DESCRIPTION "This mbean defines the mapping between the current context (security principal, group etc) and the request class to use.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 860  }
      
   
   contextCaseEntry OBJECT-TYPE
      SYNTAX      ContextCaseEntry
      MAX-ACCESS  not-accessible
      STATUS      current
      DESCRIPTION "Generated SNMP Table Entry."
      INDEX { contextCaseIndex}
      ::= { contextCaseTable 1 }
      
   ContextCaseEntry ::=
      SEQUENCE
      {
         contextCaseIndex     OCTET STRING,
         contextCaseObjectName OCTET STRING,
         contextCaseType      OCTET STRING,
         contextCaseRequestClassName OCTET STRING,
         contextCaseDeploymentOrder Integer32,
         contextCaseGroupName OCTET STRING,
         contextCaseName      OCTET STRING,
         contextCaseUserName  OCTET STRING
      }
      
   
   contextCaseIndex OBJECT-TYPE
      SYNTAX      OCTET STRING
      MAX-ACCESS  not-accessible
      STATUS      current
      DESCRIPTION "Index column"
      ::= { contextCaseEntry 1  }
   
   
   contextCaseObjectName OBJECT-TYPE
      SYNTAX      OCTET STRING
      MAX-ACCESS  read-only
      STATUS      current
      DESCRIPTION "ObjectName column"
      ::= { contextCaseEntry 2  }
   
   
   contextCaseType OBJECT-TYPE
      SYNTAX      OCTET STRING
      MAX-ACCESS  read-only
      STATUS      current
      DESCRIPTION "Returns the type of the MBean."
      ::= { contextCaseEntry 3  }
   
   
   contextCaseRequestClassName OBJECT-TYPE
      SYNTAX      OCTET STRING
      MAX-ACCESS  read-only
      STATUS      current
      DESCRIPTION ""
      ::= { contextCaseEntry 4  }
   
   
   contextCaseDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { contextCaseEntry 5  }
   
   
   contextCaseGroupName OBJECT-TYPE
      SYNTAX      OCTET STRING
      MAX-ACCESS  read-only
      STATUS      current
      DESCRIPTION ""
      ::= { contextCaseEntry 6  }
   
   
   contextCaseName OBJECT-TYPE
      SYNTAX      OCTET STRING
      MAX-ACCESS  read-only
      STATUS      current
      DESCRIPTION "The user-specified name of this MBean instance.  This name is included as one of the key properties in the MBean's javax.management.ObjectName: Name=user-specified-name"
      ::= { contextCaseEntry 7  }
   
   
   contextCaseUserName OBJECT-TYPE
      SYNTAX      OCTET STRING
      MAX-ACCESS  read-only
      STATUS      current
      DESCRIPTION ""
      ::= { contextCaseEntry 8  }
   
   
   contextRequestClassTable OBJECT-TYPE
      SYNTAX      SEQUENCE OF ContextRequestClassEntry
      MAX-ACCESS  not-accessible
      STATUS      current
      DESCRIPTION "This mbean defines the mapping between the current context (security principal, group) and the request class to use.   ContextRequestClass provides a mapping between security names/groups and request classes. During work schedule, the exact request class is determined by looking at the security information of the caller. ContextRequestClass is not a request class by itself and is used to hold the mapping of request classes.   Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 865  }
      
   
   contextRequestClassEntry OBJECT-TYPE
      SYNTAX      ContextRequestClassEntry
      MAX-ACCESS  not-accessible
      STATUS      current
      DESCRIPTION "Generated SNMP Table Entry."
      INDEX { contextRequestClassIndex}
      ::= { contextRequestClassTable 1 }
      
   ContextRequestClassEntry ::=
      SEQUENCE
      {
         contextRequestClassIndex OCTET STRING,
         contextRequestClassObjectName OCTET STRING,
         contextRequestClassType OCTET STRING,
         contextRequestClassDeploymentOrder Integer32,
         contextRequestClassName OCTET STRING
      }
      
   
   contextRequestClassIndex OBJECT-TYPE
      SYNTAX      OCTET STRING
      MAX-ACCESS  not-accessible
      STATUS      current
      DESCRIPTION "Index column"
      ::= { contextRequestClassEntry 1  }
   
   
   contextRequestClassObjectName OBJECT-TYPE
      SYNTAX      OCTET STRING
      MAX-ACCESS  read-only
      STATUS      current
      DESCRIPTION "ObjectName column"
      ::= { contextRequestClassEntry 2  }
   
   
   contextRequestClassType OBJECT-TYPE
      SYNTAX      OCTET STRING
      MAX-ACCESS  read-only
      STATUS      current
      DESCRIPTION "Returns the type of the MBean."
      ::= { contextRequestClassEntry 3  }
   
   
   contextRequestClassDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { contextRequestClassEntry 4  }
   
   
   contextRequestClassName OBJECT-TYPE
      SYNTAX      OCTET STRING
      MAX-ACCESS  read-only
      STATUS      current
      DESCRIPTION "The user-specified name of this MBean instance.  This name is included as one of the key properties in the MBean's javax.management.ObjectName: Name=user-specified-name"
      ::= { contextRequestClassEntry 5  }
   
   
   conversationServiceTable OBJECT-TYPE
      SYNTAX      SEQUENCE OF ConversationServiceEntry
      MAX-ACCESS  not-accessible
      STATUS      current
      DESCRIPTION "Internal router for Conversation IDs"
      ::= { wls 870  }
      
   
   conversationServiceEntry OBJECT-TYPE
      SYNTAX      ConversationServiceEntry
      MAX-ACCESS  not-accessible
      STATUS      current
      DESCRIPTION "Generated SNMP Table Entry."
      INDEX { conversationServiceIndex}
      ::= { conversationServiceTable 1 }
      
   ConversationServiceEntry ::=
      SEQUENCE
      {
         conversationServiceIndex OCTET STRING,
         conversationServiceObjectName OCTET STRING,
         conversationServiceType OCTET STRING,
         conversationServiceDeploymentOrder Integer32,
         conversationServiceName OCTET STRING
      }
      
   
   conversationServiceIndex OBJECT-TYPE
      SYNTAX      OCTET STRING
      MAX-ACCESS  not-accessible
      STATUS      current
      DESCRIPTION "Index column"
      ::= { conversationServiceEntry 1  }
   
   
   conversationServiceObjectName OBJECT-TYPE
      SYNTAX      OCTET STRING
      MAX-ACCESS  read-only
      STATUS      current
      DESCRIPTION "ObjectName column"
      ::= { conversationServiceEntry 2  }
   
   
   conversationServiceType OBJECT-TYPE
      SYNTAX      OCTET STRING
      MAX-ACCESS  read-only
      STATUS      current
      DESCRIPTION "Returns the type of the MBean."
      ::= { conversationServiceEntry 3  }
   
   
   conversationServiceDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { conversationServiceEntry 4  }
   
   
   conversationServiceName OBJECT-TYPE
      SYNTAX      OCTET STRING
      MAX-ACCESS  read-only
      STATUS      current
      DESCRIPTION "The user-specified name of this MBean instance.  This name is included as one of the key properties in the MBean's javax.management.ObjectName: Name=user-specified-name"
      ::= { conversationServiceEntry 5  }
   
   
   customResourceTable OBJECT-TYPE
      SYNTAX      SEQUENCE OF CustomResourceEntry
      MAX-ACCESS  not-accessible
      STATUS      current
      DESCRIPTION "A CustomResource is an untyped SystemResource for which creator of the bean defines the name of the class that will be used when the resource is deployed on the managed server."
      ::= { wls 875  }
      
   
   customResourceEntry OBJECT-TYPE
      SYNTAX      CustomResourceEntry
      MAX-ACCESS  not-accessible
      STATUS      current
      DESCRIPTION "Generated SNMP Table Entry."
      INDEX { customResourceIndex}
      ::= { customResourceTable 1 }
      
   CustomResourceEntry ::=
      SEQUENCE
      {
         customResourceIndex  OCTET STRING,
         customResourceObjectName OCTET STRING,
         customResourceType   OCTET STRING,
         customResourceResourceClass OCTET STRING,
         customResourceCompatibilityName OCTET STRING,
         customResourceDeploymentOrder Integer32,
         customResourceDescriptorBeanClass OCTET STRING,
         customResourceDeploymentPrincipalName OCTET STRING,
         customResourceDescriptorFileName OCTET STRING,
         customResourceModuleType OCTET STRING,
         customResourceName   OCTET STRING,
         customResourceSourcePath OCTET STRING
      }
      
   
   customResourceIndex OBJECT-TYPE
      SYNTAX      OCTET STRING
      MAX-ACCESS  not-accessible
      STATUS      current
      DESCRIPTION "Index column"
      ::= { customResourceEntry 1  }
   
   
   customResourceObjectName OBJECT-TYPE
      SYNTAX      OCTET STRING
      MAX-ACCESS  read-only
      STATUS      current
      DESCRIPTION "ObjectName column"
      ::= { customResourceEntry 2  }
   
   
   customResourceType OBJECT-TYPE
      SYNTAX      OCTET STRING
      MAX-ACCESS  read-only
      STATUS      current
      DESCRIPTION "Returns the type of the MBean."
      ::= { customResourceEntry 3  }
   
   
   customResourceResourceClass OBJECT-TYPE
      SYNTAX      OCTET STRING
      MAX-ACCESS  read-only
      STATUS      current
      DESCRIPTION "This is the name of the class that is used to manage the lifecycle of the resource.  An instance of the ResourceClass is created and is passed the DescriptorBean.  If this value is not set then the resource does not participate in the deployment lifecycle and simply represent a distribution of configuration information to be used by other subsystems."
      ::= { customResourceEntry 4  }
   
   
   customResourceCompatibilityName OBJECT-TYPE
      SYNTAX      OCTET STRING
      MAX-ACCESS  read-only
      STATUS      current
      DESCRIPTION "This is only set for beans created as a result of conversion from an 8.1 application configured using ApplicationMBean and ComponentMBean.  Standalone modules in 8.1 have both an ApplicationMBean name and ComponentMBean name. This attribute stores the name of the latter, to be used when the server creates the transient ComponentMBean for backward compatibility."
      ::= { customResourceEntry 5  }
   
   
   customResourceDeploymentOrder OBJECT-TYPE
      SYNTAX      Integer32
      MAX-ACCESS  read-only
      STATUS      current
      DESCRIPTION "A numerical value that indicates when this unit is deployed, relative to other DeployableUnits on a server, during startup.  Units with lower Load Order values are deployed before those with higher values."
      ::= { customResourceEntry 6  }
   
   
   customResourceDescriptorBeanClass OBJECT-TYPE
      SYNTAX      OCTET STRING
      MAX-ACCESS  read-only
      STATUS      current
      DESCRIPTION "Returns the interface of the bean that is returned by the #getResource method."
      ::= { customResourceEntry 7  }
   
   
   customResourceDeploymentPrincipalName OBJECT-TYPE
      SYNTAX      OCTET STRING
      MAX-ACCESS  read-only
      STATUS      current
      DESCRIPTION "A string value that indicates what principal should be used when deploying the file or archive during startup and shutdown. This principal will be used to set the current subject when calling out into application code for interfaces such as ApplicationLifecycleListener, If no principal name is specifed, then the anonymous principal will be used."
      ::= { customResourceEntry 8  }
   
   
   customResourceDescriptorFileName OBJECT-TYPE
      SYNTAX      OCTET STRING
      MAX-ACCESS  read-only
      STATUS      current
      DESCRIPTION "The name of the file that contains the module. By default the file resides in the DOMAIN_DIR/config directory. By default, the file name is derived from the bean name using the following pattern:  &lt; beanName &gt;.xml  Note that this is a read-only property that can only be set when the bean is created."
      ::= { customResourceEntry 9  }
   
   
   customResourceModuleType OBJECT-TYPE
      SYNTAX      OCTET STRING
      MAX-ACCESS  read-only
      STATUS      current
      DESCRIPTION "The values match those defined by jsr88. This attribute may move to another MBean."
      ::= { customResourceEntry 10  }
   
   
   customResourceName OBJECT-TYPE
      SYNTAX      OCTET STRING
      MAX-ACCESS  read-only
      STATUS      current
      DESCRIPTION "Unique identifier for this bean instance."
      ::= { customResourceEntry 11  }
   
   
   customResourceSourcePath OBJECT-TYPE
      SYNTAX      OCTET STRING
      MAX-ACCESS  read-only
      STATUS      current
      DESCRIPTION ""
      ::= { customResourceEntry 12  }
   
   
   databaseLessLeasingBasisTable OBJECT-TYPE
      SYNTAX      SEQUENCE OF DatabaseLessLeasingBasisEntry
      MAX-ACCESS  not-accessible
      STATUS      current
      DESCRIPTION "DatabaseLessLeasingBasisMBean defines attributes related to the functioning of singleton services and server migration without the use of a HA database."
      ::= { wls 880  }
      
   
   databaseLessLeasingBasisEntry OBJECT-TYPE
      SYNTAX      DatabaseLessLeasingBasisEntry
      MAX-ACCESS  not-accessible
      STATUS      current
      DESCRIPTION "Generated SNMP Table Entry."
      INDEX { databaseLessLeasingBasisIndex}
      ::= { databaseLessLeasingBasisTable 1 }
      
   DatabaseLessLeasingBasisEntry ::=
      SEQUENCE
      {
         databaseLessLeasingBasisIndex OCTET STRING,
         databaseLessLeasingBasisObjectName OCTET STRING,
         databaseLessLeasingBasisType OCTET STRING,
         databaseLessLeasingBasisMemberDiscoveryTimeout Integer32,
         databaseLessLeasingBasisName OCTET STRING
      }
      
   
   databaseLessLeasingBasisIndex OBJECT-TYPE
      SYNTAX      OCTET STRING
      MAX-ACCESS  not-accessible
      STATUS      current
      DESCRIPTION "Index column"
      ::= { databaseLessLeasingBasisEntry 1  }
   
   
   databaseLessLeasingBasisObjectName OBJECT-TYPE
      SYNTAX      OCTET STRING
      MAX-ACCESS  read-only
      STATUS      current
      DESCRIPTION "ObjectName column"
      ::= { databaseLessLeasingBasisEntry 2  }
   
   
   databaseLessLeasingBasisType OBJECT-TYPE
      SYNTAX      OCTET STRING
      MAX-ACCESS  read-only
      STATUS      current
      DESCRIPTION "Returns the type of the MBean."
      ::= { databaseLessLeasingBasisEntry 3  }
   
   
   databaseLessLeasingBasisMemberDiscoveryTimeout OBJECT-TYPE
      SYNTAX      Integer32
      MAX-ACCESS  read-only
      STATUS      current
      DESCRIPTION "Gets the MemberDiscoveryTimeout value. This value defines the amount of time a server waits during or after startup to discover members that belong to the same cluster. This information is used to join or form a new cluster."
      ::= { databaseLessLeasingBasisEntry 4  }
   
   
   databaseLessLeasingBasisName OBJECT-TYPE
      SYNTAX      OCTET STRING
      MAX-ACCESS  read-only
      STATUS      current
      DESCRIPTION "The user-specified name of this MBean instance.  This name is included as one of the key properties in the MBean's javax.management.ObjectName: Name=user-specified-name"
      ::= { databaseLessLeasingBasisEntry 5  }
   
   
   debugScopeTable OBJECT-TYPE
      SYNTAX      SEQUENCE OF DebugScopeEntry
      MAX-ACCESS  not-accessible
      STATUS      current
      DESCRIPTION "This interface captures whether the enabled state of a debug scope. The name of a debug scope is the fully qualified scope name for example weblogic.security.SSL"
      ::= { wls 885  }
      
   
   debugScopeEntry OBJECT-TYPE
      SYNTAX      DebugScopeEntry
      MAX-ACCESS  not-accessible
      STATUS      current
      DESCRIPTION "Generated SNMP Table Entry."
      INDEX { debugScopeIndex}
      ::= { debugScopeTable 1 }
      
   DebugScopeEntry ::=
      SEQUENCE
      {
         debugScopeIndex      OCTET STRING,
         debugScopeObjectName OCTET STRING,
         debugScopeType       OCTET STRING
      }
      
   
   debugScopeIndex OBJECT-TYPE
      SYNTAX      OCTET STRING
      MAX-ACCESS  not-accessible
      STATUS      current
      DESCRIPTION "Index column"
      ::= { debugScopeEntry 1  }
   
   
   debugScopeObjectName OBJECT-TYPE
      SYNTAX      OCTET STRING
      MAX-ACCESS  read-only
      STATUS      current
      DESCRIPTION "ObjectName column"
      ::= { debugScopeEntry 2  }
   
   
   debugScopeType OBJECT-TYPE
      SYNTAX      OCTET STRING
      MAX-ACCESS  read-only
      STATUS      current
      DESCRIPTION "Returns the type of the MBean."
      ::= { debugScopeEntry 3  }
   
   
   defaultFileStoreTable OBJECT-TYPE
      SYNTAX      SEQUENCE OF DefaultFileStoreEntry
      MAX-ACCESS  not-accessible
      STATUS      current
      DESCRIPTION "This MBean describes the configuration of the default file store. Each WebLogic Server instance has a default file store.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 890  }
      
   
   defaultFileStoreEntry OBJECT-TYPE
      SYNTAX      DefaultFileStoreEntry
      MAX-ACCESS  not-accessible
      STATUS      current
      DESCRIPTION "Generated SNMP Table Entry."
      INDEX { defaultFileStoreIndex}
      ::= { defaultFileStoreTable 1 }
      
   DefaultFileStoreEntry ::=
      SEQUENCE
      {
         defaultFileStoreIndex OCTET STRING,
         defaultFileStoreObjectName OCTET STRING,
         defaultFileStoreType OCTET STRING,
         defaultFileStoreName OCTET STRING
      }
      
   
   defaultFileStoreIndex OBJECT-TYPE
      SYNTAX      OCTET STRING
      MAX-ACCESS  not-accessible
      STATUS      current
      DESCRIPTION "Index column"
      ::= { defaultFileStoreEntry 1  }
   
   
   defaultFileStoreObjectName OBJECT-TYPE
      SYNTAX      OCTET STRING
      MAX-ACCESS  read-only
      STATUS      current
      DESCRIPTION "ObjectName column"
      ::= { defaultFileStoreEntry 2  }
   
   
   defaultFileStoreType OBJECT-TYPE
      SYNTAX      OCTET STRING
      MAX-ACCESS  read-only
      STATUS      current
      DESCRIPTION "Returns the type of the MBean."
      ::= { defaultFileStoreEntry 3  }
   
   
   defaultFileStoreName OBJECT-TYPE
      SYNTAX      OCTET STRING
      MAX-ACCESS  read-only
      STATUS      current
      DESCRIPTION "The user-specified name of this MBean instance.  This name is included as one of the key properties in the MBean's javax.management.ObjectName: Name=user-specified-name"
      ::= { defaultFileStoreEntry 4  }
   
   
   deploymentConfigurationTable OBJECT-TYPE
      SYNTAX      SEQUENCE OF DeploymentConfigurationEntry
      MAX-ACCESS  not-accessible
      STATUS      current
      DESCRIPTION "Specifies the domain-level deployment configuration attributes.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 895  }
      
   
   deploymentConfigurationEntry OBJECT-TYPE
      SYNTAX      DeploymentConfigurationEntry
      MAX-ACCESS  not-accessible
      STATUS      current
      DESCRIPTION "Generated SNMP Table Entry."
      INDEX { deploymentConfigurationIndex}
      ::= { deploymentConfigurationTable 1 }
      
   DeploymentConfigurationEntry ::=
      SEQUENCE
      {
         deploymentConfigurationIndex OCTET STRING,
         deploymentConfigurationObjectName OCTET STRING,
         deploymentConfigurationType OCTET STRING,
         deploymentConfigurationRemoteDeployerEJBEnabled OCTET STRING,
         deploymentConfigurationName OCTET STRING
      }
      
   
   deploymentConfigurationIndex OBJECT-TYPE
      SYNTAX      OCTET STRING
      MAX-ACCESS  not-accessible
      STATUS      current
      DESCRIPTION "Index column"
      ::= { deploymentConfigurationEntry 1  }
   
   
   deploymentConfigurationObjectName OBJECT-TYPE
      SYNTAX      OCTET STRING
      MAX-ACCESS  read-only
      STATUS      current
      DESCRIPTION "ObjectName column"
      ::= { deploymentConfigurationEntry 2  }
   
   
   deploymentConfigurationType OBJECT-TYPE
      SYNTAX      OCTET STRING
      MAX-ACCESS  read-only
      STATUS      current
      DESCRIPTION "Returns the type of the MBean."
      ::= { deploymentConfigurationEntry 3  }
   
   
   deploymentConfigurationRemoteDeployerEJBEnabled OBJECT-TYPE
      SYNTAX      OCTET STRING
      MAX-ACCESS  read-only
      STATUS      current
      DESCRIPTION "Specifies whether the Remote Deployer EJB is automatically deployed in the current domain. The Remote Deployer EJB is only used by the weblogic.Deployer tool in the WLS 9.0 and 9.1 releases when the -remote option is specified.  If the Remote Deployer EJB is not deployed, you will not be able to use the -remote option in weblogic.Deployer running in a 9.0 or 9.1 installation. You can still use the -remote option from weblogic.Deployer in 9.2 or later releases."
      ::= { deploymentConfigurationEntry 4  }
   
   
   deploymentConfigurationName OBJECT-TYPE
      SYNTAX      OCTET STRING
      MAX-ACCESS  read-only
      STATUS      current
      DESCRIPTION "The user-specified name of this MBean instance.  This name is included as one of the key properties in the MBean's javax.management.ObjectName: Name=user-specified-name"
      ::= { deploymentConfigurationEntry 5  }
   
   
   domainLibraryTable OBJECT-TYPE
      SYNTAX      SEQUENCE OF DomainLibraryEntry
      MAX-ACCESS  not-accessible
      STATUS      current
      DESCRIPTION "Configuration bean for Libraries.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 900  }
      
   
   domainLibraryEntry OBJECT-TYPE
      SYNTAX      DomainLibraryEntry
      MAX-ACCESS  not-accessible
      STATUS      current
      DESCRIPTION "Generated SNMP Table Entry."
      INDEX { domainLibraryIndex}
      ::= { domainLibraryTable 1 }
      
   DomainLibraryEntry ::=
      SEQUENCE
      {
         domainLibraryIndex   OCTET STRING,
         domainLibraryObjectName OCTET STRING,
         domainLibraryType    OCTET STRING,
         domainLibraryCompatibilityName OCTET STRING,
         domainLibraryApplicationName OCTET STRING,
         domainLibraryAbsolutePlanDir OCTET STRING,
         domainLibraryAbsolutePlanPath OCTET STRING,
         domainLibraryStagingMode OCTET STRING,
         domainLibraryInstallDir OCTET STRING,
         domainLibraryValidateDDSecurityData OCTET STRING,
         domainLibraryName    OCTET STRING,
         domainLibraryAbsoluteSourcePath OCTET STRING,
         domainLibrarySourcePath OCTET STRING,
         domainLibraryAbsoluteInstallDir OCTET STRING,
         domainLibraryDeploymentOrder Integer32,
         domainLibrarySecurityDDModel OCTET STRING,
         domainLibraryApplicationIdentifier OCTET STRING,
         domainLibraryDeploymentPrincipalName OCTET STRING,
         domainLibraryPlanDir OCTET STRING,
         domainLibraryPlanPath OCTET STRING,
         domainLibraryVersionIdentifier OCTET STRING,
         domainLibraryModuleType OCTET STRING
      }
      
   
   domainLibraryIndex OBJECT-TYPE
      SYNTAX      OCTET STRING
      MAX-ACCESS  not-accessible
      STATUS      current
      DESCRIPTION "Index column"
      ::= { domainLibraryEntry 1  }
   
   
   domainLibraryObjectName OBJECT-TYPE
      SYNTAX      OCTET STRING
      MAX-ACCESS  read-only
      STATUS      current
      DESCRIPTION "ObjectName column"
      ::= { domainLibraryEntry 2  }
   
   
   domainLibraryType OBJECT-TYPE
      SYNTAX      OCTET STRING
      MAX-ACCESS  read-only
      STATUS      current
      DESCRIPTION "Returns the type of the MBean."
      ::= { domainLibraryEntry 3  }
   
   
   domainLibraryCompatibilityName OBJECT-TYPE
      SYNTAX      OCTET STRING
      MAX-ACCESS  read-only
      STATUS      current
      DESCRIPTION "This is only set for beans created as a result of conversion from an 8.1 application configured using ApplicationMBean and ComponentMBean.  Standalone modules in 8.1 have both an ApplicationMBean name and ComponentMBean name. This attribute stores the name of the latter, to be used when the server creates the transient ComponentMBean for backward compatibility."
      ::= { domainLibraryEntry 4  }
   
   
   domainLibraryApplicationName OBJECT-TYPE
      SYNTAX      OCTET STRING
      MAX-ACCESS  read-only
      STATUS      current
      DESCRIPTION "The name of the application. Note that the name of the current MBean is not the name of the application."
      ::= { domainLibraryEntry 5  }
   
   
   domainLibraryAbsolutePlanDir OBJECT-TYPE
      SYNTAX      OCTET STRING
      MAX-ACCESS  read-only
      STATUS      current
      DESCRIPTION "The fully resolved location of this application's deployment plan directory on the admin server."
      ::= { domainLibraryEntry 6  }
   
   
   domainLibraryAbsolutePlanPath OBJECT-TYPE
      SYNTAX      OCTET STRING
      MAX-ACCESS  read-only
      STATUS      current
      DESCRIPTION "The fully resolved location of this application's deployment plan on the admin server."
      ::= { domainLibraryEntry 7  }
   
   
   domainLibraryStagingMode OBJECT-TYPE
      SYNTAX      OCTET STRING
      MAX-ACCESS  read-only
      STATUS      current
      DESCRIPTION "The mode that specifies whether a deployment's files are copied from a source on the Administration Server to the Managed Server's staging area during application preparation.  Staging mode for an application can only be set the first time the application is deployed. Once staging mode for an application is set, it cannot be changed while the application is configured in the domain. The only way to change staging mode is to undeploy then redeploy the application. This attribute overrides the server's staging mode."
      ::= { domainLibraryEntry 8  }
   
   
   domainLibraryInstallDir OBJECT-TYPE
      SYNTAX      OCTET STRING
      MAX-ACCESS  read-only
      STATUS      current
      DESCRIPTION "The path to application's install-root directory, relative to the domain/config/deployments directory. When the Install Directory is specified, SourcePath, PlanDir, and PlanPath are derived from this path, and need not be specified. Default value for this is the name of the deployment."
      ::= { domainLibraryEntry 9  }
   
   
   domainLibraryValidateDDSecurityData OBJECT-TYPE
      SYNTAX      OCTET STRING
      MAX-ACCESS  read-only
      STATUS      current
      DESCRIPTION "This attribute is not used in the current BEA release."
      ::= { domainLibraryEntry 10  }
   
   
   domainLibraryName OBJECT-TYPE
      SYNTAX      OCTET STRING
      MAX-ACCESS  read-only
      STATUS      current
      DESCRIPTION "Unique identifier for this bean instance."
      ::= { domainLibraryEntry 11  }
   
   
   domainLibraryAbsoluteSourcePath OBJECT-TYPE
      SYNTAX      OCTET STRING
      MAX-ACCESS  read-only
      STATUS      current
      DESCRIPTION "The fully resolved location of this application's source files on the admin server."
      ::= { domainLibraryEntry 12  }
   
   
   domainLibrarySourcePath OBJECT-TYPE
      SYNTAX      OCTET STRING
      MAX-ACCESS  read-only
      STATUS      current
      DESCRIPTION "The path to the source of the deployable unit on the Administration Server. Rules:  If InstallDir is null, the source path must be an absolute path. If the source path is relative, it is resolved relative to InstallDir/app.  Use AbsoluteSourcePath to get a fully resolved value."
      ::= { domainLibraryEntry 13  }
   
   
   domainLibraryAbsoluteInstallDir OBJECT-TYPE
      SYNTAX      OCTET STRING
      MAX-ACCESS  read-only
      STATUS      current
      DESCRIPTION "The fully resolved location of this application's installation root directory on the admin server."
      ::= { domainLibraryEntry 14  }
   
   
   domainLibraryDeploymentOrder OBJECT-TYPE
      SYNTAX      Integer32
      MAX-ACCESS  read-only
      STATUS      current
      DESCRIPTION "A numerical value that indicates when this unit is deployed, relative to other DeployableUnits on a server, during startup.  Units with lower Load Order values are deployed before those with higher values."
      ::= { domainLibraryEntry 15  }
   
   
   domainLibrarySecurityDDModel OBJECT-TYPE
      SYNTAX      OCTET STRING
      MAX-ACCESS  read-only
      STATUS      current
      DESCRIPTION "The security model that is used to secure a deployed module.  To set this value, you can use the weblogic.Deployer command-line tool, the Deployment Assistant in the Administration Console, the WebLogic Scripting Tool (WLST), or some other JMX client.  If you deploy a module using one of the previously mentioned tools and you do not specify a security model value, the module is secured with the security realm's default model ( see {@link weblogic.security.RealmMBean#getSecurityDDModel RealmMBean SecurityDDModel}).  If you deploy a module by modifying the domain's config.xml file and restarting the server, and if you do not specify a security model value for the module in config.xml, the module is secured with the DDOnly model, which is the default value of this AppDeploymentMBean attribute.  In summary, the order of precedence for the value of this attribute is as follows:   If you deploy a module using a runtime deployment utility, the order of precedence is: The value set by the deployment utility. The value set as the security realm's default security model.  If you deploy a module by modifying config.xml and restarting the server, the order of precedence is: The value that you specify for the module in config.xml. The default value of this AppDeploymentMBean SecurityDDModel attribute."
      ::= { domainLibraryEntry 16  }
   
   
   domainLibraryApplicationIdentifier OBJECT-TYPE
      SYNTAX      OCTET STRING
      MAX-ACCESS  read-only
      STATUS      current
      DESCRIPTION "The Application Identifier of the application version uniquely identifies the application version across all versions of all applications. If the application is not versioned, the Application Identifier is the same as the application name."
      ::= { domainLibraryEntry 17  }
   
   
   domainLibraryDeploymentPrincipalName OBJECT-TYPE
      SYNTAX      OCTET STRING
      MAX-ACCESS  read-only
      STATUS      current
      DESCRIPTION "A string value that indicates what principal should be used when deploying the file or archive during startup and shutdown. This principal will be used to set the current subject when calling out into application code for interfaces such as ApplicationLifecycleListener, If no principal name is specifed, then the anonymous principal will be used."
      ::= { domainLibraryEntry 18  }
   
   
   domainLibraryPlanDir OBJECT-TYPE
      SYNTAX      OCTET STRING
      MAX-ACCESS  read-only
      STATUS      current
      DESCRIPTION "The location of this application's configuration area. This directory can contain external descriptor files as specified within the deployment plan document.  Rules:  If InstallDir is null, plan directory should be an absolute path. If the plan directory is a relative path, it is resolved relative to InstallDir.   Use AbsolutePlanDir to get a fully resolved value."
      ::= { domainLibraryEntry 19  }
   
   
   domainLibraryPlanPath OBJECT-TYPE
      SYNTAX      OCTET STRING
      MAX-ACCESS  read-only
      STATUS      current
      DESCRIPTION "The path to the deployment plan document on Administration Server. Rules:  If PlanDir is null, the plan path must be an absolute path. If the plan path is a relative path, it is resolved relative to PlanDir.  Use AbsolutePlanPath to get a fully resolved value. If there is no plan, this returns no plan specified."
      ::= { domainLibraryEntry 20  }
   
   
   domainLibraryVersionIdentifier OBJECT-TYPE
      SYNTAX      OCTET STRING
      MAX-ACCESS  read-only
      STATUS      current
      DESCRIPTION "Uniquely identifies the application version across all versions of the same application. If the application is not versioned, this returns null."
      ::= { domainLibraryEntry 21  }
   
   
   domainLibraryModuleType OBJECT-TYPE
      SYNTAX      OCTET STRING
      MAX-ACCESS  read-only
      STATUS      current
      DESCRIPTION "The values match those defined by jsr88. This attribute may move to another MBean."
      ::= { domainLibraryEntry 22  }
   
   
   embeddedLDAPTable OBJECT-TYPE
      SYNTAX      SEQUENCE OF EmbeddedLDAPEntry
      MAX-ACCESS  not-accessible
      STATUS      current
      DESCRIPTION "The MBean that defines the configuration properties for the embedded LDAP server for the WebLogic domain."
      ::= { wls 905  }
      
   
   embeddedLDAPEntry OBJECT-TYPE
      SYNTAX      EmbeddedLDAPEntry
      MAX-ACCESS  not-accessible
      STATUS      current
      DESCRIPTION "Generated SNMP Table Entry."
      INDEX { embeddedLDAPIndex}
      ::= { embeddedLDAPTable 1 }
      
   EmbeddedLDAPEntry ::=
      SEQUENCE
      {
         embeddedLDAPIndex    OCTET STRING,
         embeddedLDAPObjectName OCTET STRING,
         embeddedLDAPType     OCTET STRING,
         embeddedLDAPTimeout  Integer32,
         embeddedLDAPAnonymousBindAllowed OCTET STRING,
         embeddedLDAPMasterFirst OCTET STRING,
         embeddedLDAPCacheTTL Integer32,
         embeddedLDAPBackupCopies Integer32,
         embeddedLDAPRefreshReplicaAtStartup OCTET STRING,
         embeddedLDAPBackupMinute Integer32,
         embeddedLDAPCacheSize Integer32,
         embeddedLDAPBackupHour Integer32,
         embeddedLDAPName     OCTET STRING,
         embeddedLDAPCacheEnabled OCTET STRING
      }
      
   
   embeddedLDAPIndex OBJECT-TYPE
      SYNTAX      OCTET STRING
      MAX-ACCESS  not-accessible
      STATUS      current
      DESCRIPTION "Index column"
      ::= { embeddedLDAPEntry 1  }
   
   
   embeddedLDAPObjectName OBJECT-TYPE
      SYNTAX      OCTET STRING
      MAX-ACCESS  read-only
      STATUS      current
      DESCRIPTION "ObjectName column"
      ::= { embeddedLDAPEntry 2  }
   
   
   embeddedLDAPType OBJECT-TYPE
      SYNTAX      OCTET STRING
      MAX-ACCESS  read-only
      STATUS      current
      DESCRIPTION "Returns the type of the MBean."
      ::= { embeddedLDAPEntry 3  }
   
   
   embeddedLDAPTimeout OBJECT-TYPE
      SYNTAX      Integer32
      MAX-ACCESS  read-only
      STATUS      current
      DESCRIPTION "Specifies the maximum number of seconds to wait for results from the embedded LDAP server before timing out. If this option is set to 0, there is no maximum time limit."
      ::= { embeddedLDAPEntry 4  }
   
   
   embeddedLDAPAnonymousBindAllowed OBJECT-TYPE
      SYNTAX      OCTET STRING
      MAX-ACCESS  read-only
      STATUS      current
      DESCRIPTION "Specifies whether the embedded LDAP server should allow anonymous connections."
      ::= { embeddedLDAPEntry 5  }
   
   
   embeddedLDAPMasterFirst OBJECT-TYPE
      SYNTAX      OCTET STRING
      MAX-ACCESS  read-only
      STATUS      current
      DESCRIPTION "Specifies whether a Managed Server should always connect to the master LDAP server (contained in the Administration Server), instead of connecting to the local replicated LDAP server (contained in the Managed Server)."
      ::= { embeddedLDAPEntry 6  }
   
   
   embeddedLDAPCacheTTL OBJECT-TYPE
      SYNTAX      Integer32
      MAX-ACCESS  read-only
      STATUS      current
      DESCRIPTION "The time-to-live of the cache (in seconds) that is used with the embedded LDAP server."
      ::= { embeddedLDAPEntry 7  }
   
   
   embeddedLDAPBackupCopies OBJECT-TYPE
      SYNTAX      Integer32
      MAX-ACCESS  read-only
      STATUS      current
      DESCRIPTION "The maximum number of backup copies that should be made for the embedded LDAP server.  This value limits the number of zip files in the ldap/backup directory."
      ::= { embeddedLDAPEntry 8  }
   
   
   embeddedLDAPRefreshReplicaAtStartup OBJECT-TYPE
      SYNTAX      OCTET STRING
      MAX-ACCESS  read-only
      STATUS      current
      DESCRIPTION "Specifies whether a Managed Server should refresh all replicated data at boot time. (This is useful if you have made a large amount of changes when the Managed Server was not active, and you want to download the entire replica instead of having the Administration Server push each change to the Managed Server.)"
      ::= { embeddedLDAPEntry 9  }
   
   
   embeddedLDAPBackupMinute OBJECT-TYPE
      SYNTAX      Integer32
      MAX-ACCESS  read-only
      STATUS      current
      DESCRIPTION "The minute at which the embedded LDAP server should be backed up.  The Backup Minute value is used in conjunction with the Back Up Hour value to determine the time at which the embedded LDAP server data files are backed up"
      ::= { embeddedLDAPEntry 10  }
   
   
   embeddedLDAPCacheSize OBJECT-TYPE
      SYNTAX      Integer32
      MAX-ACCESS  read-only
      STATUS      current
      DESCRIPTION "The size of the cache (in kilobytes) that is used with the embedded LDAP server."
      ::= { embeddedLDAPEntry 11  }
   
   
   embeddedLDAPBackupHour OBJECT-TYPE
      SYNTAX      Integer32
      MAX-ACCESS  read-only
      STATUS      current
      DESCRIPTION "The hour at which the embedded LDAP server should be backed up.  The Backup Hour value is used in conjunction with the Backup Minute value to determine the time at which the embedded LDAP server data files are backed up. At the specified time, WebLogic Server suspends writes to the embedded LDAP server, backs up the data files into a zip files in the ldap/backup directory, and then resumes writes."
      ::= { embeddedLDAPEntry 12  }
   
   
   embeddedLDAPName OBJECT-TYPE
      SYNTAX      OCTET STRING
      MAX-ACCESS  read-only
      STATUS      current
      DESCRIPTION "The user-specified name of this MBean instance.  This name is included as one of the key properties in the MBean's javax.management.ObjectName: Name=user-specified-name"
      ::= { embeddedLDAPEntry 13  }
   
   
   embeddedLDAPCacheEnabled OBJECT-TYPE
      SYNTAX      OCTET STRING
      MAX-ACCESS  read-only
      STATUS      current
      DESCRIPTION "Specifies whether a cache is used with the embedded LDAP server.  This cache is used when a managed server is reading or writing to the master embedded LDAP server that is running on the Administration server."
      ::= { embeddedLDAPEntry 14  }
   
   
   errorHandlingTable OBJECT-TYPE
      SYNTAX      SEQUENCE OF ErrorHandlingEntry
      MAX-ACCESS  not-accessible
      STATUS      current
      DESCRIPTION "Fake ErrorHandlingMBean  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 910  }
      
   
   errorHandlingEntry OBJECT-TYPE
      SYNTAX      ErrorHandlingEntry
      MAX-ACCESS  not-accessible
      STATUS      current
      DESCRIPTION "Generated SNMP Table Entry."
      INDEX { errorHandlingIndex}
      ::= { errorHandlingTable 1 }
      
   ErrorHandlingEntry ::=
      SEQUENCE
      {
         errorHandlingIndex   OCTET STRING,
         errorHandlingObjectName OCTET STRING,
         errorHandlingType    OCTET STRING,
         errorHandlingLogPolicy OCTET STRING,
         errorHandlingPolicy  OCTET STRING,
         errorHandlingName    OCTET STRING
      }
      
   
   errorHandlingIndex OBJECT-TYPE
      SYNTAX      OCTET STRING
      MAX-ACCESS  not-accessible
      STATUS      current
      DESCRIPTION "Index column"
      ::= { errorHandlingEntry 1  }
   
   
   errorHandlingObjectName OBJECT-TYPE
      SYNTAX      OCTET STRING
      MAX-ACCESS  read-only
      STATUS      current
      DESCRIPTION "ObjectName column"
      ::= { errorHandlingEntry 2  }
   
   
   errorHandlingType OBJECT-TYPE
      SYNTAX      OCTET STRING
      MAX-ACCESS  read-only
      STATUS      current
      DESCRIPTION "Returns the type of the MBean."
      ::= { errorHandlingEntry 3  }
   
   
   errorHandlingLogPolicy OBJECT-TYPE
      SYNTAX      OCTET STRING
      MAX-ACCESS  read-only
      STATUS      current
      DESCRIPTION "Policy"
      ::= { errorHandlingEntry 4  }
   
   
   errorHandlingPolicy OBJECT-TYPE
      SYNTAX      OCTET STRING
      MAX-ACCESS  read-only
      STATUS      current
      DESCRIPTION "Policy"
      ::= { errorHandlingEntry 5  }
   
   
   errorHandlingName OBJECT-TYPE
      SYNTAX      OCTET STRING
      MAX-ACCESS  read-only
      STATUS      current
      DESCRIPTION "The user-specified name of this MBean instance.  This name is included as one of the key properties in the MBean's javax.management.ObjectName: Name=user-specified-name"
      ::= { errorHandlingEntry 6  }
   
   
   fairShareRequestClassTable OBJECT-TYPE
      SYNTAX      SEQUENCE OF FairShareRequestClassEntry
      MAX-ACCESS  not-accessible
      STATUS      current
      DESCRIPTION "This mbean defines the fair share value to use for this request class. One of the components of work managers is a request class that indicates the proportional of the total server thread use time this request class gets. The default fair share value is 50.  Fair shares are reflected in scheduling logic such that as long as multiple fair shares compete, the average number of threads used by each is in proportion to their fair share. For example, consider we only have two fair shares, A and B, having a fair share of 80 and 20, respectively. During a period in which both fair shares are sufficiently requested, say, zero think time and more clients than threads, the probability that a thread will work on behalf of A or B will tend toward 80% or 20%, respectively. The scheduling logic ensures this even when A tends to use a thread for much longer than B.   Fair share values can range from 1 to 1000. The default fair share value is 50.   Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 915  }
      
   
   fairShareRequestClassEntry OBJECT-TYPE
      SYNTAX      FairShareRequestClassEntry
      MAX-ACCESS  not-accessible
      STATUS      current
      DESCRIPTION "Generated SNMP Table Entry."
      INDEX { fairShareRequestClassIndex}
      ::= { fairShareRequestClassTable 1 }
      
   FairShareRequestClassEntry ::=
      SEQUENCE
      {
         fairShareRequestClassIndex OCTET STRING,
         fairShareRequestClassObjectName OCTET STRING,
         fairShareRequestClassType OCTET STRING,
         fairShareRequestClassDeploymentOrder Integer32,
         fairShareRequestClassFairShare Integer32,
         fairShareRequestClassName OCTET STRING
      }
      
   
   fairShareRequestClassIndex OBJECT-TYPE
      SYNTAX      OCTET STRING
      MAX-ACCESS  not-accessible
      STATUS      current
      DESCRIPTION "Index column"
      ::= { fairShareRequestClassEntry 1  }
   
   
   fairShareRequestClassObjectName OBJECT-TYPE
      SYNTAX      OCTET STRING
      MAX-ACCESS  read-only
      STATUS      current
      DESCRIPTION "ObjectName column"
      ::= { fairShareRequestClassEntry 2  }
   
   
   fairShareRequestClassType OBJECT-TYPE
      SYNTAX      OCTET STRING
      MAX-ACCESS  read-only
      STATUS      current
      DESCRIPTION "Returns the type of the MBean."
      ::= { fairShareRequestClassEntry 3  }
   
   
   fairShareRequestClassDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { fairShareRequestClassEntry 4  }
   
   
   fairShareRequestClassFairShare OBJECT-TYPE
      SYNTAX      Integer32
      MAX-ACCESS  read-only
      STATUS      current
      DESCRIPTION "Fair share value"
      ::= { fairShareRequestClassEntry 5  }
   
   
   fairShareRequestClassName OBJECT-TYPE
      SYNTAX      OCTET STRING
      MAX-ACCESS  read-only
      STATUS      current
      DESCRIPTION "The user-specified name of this MBean instance.  This name is included as one of the key properties in the MBean's javax.management.ObjectName: Name=user-specified-name"
      ::= { fairShareRequestClassEntry 6  }
   
   
   federationServicesTable OBJECT-TYPE
      SYNTAX      SEQUENCE OF FederationServicesEntry
      MAX-ACCESS  not-accessible
      STATUS      current
      DESCRIPTION "This MBean represents configuration for SAML 1.1-based Federation Services, including the intersite transfer service, assertion consumer service, and assertion retrieval service.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 920  }
      
   
   federationServicesEntry OBJECT-TYPE
      SYNTAX      FederationServicesEntry
      MAX-ACCESS  not-accessible
      STATUS      current
      DESCRIPTION "Generated SNMP Table Entry."
      INDEX { federationServicesIndex}
      ::= { federationServicesTable 1 }
      
   FederationServicesEntry ::=
      SEQUENCE
      {
         federationServicesIndex OCTET STRING,
         federationServicesObjectName OCTET STRING,
         federationServicesType OCTET STRING,
         federationServicesSourceIdHex OCTET STRING,
         federationServicesAssertionStoreClassName OCTET STRING,
         federationServicesITSRequiresSSL OCTET STRING,
         federationServicesARSRequiresTwoWaySSL OCTET STRING,
         federationServicesPOSTRecipientCheckEnabled OCTET STRING,
         federationServicesACSRequiresSSL OCTET STRING,
         federationServicesSourceSiteURL OCTET STRING,
         federationServicesSigningKeyAlias OCTET STRING,
         federationServicesName OCTET STRING,
         federationServicesSSLClientIdentityAlias OCTET STRING,
         federationServicesSourceIdBase64 OCTET STRING,
         federationServicesDestinationSiteEnabled OCTET STRING,
         federationServicesPOSTOneUseCheckEnabled OCTET STRING,
         federationServicesUsedAssertionCacheClassName OCTET STRING,
         federationServicesARSRequiresSSL OCTET STRING,
         federationServicesSourceSiteEnabled OCTET STRING
      }
      
   
   federationServicesIndex OBJECT-TYPE
      SYNTAX      OCTET STRING
      MAX-ACCESS  not-accessible
      STATUS      current
      DESCRIPTION "Index column"
      ::= { federationServicesEntry 1  }
   
   
   federationServicesObjectName OBJECT-TYPE
      SYNTAX      OCTET STRING
      MAX-ACCESS  read-only
      STATUS      current
      DESCRIPTION "ObjectName column"
      ::= { federationServicesEntry 2  }
   
   
   federationServicesType OBJECT-TYPE
      SYNTAX      OCTET STRING
      MAX-ACCESS  read-only
      STATUS      current
      DESCRIPTION "Returns the type of the MBean."
      ::= { federationServicesEntry 3  }
   
   
   federationServicesSourceIdHex OBJECT-TYPE
      SYNTAX      OCTET STRING
      MAX-ACCESS  read-only
      STATUS      current
      DESCRIPTION "The Source Site ID in hexadecimal. This read-only value is a hexadecimal representation of a 20-byte binary value that is calculated from the SourceSiteURL. If you want to configure ARTIFACT profile with another site, you will need to give a SourceId value to the other site. This value is are automatically updated when the SourceSiteURL changes."
      ::= { federationServicesEntry 4  }
   
   
   federationServicesAssertionStoreClassName OBJECT-TYPE
      SYNTAX      OCTET STRING
      MAX-ACCESS  read-only
      STATUS      current
      DESCRIPTION "The class that provides persistent storage for assertions, if you use an Assertion Store class other than the default class."
      ::= { federationServicesEntry 5  }
   
   
   federationServicesITSRequiresSSL OBJECT-TYPE
      SYNTAX      OCTET STRING
      MAX-ACCESS  read-only
      STATUS      current
      DESCRIPTION "Specifies whether the Intersite Transfer Service requires SSL."
      ::= { federationServicesEntry 6  }
   
   
   federationServicesARSRequiresTwoWaySSL OBJECT-TYPE
      SYNTAX      OCTET STRING
      MAX-ACCESS  read-only
      STATUS      current
      DESCRIPTION "Specifies whether the Assertion Retrieval Service requires two-way SSL authentication."
      ::= { federationServicesEntry 7  }
   
   
   federationServicesPOSTRecipientCheckEnabled OBJECT-TYPE
      SYNTAX      OCTET STRING
      MAX-ACCESS  read-only
      STATUS      current
      DESCRIPTION "Specifies whether the POST recipient check is enabled. When true, the recipient of the SAML Response must match the URL in the HTTP Request."
      ::= { federationServicesEntry 8  }
   
   
   federationServicesACSRequiresSSL OBJECT-TYPE
      SYNTAX      OCTET STRING
      MAX-ACCESS  read-only
      STATUS      current
      DESCRIPTION "Specifies whether the Assertion Consumer Service requires SSL."
      ::= { federationServicesEntry 9  }
   
   
   federationServicesSourceSiteURL OBJECT-TYPE
      SYNTAX      OCTET STRING
      MAX-ACCESS  read-only
      STATUS      current
      DESCRIPTION "The URL for the Source Site."
      ::= { federationServicesEntry 10  }
   
   
   federationServicesSigningKeyAlias OBJECT-TYPE
      SYNTAX      OCTET STRING
      MAX-ACCESS  read-only
      STATUS      current
      DESCRIPTION "The alias used to store and retrieve the Source Site's signing key in the keystore. This key is used to sign POST profile responses."
      ::= { federationServicesEntry 11  }
   
   
   federationServicesName OBJECT-TYPE
      SYNTAX      OCTET STRING
      MAX-ACCESS  read-only
      STATUS      current
      DESCRIPTION "The user-specified name of this MBean instance.  This name is included as one of the key properties in the MBean's javax.management.ObjectName: Name=user-specified-name"
      ::= { federationServicesEntry 12  }
   
   
   federationServicesSSLClientIdentityAlias OBJECT-TYPE
      SYNTAX      OCTET STRING
      MAX-ACCESS  read-only
      STATUS      current
      DESCRIPTION "The alias used to store and retrieve the Destination Site's SSL client identity in the keystore."
      ::= { federationServicesEntry 13  }
   
   
   federationServicesSourceIdBase64 OBJECT-TYPE
      SYNTAX      OCTET STRING
      MAX-ACCESS  read-only
      STATUS      current
      DESCRIPTION "The Source Site ID base64-encoded. This read-only value is a Base64 representation of a 20-byte binary value that is calculated from the SourceSiteURL. If you want to configure ARTIFACT profile with another site, you will need to give a SourceId value to the other site. This value is are automatically updated when the SourceSiteURL changes."
      ::= { federationServicesEntry 14  }
   
   
   federationServicesDestinationSiteEnabled OBJECT-TYPE
      SYNTAX      OCTET STRING
      MAX-ACCESS  read-only
      STATUS      current
      DESCRIPTION "Specifies whether the Destination Site is enabled."
      ::= { federationServicesEntry 15  }
   
   
   federationServicesPOSTOneUseCheckEnabled OBJECT-TYPE
      SYNTAX      OCTET STRING
      MAX-ACCESS  read-only
      STATUS      current
      DESCRIPTION "Specifies whether the POST one-use check is enabled."
      ::= { federationServicesEntry 16  }
   
   
   federationServicesUsedAssertionCacheClassName OBJECT-TYPE
      SYNTAX      OCTET STRING
      MAX-ACCESS  read-only
      STATUS      current
      DESCRIPTION "The class used as the persistent store for the Used Assertion Cache. When no class is specified, the default Used Assertion Cache implemention is used."
      ::= { federationServicesEntry 17  }
   
   
   federationServicesARSRequiresSSL OBJECT-TYPE
      SYNTAX      OCTET STRING
      MAX-ACCESS  read-only
      STATUS      current
      DESCRIPTION "Specifies whether the Assertion Retrieval Service requires SSL."
      ::= { federationServicesEntry 18  }
   
   
   federationServicesSourceSiteEnabled OBJECT-TYPE
      SYNTAX      OCTET STRING
      MAX-ACCESS  read-only
      STATUS      current
      DESCRIPTION "Indicates whether the Source Site is enabled."
      ::= { federationServicesEntry 19  }
   
   
   fileStoreTable OBJECT-TYPE
      SYNTAX      SEQUENCE OF FileStoreEntry
      MAX-ACCESS  not-accessible
      STATUS      current
      DESCRIPTION "Defines an instance of the persistent store on the specified target that will keep its persistent objects in files on the filesystem. It may be used by JMS and by other subsystems.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 925  }
      
   
   fileStoreEntry OBJECT-TYPE
      SYNTAX      FileStoreEntry
      MAX-ACCESS  not-accessible
      STATUS      current
      DESCRIPTION "Generated SNMP Table Entry."
      INDEX { fileStoreIndex}
      ::= { fileStoreTable 1 }
      
   FileStoreEntry ::=
      SEQUENCE
      {
         fileStoreIndex       OCTET STRING,
         fileStoreObjectName  OCTET STRING,
         fileStoreType        OCTET STRING,
         fileStoreDeploymentOrder Integer32,
         fileStoreLogicalName OCTET STRING,
         fileStoreXAResourceName OCTET STRING,
         fileStoreName        OCTET STRING
      }
      
   
   fileStoreIndex OBJECT-TYPE
      SYNTAX      OCTET STRING
      MAX-ACCESS  not-accessible
      STATUS      current
      DESCRIPTION "Index column"
      ::= { fileStoreEntry 1  }
   
   
   fileStoreObjectName OBJECT-TYPE
      SYNTAX      OCTET STRING
      MAX-ACCESS  read-only
      STATUS      current
      DESCRIPTION "ObjectName column"
      ::= { fileStoreEntry 2  }
   
   
   fileStoreType OBJECT-TYPE
      SYNTAX      OCTET STRING
      MAX-ACCESS  read-only
      STATUS      current
      DESCRIPTION "Returns the type of the MBean."
      ::= { fileStoreEntry 3  }
   
   
   fileStoreDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { fileStoreEntry 4  }
   
   
   fileStoreLogicalName OBJECT-TYPE
      SYNTAX      OCTET STRING
      MAX-ACCESS  read-only
      STATUS      current
      DESCRIPTION "The name used by subsystems to refer to different stores on different servers using the same name.  For example, an EJB that uses the timer service may refer to its store using the logical name, and this name may be valid on multiple servers in the same cluster, even if each server has a store with a different physical name.  Multiple stores in the same domain or the same cluster may share the same logical name. However, a given logical name may not be assigned to more than one store on the same server."
      ::= { fileStoreEntry 5  }
   
   
   fileStoreXAResourceName OBJECT-TYPE
      SYNTAX      OCTET STRING
      MAX-ACCESS  read-only
      STATUS      current
      DESCRIPTION "Overrides the name of the XAResource that this store registers with JTA.  You should not normally set this attribute. Its purpose is to allow the name of the XAResource to be overridden when a store has been upgraded from an older release and the store contained prepared transactions. The generated name should be used in all other cases."
      ::= { fileStoreEntry 6  }
   
   
   fileStoreName OBJECT-TYPE
      SYNTAX      OCTET STRING
      MAX-ACCESS  read-only
      STATUS      current
      DESCRIPTION "The user-specified name of this MBean instance.  This name is included as one of the key properties in the MBean's javax.management.ObjectName: Name=user-specified-name"
      ::= { fileStoreEntry 7  }
   
   
   foreignJNDILinkTable OBJECT-TYPE
      SYNTAX      SEQUENCE OF ForeignJNDILinkEntry
      MAX-ACCESS  not-accessible
      STATUS      current
      DESCRIPTION "Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 930  }
      
   
   foreignJNDILinkEntry OBJECT-TYPE
      SYNTAX      ForeignJNDILinkEntry
      MAX-ACCESS  not-accessible
      STATUS      current
      DESCRIPTION "Generated SNMP Table Entry."
      INDEX { foreignJNDILinkIndex}
      ::= { foreignJNDILinkTable 1 }
      
   ForeignJNDILinkEntry ::=
      SEQUENCE
      {
         foreignJNDILinkIndex OCTET STRING,
         foreignJNDILinkObjectName OCTET STRING,
         foreignJNDILinkType  OCTET STRING,
         foreignJNDILinkLocalJNDIName OCTET STRING,
         foreignJNDILinkName  OCTET STRING,
         foreignJNDILinkRemoteJNDIName OCTET STRING
      }
      
   
   foreignJNDILinkIndex OBJECT-TYPE
      SYNTAX      OCTET STRING
      MAX-ACCESS  not-accessible
      STATUS      current
      DESCRIPTION "Index column"
      ::= { foreignJNDILinkEntry 1  }
   
   
   foreignJNDILinkObjectName OBJECT-TYPE
      SYNTAX      OCTET STRING
      MAX-ACCESS  read-only
      STATUS      current
      DESCRIPTION "ObjectName column"
      ::= { foreignJNDILinkEntry 2  }
   
   
   foreignJNDILinkType OBJECT-TYPE
      SYNTAX      OCTET STRING
      MAX-ACCESS  read-only
      STATUS      current
      DESCRIPTION "Returns the type of the MBean."
      ::= { foreignJNDILinkEntry 3  }
   
   
   foreignJNDILinkLocalJNDIName OBJECT-TYPE
      SYNTAX      OCTET STRING
      MAX-ACCESS  read-only
      STATUS      current
      DESCRIPTION "The local jndi name."
      ::= { foreignJNDILinkEntry 4  }
   
   
   foreignJNDILinkName OBJECT-TYPE
      SYNTAX      OCTET STRING
      MAX-ACCESS  read-only
      STATUS      current
      DESCRIPTION "The user-specified name of this MBean instance.  This name is included as one of the key properties in the MBean's javax.management.ObjectName: Name=user-specified-name"
      ::= { foreignJNDILinkEntry 5  }
   
   
   foreignJNDILinkRemoteJNDIName OBJECT-TYPE
      SYNTAX      OCTET STRING
      MAX-ACCESS  read-only
      STATUS      current
      DESCRIPTION "The foreign jndi name."
      ::= { foreignJNDILinkEntry 6  }
   
   
   foreignJNDIProviderTable OBJECT-TYPE
      SYNTAX      SEQUENCE OF ForeignJNDIProviderEntry
      MAX-ACCESS  not-accessible
      STATUS      current
      DESCRIPTION "Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 935  }
      
   
   foreignJNDIProviderEntry OBJECT-TYPE
      SYNTAX      ForeignJNDIProviderEntry
      MAX-ACCESS  not-accessible
      STATUS      current
      DESCRIPTION "Generated SNMP Table Entry."
      INDEX { foreignJNDIProviderIndex}
      ::= { foreignJNDIProviderTable 1 }
      
   ForeignJNDIProviderEntry ::=
      SEQUENCE
      {
         foreignJNDIProviderIndex OCTET STRING,
         foreignJNDIProviderObjectName OCTET STRING,
         foreignJNDIProviderType OCTET STRING,
         foreignJNDIProviderInitialContextFactory OCTET STRING,
         foreignJNDIProviderUser OCTET STRING,
         foreignJNDIProviderProviderURL OCTET STRING,
         foreignJNDIProviderName OCTET STRING
      }
      
   
   foreignJNDIProviderIndex OBJECT-TYPE
      SYNTAX      OCTET STRING
      MAX-ACCESS  not-accessible
      STATUS      current
      DESCRIPTION "Index column"
      ::= { foreignJNDIProviderEntry 1  }
   
   
   foreignJNDIProviderObjectName OBJECT-TYPE
      SYNTAX      OCTET STRING
      MAX-ACCESS  read-only
      STATUS      current
      DESCRIPTION "ObjectName column"
      ::= { foreignJNDIProviderEntry 2  }
   
   
   foreignJNDIProviderType OBJECT-TYPE
      SYNTAX      OCTET STRING
      MAX-ACCESS  read-only
      STATUS      current
      DESCRIPTION "Returns the type of the MBean."
      ::= { foreignJNDIProviderEntry 3  }
   
   
   foreignJNDIProviderInitialContextFactory OBJECT-TYPE
      SYNTAX      OCTET STRING
      MAX-ACCESS  read-only
      STATUS      current
      DESCRIPTION "The initial context factory to use to connect. This class name depends on the JNDI provider and the vendor that are being used. The value corresponds to the standard JNDI property, java.naming.factory.initial"
      ::= { foreignJNDIProviderEntry 4  }
   
   
   foreignJNDIProviderUser OBJECT-TYPE
      SYNTAX      OCTET STRING
      MAX-ACCESS  read-only
      STATUS      current
      DESCRIPTION "The remote server's user name."
      ::= { foreignJNDIProviderEntry 5  }
   
   
   foreignJNDIProviderProviderURL OBJECT-TYPE
      SYNTAX      OCTET STRING
      MAX-ACCESS  read-only
      STATUS      current
      DESCRIPTION "The foreign jndi provider url. This value corresponds to the standard JNDI property, java.naming.provider.url"
      ::= { foreignJNDIProviderEntry 6  }
   
   
   foreignJNDIProviderName OBJECT-TYPE
      SYNTAX      OCTET STRING
      MAX-ACCESS  read-only
      STATUS      current
      DESCRIPTION "The user-specified name of this MBean instance.  This name is included as one of the key properties in the MBean's javax.management.ObjectName: Name=user-specified-name"
      ::= { foreignJNDIProviderEntry 7  }
   
   
   httpProxyTable OBJECT-TYPE
      SYNTAX      SEQUENCE OF HttpProxyEntry
      MAX-ACCESS  not-accessible
      STATUS      current
      DESCRIPTION "Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com.  Copyright (c) 2003 by BEA Systems, Inc. All Rights Reserved."
      ::= { wls 940  }
      
   
   httpProxyEntry OBJECT-TYPE
      SYNTAX      HttpProxyEntry
      MAX-ACCESS  not-accessible
      STATUS      current
      DESCRIPTION "Generated SNMP Table Entry."
      INDEX { httpProxyIndex}
      ::= { httpProxyTable 1 }
      
   HttpProxyEntry ::=
      SEQUENCE
      {
         httpProxyIndex       OCTET STRING,
         httpProxyObjectName  OCTET STRING,
         httpProxyType        OCTET STRING,
         httpProxyServerList  OCTET STRING,
         httpProxyDeploymentOrder Integer32,
         httpProxyMaxHealthCheckInterval Integer32,
         httpProxyHealthCheckInterval Integer32,
         httpProxyInitialConnections Integer32,
         httpProxyMaxConnections Integer32,
         httpProxyName        OCTET STRING,
         httpProxyMaxRetries  Integer32
      }
      
   
   httpProxyIndex OBJECT-TYPE
      SYNTAX      OCTET STRING
      MAX-ACCESS  not-accessible
      STATUS      current
      DESCRIPTION "Index column"
      ::= { httpProxyEntry 1  }
   
   
   httpProxyObjectName OBJECT-TYPE
      SYNTAX      OCTET STRING
      MAX-ACCESS  read-only
      STATUS      current
      DESCRIPTION "ObjectName column"
      ::= { httpProxyEntry 2  }
   
   
   httpProxyType OBJECT-TYPE
      SYNTAX      OCTET STRING
      MAX-ACCESS  read-only
      STATUS      current
      DESCRIPTION "Returns the type of the MBean."
      ::= { httpProxyEntry 3  }
   
   
   httpProxyServerList OBJECT-TYPE
      SYNTAX      OCTET STRING
      MAX-ACCESS  read-only
      STATUS      current
      DESCRIPTION "The list of servers in the back end that the HCS should proxy to."
      ::= { httpProxyEntry 4  }
   
   
   httpProxyDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { httpProxyEntry 5  }
   
   
   httpProxyMaxHealthCheckInterval OBJECT-TYPE
      SYNTAX      Integer32
      MAX-ACCESS  read-only
      STATUS      current
      DESCRIPTION "The maximum interval between health checks."
      ::= { httpProxyEntry 6  }
   
   
   httpProxyHealthCheckInterval OBJECT-TYPE
      SYNTAX      Integer32
      MAX-ACCESS  read-only
      STATUS      current
      DESCRIPTION "The health check interval in milliseconds between pings."
      ::= { httpProxyEntry 7  }
   
   
   httpProxyInitialConnections OBJECT-TYPE
      SYNTAX      Integer32
      MAX-ACCESS  read-only
      STATUS      current
      DESCRIPTION "The number of initial connections that should be opened to each server in the back end servers."
      ::= { httpProxyEntry 8  }
   
   
   httpProxyMaxConnections OBJECT-TYPE
      SYNTAX      Integer32
      MAX-ACCESS  read-only
      STATUS      current
      DESCRIPTION "The maximum number of connections that each server can open to the back end servers."
      ::= { httpProxyEntry 9  }
   
   
   httpProxyName OBJECT-TYPE
      SYNTAX      OCTET STRING
      MAX-ACCESS  read-only
      STATUS      current
      DESCRIPTION "The user-specified name of this MBean instance.  This name is included as one of the key properties in the MBean's javax.management.ObjectName: Name=user-specified-name"
      ::= { httpProxyEntry 10  }
   
   
   httpProxyMaxRetries OBJECT-TYPE
      SYNTAX      Integer32
      MAX-ACCESS  read-only
      STATUS      current
      DESCRIPTION "The max retries after which the server will be marked dead."
      ::= { httpProxyEntry 11  }
   
   
   jdbcPoolComponentTable OBJECT-TYPE
      SYNTAX      SEQUENCE OF JdbcPoolComponentEntry
      MAX-ACCESS  not-accessible
      STATUS      current
      DESCRIPTION ""
      ::= { wls 945  }
      
   
   jdbcPoolComponentEntry OBJECT-TYPE
      SYNTAX      JdbcPoolComponentEntry
      MAX-ACCESS  not-accessible
      STATUS      current
      DESCRIPTION "Generated SNMP Table Entry."
      INDEX { jdbcPoolComponentIndex}
      ::= { jdbcPoolComponentTable 1 }
      
   JdbcPoolComponentEntry ::=
      SEQUENCE
      {
         jdbcPoolComponentIndex OCTET STRING,
         jdbcPoolComponentObjectName OCTET STRING,
         jdbcPoolComponentType OCTET STRING,
         jdbcPoolComponentDeploymentOrder Integer32,
         jdbcPoolComponentURI OCTET STRING,
         jdbcPoolComponentName OCTET STRING
      }
      
   
   jdbcPoolComponentIndex OBJECT-TYPE
      SYNTAX      OCTET STRING
      MAX-ACCESS  not-accessible
      STATUS      current
      DESCRIPTION "Index column"
      ::= { jdbcPoolComponentEntry 1  }
   
   
   jdbcPoolComponentObjectName OBJECT-TYPE
      SYNTAX      OCTET STRING
      MAX-ACCESS  read-only
      STATUS      current
      DESCRIPTION "ObjectName column"
      ::= { jdbcPoolComponentEntry 2  }
   
   
   jdbcPoolComponentType OBJECT-TYPE
      SYNTAX      OCTET STRING
      MAX-ACCESS  read-only
      STATUS      current
      DESCRIPTION "Returns the type of the MBean."
      ::= { jdbcPoolComponentEntry 3  }
   
   
   jdbcPoolComponentDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { jdbcPoolComponentEntry 4  }
   
   
   jdbcPoolComponentURI OBJECT-TYPE
      SYNTAX      OCTET STRING
      MAX-ACCESS  read-only
      STATUS      current
      DESCRIPTION "A URI that points to the application module, usually on the Administration Server.  URI can only be set if this is a standalone component; the URI for an application is defined in the application's deployment descriptor. *"
      ::= { jdbcPoolComponentEntry 5  }
   
   
   jdbcPoolComponentName OBJECT-TYPE
      SYNTAX      OCTET STRING
      MAX-ACCESS  read-only
      STATUS      current
      DESCRIPTION "The user-specified name of this MBean instance.  This name is included as one of the key properties in the MBean's javax.management.ObjectName: Name=user-specified-name"
      ::= { jdbcPoolComponentEntry 6  }
   
   
   jdbcStoreTable OBJECT-TYPE
      SYNTAX      SEQUENCE OF JdbcStoreEntry
      MAX-ACCESS  not-accessible
      STATUS      current
      DESCRIPTION "Defines an instance of the persistent store that stores its persistent records in a JDBC-accessible database. It may be used by JMS and by other subsystems.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 950  }
      
   
   jdbcStoreEntry OBJECT-TYPE
      SYNTAX      JdbcStoreEntry
      MAX-ACCESS  not-accessible
      STATUS      current
      DESCRIPTION "Generated SNMP Table Entry."
      INDEX { jdbcStoreIndex}
      ::= { jdbcStoreTable 1 }
      
   JdbcStoreEntry ::=
      SEQUENCE
      {
         jdbcStoreIndex       OCTET STRING,
         jdbcStoreObjectName  OCTET STRING,
         jdbcStoreType        OCTET STRING,
         jdbcStoreDeploymentOrder Integer32,
         jdbcStoreDeletesPerBatchMaximum Integer32,
         jdbcStoreLogicalName OCTET STRING,
         jdbcStoreXAResourceName OCTET STRING,
         jdbcStoreDeletesPerStatementMaximum Integer32,
         jdbcStoreInsertsPerBatchMaximum Integer32,
         jdbcStoreName        OCTET STRING
      }
      
   
   jdbcStoreIndex OBJECT-TYPE
      SYNTAX      OCTET STRING
      MAX-ACCESS  not-accessible
      STATUS      current
      DESCRIPTION "Index column"
      ::= { jdbcStoreEntry 1  }
   
   
   jdbcStoreObjectName OBJECT-TYPE
      SYNTAX      OCTET STRING
      MAX-ACCESS  read-only
      STATUS      current
      DESCRIPTION "ObjectName column"
      ::= { jdbcStoreEntry 2  }
   
   
   jdbcStoreType OBJECT-TYPE
      SYNTAX      OCTET STRING
      MAX-ACCESS  read-only
      STATUS      current
      DESCRIPTION "Returns the type of the MBean."
      ::= { jdbcStoreEntry 3  }
   
   
   jdbcStoreDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { jdbcStoreEntry 4  }
   
   
   jdbcStoreDeletesPerBatchMaximum OBJECT-TYPE
      SYNTAX      Integer32
      MAX-ACCESS  read-only
      STATUS      current
      DESCRIPTION "The maximum number of table rows that are deleted per database call.    When possible, a JDBC store uses JDBC 3.0 batching to batch concurrent client requests.    Both the maximum batch size for concurrent inserts and for concurrent writes are configurable.    To disable JDBC 3.0 batching, set the maximum batch size to 1.    The maximum batch size has no effect on the maximum number of concurrent client requests."
      ::= { jdbcStoreEntry 5  }
   
   
   jdbcStoreLogicalName OBJECT-TYPE
      SYNTAX      OCTET STRING
      MAX-ACCESS  read-only
      STATUS      current
      DESCRIPTION "The name used by subsystems to refer to different stores on different servers using the same name.  For example, an EJB that uses the timer service may refer to its store using the logical name, and this name may be valid on multiple servers in the same cluster, even if each server has a store with a different physical name.  Multiple stores in the same domain or the same cluster may share the same logical name. However, a given logical name may not be assigned to more than one store on the same server."
      ::= { jdbcStoreEntry 6  }
   
   
   jdbcStoreXAResourceName OBJECT-TYPE
      SYNTAX      OCTET STRING
      MAX-ACCESS  read-only
      STATUS      current
      DESCRIPTION "Overrides the name of the XAResource that this store registers with JTA.  You should not normally set this attribute. Its purpose is to allow the name of the XAResource to be overridden when a store has been upgraded from an older release and the store contained prepared transactions. The generated name should be used in all other cases."
      ::= { jdbcStoreEntry 7  }
   
   
   jdbcStoreDeletesPerStatementMaximum OBJECT-TYPE
      SYNTAX      Integer32
      MAX-ACCESS  read-only
      STATUS      current
      DESCRIPTION "The maximum number of table rows that are deleted per database call.    Applies only when a JDBC store does not use JDBC 3.0 batching to batch concurrent client requests.    The maximum deletes per statement has no effect on the maximum number of concurrent client requests.    For some databases, the JDBC store may choose a lower value than the one configured."
      ::= { jdbcStoreEntry 8  }
   
   
   jdbcStoreInsertsPerBatchMaximum OBJECT-TYPE
      SYNTAX      Integer32
      MAX-ACCESS  read-only
      STATUS      current
      DESCRIPTION "The maximum number of table rows that are inserted per database call.    When possible, a JDBC store uses JDBC 3.0 batching to batch concurrent client requests.    Both the maximum batch size for concurrent inserts and for concurrent writes are configurable.    To disable JDBC 3.0 batching, set the maximum batch size to 1.    The maximum batch size has no effect on the maximum number of concurrent client requests."
      ::= { jdbcStoreEntry 9  }
   
   
   jdbcStoreName OBJECT-TYPE
      SYNTAX      OCTET STRING
      MAX-ACCESS  read-only
      STATUS      current
      DESCRIPTION "The user-specified name of this MBean instance.  This name is included as one of the key properties in the MBean's javax.management.ObjectName: Name=user-specified-name"
      ::= { jdbcStoreEntry 10  }
   
   
   jdbcSystemResourceTable OBJECT-TYPE
      SYNTAX      SEQUENCE OF JdbcSystemResourceEntry
      MAX-ACCESS  not-accessible
      STATUS      current
      DESCRIPTION "This bean defines a system-level JDBC resource.  It links a separate descriptor that specifies the definition.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 955  }
      
   
   jdbcSystemResourceEntry OBJECT-TYPE
      SYNTAX      JdbcSystemResourceEntry
      MAX-ACCESS  not-accessible
      STATUS      current
      DESCRIPTION "Generated SNMP Table Entry."
      INDEX { jdbcSystemResourceIndex}
      ::= { jdbcSystemResourceTable 1 }
      
   JdbcSystemResourceEntry ::=
      SEQUENCE
      {
         jdbcSystemResourceIndex OCTET STRING,
         jdbcSystemResourceObjectName OCTET STRING,
         jdbcSystemResourceType OCTET STRING,
         jdbcSystemResourceCompatibilityName OCTET STRING,
         jdbcSystemResourceDeploymentOrder Integer32,
         jdbcSystemResourceDeploymentPrincipalName OCTET STRING,
         jdbcSystemResourceDescriptorFileName OCTET STRING,
         jdbcSystemResourceModuleType OCTET STRING,
         jdbcSystemResourceName OCTET STRING,
         jdbcSystemResourceSourcePath OCTET STRING
      }
      
   
   jdbcSystemResourceIndex OBJECT-TYPE
      SYNTAX      OCTET STRING
      MAX-ACCESS  not-accessible
      STATUS      current
      DESCRIPTION "Index column"
      ::= { jdbcSystemResourceEntry 1  }
   
   
   jdbcSystemResourceObjectName OBJECT-TYPE
      SYNTAX      OCTET STRING
      MAX-ACCESS  read-only
      STATUS      current
      DESCRIPTION "ObjectName column"
      ::= { jdbcSystemResourceEntry 2  }
   
   
   jdbcSystemResourceType OBJECT-TYPE
      SYNTAX      OCTET STRING
      MAX-ACCESS  read-only
      STATUS      current
      DESCRIPTION "Returns the type of the MBean."
      ::= { jdbcSystemResourceEntry 3  }
   
   
   jdbcSystemResourceCompatibilityName OBJECT-TYPE
      SYNTAX      OCTET STRING
      MAX-ACCESS  read-only
      STATUS      current
      DESCRIPTION "This is only set for beans created as a result of conversion from an 8.1 application configured using ApplicationMBean and ComponentMBean.  Standalone modules in 8.1 have both an ApplicationMBean name and ComponentMBean name. This attribute stores the name of the latter, to be used when the server creates the transient ComponentMBean for backward compatibility."
      ::= { jdbcSystemResourceEntry 4  }
   
   
   jdbcSystemResourceDeploymentOrder OBJECT-TYPE
      SYNTAX      Integer32
      MAX-ACCESS  read-only
      STATUS      current
      DESCRIPTION "A numerical value that indicates when this unit is deployed, relative to other DeployableUnits on a server, during startup.  Units with lower Load Order values are deployed before those with higher values."
      ::= { jdbcSystemResourceEntry 5  }
   
   
   jdbcSystemResourceDeploymentPrincipalName OBJECT-TYPE
      SYNTAX      OCTET STRING
      MAX-ACCESS  read-only
      STATUS      current
      DESCRIPTION "A string value that indicates what principal should be used when deploying the file or archive during startup and shutdown. This principal will be used to set the current subject when calling out into application code for interfaces such as ApplicationLifecycleListener, If no principal name is specifed, then the anonymous principal will be used."
      ::= { jdbcSystemResourceEntry 6  }
   
   
   jdbcSystemResourceDescriptorFileName OBJECT-TYPE
      SYNTAX      OCTET STRING
      MAX-ACCESS  read-only
      STATUS      current
      DESCRIPTION "The name of the file containing this configuration.  This is a relative name rooted at DOMAIN_DIR/config.  By default the file resides in the jdbc subdirectory and derives its name from the bean name using the following pattern:  .xml  Note that this is a read-only property that can only be set when the bean is created."
      ::= { jdbcSystemResourceEntry 7  }
   
   
   jdbcSystemResourceModuleType OBJECT-TYPE
      SYNTAX      OCTET STRING
      MAX-ACCESS  read-only
      STATUS      current
      DESCRIPTION "The values match those defined by jsr88. This attribute may move to another MBean."
      ::= { jdbcSystemResourceEntry 8  }
   
   
   jdbcSystemResourceName OBJECT-TYPE
      SYNTAX      OCTET STRING
      MAX-ACCESS  read-only
      STATUS      current
      DESCRIPTION "Unique identifier for this bean instance."
      ::= { jdbcSystemResourceEntry 9  }
   
   
   jdbcSystemResourceSourcePath OBJECT-TYPE
      SYNTAX      OCTET STRING
      MAX-ACCESS  read-only
      STATUS      current
      DESCRIPTION ""
      ::= { jdbcSystemResourceEntry 10  }
   
   
   jmsInteropModuleTable OBJECT-TYPE
      SYNTAX      SEQUENCE OF JmsInteropModuleEntry
      MAX-ACCESS  not-accessible
      STATUS      current
      DESCRIPTION "This bean defines a system-level JMS resource.  It links a separate descriptor that specifies the definition.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 960  }
      
   
   jmsInteropModuleEntry OBJECT-TYPE
      SYNTAX      JmsInteropModuleEntry
      MAX-ACCESS  not-accessible
      STATUS      current
      DESCRIPTION "Generated SNMP Table Entry."
      INDEX { jmsInteropModuleIndex}
      ::= { jmsInteropModuleTable 1 }
      
   JmsInteropModuleEntry ::=
      SEQUENCE
      {
         jmsInteropModuleIndex OCTET STRING,
         jmsInteropModuleObjectName OCTET STRING,
         jmsInteropModuleType OCTET STRING,
         jmsInteropModuleCompatibilityName OCTET STRING,
         jmsInteropModuleDeploymentOrder Integer32,
         jmsInteropModuleDeploymentPrincipalName OCTET STRING,
         jmsInteropModuleDescriptorFileName OCTET STRING,
         jmsInteropModuleModuleType OCTET STRING,
         jmsInteropModuleName OCTET STRING,
         jmsInteropModuleSourcePath OCTET STRING
      }
      
   
   jmsInteropModuleIndex OBJECT-TYPE
      SYNTAX      OCTET STRING
      MAX-ACCESS  not-accessible
      STATUS      current
      DESCRIPTION "Index column"
      ::= { jmsInteropModuleEntry 1  }
   
   
   jmsInteropModuleObjectName OBJECT-TYPE
      SYNTAX      OCTET STRING
      MAX-ACCESS  read-only
      STATUS      current
      DESCRIPTION "ObjectName column"
      ::= { jmsInteropModuleEntry 2  }
   
   
   jmsInteropModuleType OBJECT-TYPE
      SYNTAX      OCTET STRING
      MAX-ACCESS  read-only
      STATUS      current
      DESCRIPTION "Returns the type of the MBean."
      ::= { jmsInteropModuleEntry 3  }
   
   
   jmsInteropModuleCompatibilityName OBJECT-TYPE
      SYNTAX      OCTET STRING
      MAX-ACCESS  read-only
      STATUS      current
      DESCRIPTION "This is only set for beans created as a result of conversion from an 8.1 application configured using ApplicationMBean and ComponentMBean.  Standalone modules in 8.1 have both an ApplicationMBean name and ComponentMBean name. This attribute stores the name of the latter, to be used when the server creates the transient ComponentMBean for backward compatibility."
      ::= { jmsInteropModuleEntry 4  }
   
   
   jmsInteropModuleDeploymentOrder OBJECT-TYPE
      SYNTAX      Integer32
      MAX-ACCESS  read-only
      STATUS      current
      DESCRIPTION "A numerical value that indicates when this unit is deployed, relative to other DeployableUnits on a server, during startup.  Units with lower Load Order values are deployed before those with higher values."
      ::= { jmsInteropModuleEntry 5  }
   
   
   jmsInteropModuleDeploymentPrincipalName OBJECT-TYPE
      SYNTAX      OCTET STRING
      MAX-ACCESS  read-only
      STATUS      current
      DESCRIPTION "A string value that indicates what principal should be used when deploying the file or archive during startup and shutdown. This principal will be used to set the current subject when calling out into application code for interfaces such as ApplicationLifecycleListener, If no principal name is specifed, then the anonymous principal will be used."
      ::= { jmsInteropModuleEntry 6  }
   
   
   jmsInteropModuleDescriptorFileName OBJECT-TYPE
      SYNTAX      OCTET STRING
      MAX-ACCESS  read-only
      STATUS      current
      DESCRIPTION "The name of the file that contains the module configuration. By default the file resides in the DOMAIN_DIR/config/jms directory. The module file derives its name from the bean name using the following pattern:  .xml  Note that this is a read-only property that can only be set when the bean is created."
      ::= { jmsInteropModuleEntry 7  }
   
   
   jmsInteropModuleModuleType OBJECT-TYPE
      SYNTAX      OCTET STRING
      MAX-ACCESS  read-only
      STATUS      current
      DESCRIPTION "The values match those defined by jsr88. This attribute may move to another MBean."
      ::= { jmsInteropModuleEntry 8  }
   
   
   jmsInteropModuleName OBJECT-TYPE
      SYNTAX      OCTET STRING
      MAX-ACCESS  read-only
      STATUS      current
      DESCRIPTION "Unique identifier for this bean instance."
      ::= { jmsInteropModuleEntry 9  }
   
   
   jmsInteropModuleSourcePath OBJECT-TYPE
      SYNTAX      OCTET STRING
      MAX-ACCESS  read-only
      STATUS      current
      DESCRIPTION ""
      ::= { jmsInteropModuleEntry 10  }
   
   
   jmsMessageLogFileTable OBJECT-TYPE
      SYNTAX      SEQUENCE OF JmsMessageLogFileEntry
      MAX-ACCESS  not-accessible
      STATUS      current
      DESCRIPTION "This defines the configuration aspects of the logs for a jms server.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 965  }
      
   
   jmsMessageLogFileEntry OBJECT-TYPE
      SYNTAX      JmsMessageLogFileEntry
      MAX-ACCESS  not-accessible
      STATUS      current
      DESCRIPTION "Generated SNMP Table Entry."
      INDEX { jmsMessageLogFileIndex}
      ::= { jmsMessageLogFileTable 1 }
      
   JmsMessageLogFileEntry ::=
      SEQUENCE
      {
         jmsMessageLogFileIndex OCTET STRING,
         jmsMessageLogFileObjectName OCTET STRING,
         jmsMessageLogFileType OCTET STRING,
         jmsMessageLogFileNumberOfFilesLimited OCTET STRING,
         jmsMessageLogFileFileTimeSpan Integer32,
         jmsMessageLogFileRotationType OCTET STRING,
         jmsMessageLogFileFileCount Integer32,
         jmsMessageLogFileFileName OCTET STRING,
         jmsMessageLogFileFileMinSize Integer32,
         jmsMessageLogFileBufferSizeKB Integer32,
         jmsMessageLogFileDateFormatPattern OCTET STRING,
         jmsMessageLogFileRotationTime OCTET STRING,
         jmsMessageLogFileRotateLogOnStartup OCTET STRING,
         jmsMessageLogFileName OCTET STRING,
         jmsMessageLogFileLogFileRotationDir OCTET STRING
      }
      
   
   jmsMessageLogFileIndex OBJECT-TYPE
      SYNTAX      OCTET STRING
      MAX-ACCESS  not-accessible
      STATUS      current
      DESCRIPTION "Index column"
      ::= { jmsMessageLogFileEntry 1  }
   
   
   jmsMessageLogFileObjectName OBJECT-TYPE
      SYNTAX      OCTET STRING
      MAX-ACCESS  read-only
      STATUS      current
      DESCRIPTION "ObjectName column"
      ::= { jmsMessageLogFileEntry 2  }
   
   
   jmsMessageLogFileType OBJECT-TYPE
      SYNTAX      OCTET STRING
      MAX-ACCESS  read-only
      STATUS      current
      DESCRIPTION "Returns the type of the MBean."
      ::= { jmsMessageLogFileEntry 3  }
   
   
   jmsMessageLogFileNumberOfFilesLimited OBJECT-TYPE
      SYNTAX      OCTET STRING
      MAX-ACCESS  read-only
      STATUS      current
      DESCRIPTION "Indicates whether to limit the number of log files that this server instance creates to store old messages. (Requires that you specify a file rotation type of SIZE or TIME.)  After the server reaches this limit, it deletes the oldest log file and creates a new log file with the latest suffix.  If you do not enable this option, the server creates new files indefinitely and you must clean up these files as you require."
      ::= { jmsMessageLogFileEntry 4  }
   
   
   jmsMessageLogFileFileTimeSpan OBJECT-TYPE
      SYNTAX      Integer32
      MAX-ACCESS  read-only
      STATUS      current
      DESCRIPTION "The interval (in hours) at which the server saves old log messages to another file. (Requires that you specify a file rotation type of TIME.)"
      ::= { jmsMessageLogFileEntry 5  }
   
   
   jmsMessageLogFileRotationType OBJECT-TYPE
      SYNTAX      OCTET STRING
      MAX-ACCESS  read-only
      STATUS      current
      DESCRIPTION "Criteria for moving old log messages to a separate file.  NONE Messages accumulate in a single file. You must erase the contents of the file when the size is too large. Note that WebLogic Server sets a threshold size limit of 500 MB before it forces a hard rotation to prevent excessive log file growth.  SIZE When the log file reaches the size that you specify in FileMinSize, the server renames the file as FileName.n.  TIME At each time interval that you specify in TimeSpan, the server renames the file as FileName.n.   After the server renames a file, subsequent messages accumulate in a new file with the name that you specified in FileName."
      ::= { jmsMessageLogFileEntry 6  }
   
   
   jmsMessageLogFileFileCount OBJECT-TYPE
      SYNTAX      Integer32
      MAX-ACCESS  read-only
      STATUS      current
      DESCRIPTION "The maximum number of log files that the server creates when it rotates the log. This number does not include the file that the server uses to store current messages. (Requires that you enable Number of Files Limited.)"
      ::= { jmsMessageLogFileEntry 7  }
   
   
   jmsMessageLogFileFileName OBJECT-TYPE
      SYNTAX      OCTET STRING
      MAX-ACCESS  read-only
      STATUS      current
      DESCRIPTION "The name of the file that stores current JMS server log messages. Usually it is a computed value based on the name of the parent of this MBean. For example, for a JMS server log, it is jmsserverName.log.  However, if the name of the parent cannot be obtained, the file name is weblogic.log. If you specify a relative pathname, it is interpreted as relative to the server's root directory.  To include a time and date stamp in the file name when the log file is rotated, add java.text.SimpleDateFormat variables to the file name. Surround each variable with percentage (%) characters.  For example, if the file name is defined to be myjmsserver_%yyyy%_%MM%_%dd%_%hh%_%mm%.log, the log file will be named myserver_yyyy_mm_dd_hh_mm.log.  When the log file is rotated, the rotated file name contains the date stamp. For example, if the log file is rotated on 2 April, 2005 at 10:05 AM, the log file that contains the old messages will be named myserver_2005_04_02_10_05.log.  If you do not include a time and date stamp, the rotated log files are numbered in order of creation. For example, myjmsserver.log00007."
      ::= { jmsMessageLogFileEntry 8  }
   
   
   jmsMessageLogFileFileMinSize OBJECT-TYPE
      SYNTAX      Integer32
      MAX-ACCESS  read-only
      STATUS      current
      DESCRIPTION "The size (1 - 65535 kilobytes) that triggers the server to move log messages to a separate file. After the log file reaches the specified minimum size, the next time the server checks the file size, it will rename the current log file as FileName.n and create a new one to store subsequent messages. (Requires that you specify a file rotation type of Size.)"
      ::= { jmsMessageLogFileEntry 9  }
   
   
   jmsMessageLogFileBufferSizeKB OBJECT-TYPE
      SYNTAX      Integer32
      MAX-ACCESS  read-only
      STATUS      current
      DESCRIPTION "Gets the underlying log buffer size in kilo bytes"
      ::= { jmsMessageLogFileEntry 10  }
   
   
   jmsMessageLogFileDateFormatPattern OBJECT-TYPE
      SYNTAX      OCTET STRING
      MAX-ACCESS  read-only
      STATUS      current
      DESCRIPTION "The date format pattern used for rendering dates in the  log. The DateFormatPattern string conforms to the specification of the java.text.SimpleDateFormat class."
      ::= { jmsMessageLogFileEntry 11  }
   
   
   jmsMessageLogFileRotationTime OBJECT-TYPE
      SYNTAX      OCTET STRING
      MAX-ACCESS  read-only
      STATUS      current
      DESCRIPTION "Determines the start time (hour and minute) for a time-based rotation sequence.  At the time that this value specifies, the server renames the current log file. Thereafter, the server renames the log file at an interval that you specify in File Time Span.  If the specified time has already past, then the server starts its file rotation immediately.   Use the following format: k:mm, where k is the hour in a 24-hour format. mm is the minute"
      ::= { jmsMessageLogFileEntry 12  }
   
   
   jmsMessageLogFileRotateLogOnStartup OBJECT-TYPE
      SYNTAX      OCTET STRING
      MAX-ACCESS  read-only
      STATUS      current
      DESCRIPTION "Specifies whether a server rotates its log file during its startup cycle."
      ::= { jmsMessageLogFileEntry 13  }
   
   
   jmsMessageLogFileName OBJECT-TYPE
      SYNTAX      OCTET STRING
      MAX-ACCESS  read-only
      STATUS      current
      DESCRIPTION "The user-specified name of this MBean instance.  This name is included as one of the key properties in the MBean's javax.management.ObjectName: Name=user-specified-name"
      ::= { jmsMessageLogFileEntry 14  }
   
   
   jmsMessageLogFileLogFileRotationDir OBJECT-TYPE
      SYNTAX      OCTET STRING
      MAX-ACCESS  read-only
      STATUS      current
      DESCRIPTION "The directory where the rotated log files will be stored. By default the rotated files are stored in the same directory where the log file is stored."
      ::= { jmsMessageLogFileEntry 15  }
   
   
   jmsSAFMessageLogFileTable OBJECT-TYPE
      SYNTAX      SEQUENCE OF JmsSAFMessageLogFileEntry
      MAX-ACCESS  not-accessible
      STATUS      current
      DESCRIPTION "This defines the configuration aspects of the logs for a jms server.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 970  }
      
   
   jmsSAFMessageLogFileEntry OBJECT-TYPE
      SYNTAX      JmsSAFMessageLogFileEntry
      MAX-ACCESS  not-accessible
      STATUS      current
      DESCRIPTION "Generated SNMP Table Entry."
      INDEX { jmsSAFMessageLogFileIndex}
      ::= { jmsSAFMessageLogFileTable 1 }
      
   JmsSAFMessageLogFileEntry ::=
      SEQUENCE
      {
         jmsSAFMessageLogFileIndex OCTET STRING,
         jmsSAFMessageLogFileObjectName OCTET STRING,
         jmsSAFMessageLogFileType OCTET STRING,
         jmsSAFMessageLogFileNumberOfFilesLimited OCTET STRING,
         jmsSAFMessageLogFileFileTimeSpan Integer32,
         jmsSAFMessageLogFileRotationType OCTET STRING,
         jmsSAFMessageLogFileFileCount Integer32,
         jmsSAFMessageLogFileFileName OCTET STRING,
         jmsSAFMessageLogFileFileMinSize Integer32,
         jmsSAFMessageLogFileBufferSizeKB Integer32,
         jmsSAFMessageLogFileDateFormatPattern OCTET STRING,
         jmsSAFMessageLogFileRotationTime OCTET STRING,
         jmsSAFMessageLogFileRotateLogOnStartup OCTET STRING,
         jmsSAFMessageLogFileName OCTET STRING,
         jmsSAFMessageLogFileLogFileRotationDir OCTET STRING
      }
      
   
   jmsSAFMessageLogFileIndex OBJECT-TYPE
      SYNTAX      OCTET STRING
      MAX-ACCESS  not-accessible
      STATUS      current
      DESCRIPTION "Index column"
      ::= { jmsSAFMessageLogFileEntry 1  }
   
   
   jmsSAFMessageLogFileObjectName OBJECT-TYPE
      SYNTAX      OCTET STRING
      MAX-ACCESS  read-only
      STATUS      current
      DESCRIPTION "ObjectName column"
      ::= { jmsSAFMessageLogFileEntry 2  }
   
   
   jmsSAFMessageLogFileType OBJECT-TYPE
      SYNTAX      OCTET STRING
      MAX-ACCESS  read-only
      STATUS      current
      DESCRIPTION "Returns the type of the MBean."
      ::= { jmsSAFMessageLogFileEntry 3  }
   
   
   jmsSAFMessageLogFileNumberOfFilesLimited OBJECT-TYPE
      SYNTAX      OCTET STRING
      MAX-ACCESS  read-only
      STATUS      current
      DESCRIPTION "Indicates whether to limit the number of log files that this server instance creates to store old messages. (Requires that you specify a file rotation type of SIZE or TIME.)  After the server reaches this limit, it deletes the oldest log file and creates a new log file with the latest suffix.  If you do not enable this option, the server creates new files indefinitely and you must clean up these files as you require."
      ::= { jmsSAFMessageLogFileEntry 4  }
   
   
   jmsSAFMessageLogFileFileTimeSpan OBJECT-TYPE
      SYNTAX      Integer32
      MAX-ACCESS  read-only
      STATUS      current
      DESCRIPTION "The interval (in hours) at which the server saves old log messages to another file. (Requires that you specify a file rotation type of TIME.)"
      ::= { jmsSAFMessageLogFileEntry 5  }
   
   
   jmsSAFMessageLogFileRotationType OBJECT-TYPE
      SYNTAX      OCTET STRING
      MAX-ACCESS  read-only
      STATUS      current
      DESCRIPTION "Criteria for moving old log messages to a separate file.  NONE Messages accumulate in a single file. You must erase the contents of the file when the size is too large. Note that WebLogic Server sets a threshold size limit of 500 MB before it forces a hard rotation to prevent excessive log file growth.  SIZE When the log file reaches the size that you specify in FileMinSize, the server renames the file as FileName.n.  TIME At each time interval that you specify in TimeSpan, the server renames the file as FileName.n.   After the server renames a file, subsequent messages accumulate in a new file with the name that you specified in FileName."
      ::= { jmsSAFMessageLogFileEntry 6  }
   
   
   jmsSAFMessageLogFileFileCount OBJECT-TYPE
      SYNTAX      Integer32
      MAX-ACCESS  read-only
      STATUS      current
      DESCRIPTION "The maximum number of log files that the server creates when it rotates the log. This number does not include the file that the server uses to store current messages. (Requires that you enable Number of Files Limited.)"
      ::= { jmsSAFMessageLogFileEntry 7  }
   
   
   jmsSAFMessageLogFileFileName OBJECT-TYPE
      SYNTAX      OCTET STRING
      MAX-ACCESS  read-only
      STATUS      current
      DESCRIPTION ""
      ::= { jmsSAFMessageLogFileEntry 8  }
   
   
   jmsSAFMessageLogFileFileMinSize OBJECT-TYPE
      SYNTAX      Integer32
      MAX-ACCESS  read-only
      STATUS      current
      DESCRIPTION "The size (1 - 65535 kilobytes) that triggers the server to move log messages to a separate file. After the log file reaches the specified minimum size, the next time the server checks the file size, it will rename the current log file as FileName.n and create a new one to store subsequent messages. (Requires that you specify a file rotation type of Size.)"
      ::= { jmsSAFMessageLogFileEntry 9  }
   
   
   jmsSAFMessageLogFileBufferSizeKB OBJECT-TYPE
      SYNTAX      Integer32
      MAX-ACCESS  read-only
      STATUS      current
      DESCRIPTION "Gets the underlying log buffer size in kilo bytes"
      ::= { jmsSAFMessageLogFileEntry 10  }
   
   
   jmsSAFMessageLogFileDateFormatPattern OBJECT-TYPE
      SYNTAX      OCTET STRING
      MAX-ACCESS  read-only
      STATUS      current
      DESCRIPTION "The date format pattern used for rendering dates in the  log. The DateFormatPattern string conforms to the specification of the java.text.SimpleDateFormat class."
      ::= { jmsSAFMessageLogFileEntry 11  }
   
   
   jmsSAFMessageLogFileRotationTime OBJECT-TYPE
      SYNTAX      OCTET STRING
      MAX-ACCESS  read-only
      STATUS      current
      DESCRIPTION "Determines the start time (hour and minute) for a time-based rotation sequence.  At the time that this value specifies, the server renames the current log file. Thereafter, the server renames the log file at an interval that you specify in File Time Span.  If the specified time has already past, then the server starts its file rotation immediately.   Use the following format: k:mm, where k is the hour in a 24-hour format. mm is the minute"
      ::= { jmsSAFMessageLogFileEntry 12  }
   
   
   jmsSAFMessageLogFileRotateLogOnStartup OBJECT-TYPE
      SYNTAX      OCTET STRING
      MAX-ACCESS  read-only
      STATUS      current
      DESCRIPTION "Specifies whether a server rotates its log file during its startup cycle."
      ::= { jmsSAFMessageLogFileEntry 13  }
   
   
   jmsSAFMessageLogFileName OBJECT-TYPE
      SYNTAX      OCTET STRING
      MAX-ACCESS  read-only
      STATUS      current
      DESCRIPTION "The user-specified name of this MBean instance.  This name is included as one of the key properties in the MBean's javax.management.ObjectName: Name=user-specified-name"
      ::= { jmsSAFMessageLogFileEntry 14  }
   
   
   jmsSAFMessageLogFileLogFileRotationDir OBJECT-TYPE
      SYNTAX      OCTET STRING
      MAX-ACCESS  read-only
      STATUS      current
      DESCRIPTION "The directory where the rotated log files will be stored. By default the rotated files are stored in the same directory where the log file is stored."
      ::= { jmsSAFMessageLogFileEntry 15  }
   
   
   jmxTable OBJECT-TYPE
      SYNTAX      SEQUENCE OF JmxEntry
      MAX-ACCESS  not-accessible
      STATUS      current
      DESCRIPTION "Controls which JMX agents are initialized in the current WebLogic Server domain. Each JMX agent supports specific functions such as monitoring runtime statistics or modifying the domain's configuration."
      ::= { wls 975  }
      
   
   jmxEntry OBJECT-TYPE
      SYNTAX      JmxEntry
      MAX-ACCESS  not-accessible
      STATUS      current
      DESCRIPTION "Generated SNMP Table Entry."
      INDEX { jmxIndex}
      ::= { jmxTable 1 }
      
   JmxEntry ::=
      SEQUENCE
      {
         jmxIndex             OCTET STRING,
         jmxObjectName        OCTET STRING,
         jmxType              OCTET STRING,
         jmxCompatibilityMBeanServerEnabled OCTET STRING,
         jmxManagementEJBEnabled OCTET STRING,
         jmxPlatformMBeanServerEnabled OCTET STRING,
         jmxInvocationTimeoutSeconds Integer32,
         jmxRuntimeMBeanServerEnabled OCTET STRING,
         jmxDomainMBeanServerEnabled OCTET STRING,
         jmxName              OCTET STRING,
         jmxEditMBeanServerEnabled OCTET STRING
      }
      
   
   jmxIndex OBJECT-TYPE
      SYNTAX      OCTET STRING
      MAX-ACCESS  not-accessible
      STATUS      current
      DESCRIPTION "Index column"
      ::= { jmxEntry 1  }
   
   
   jmxObjectName OBJECT-TYPE
      SYNTAX      OCTET STRING
      MAX-ACCESS  read-only
      STATUS      current
      DESCRIPTION "ObjectName column"
      ::= { jmxEntry 2  }
   
   
   jmxType OBJECT-TYPE
      SYNTAX      OCTET STRING
      MAX-ACCESS  read-only
      STATUS      current
      DESCRIPTION "Returns the type of the MBean."
      ::= { jmxEntry 3  }
   
   
   jmxCompatibilityMBeanServerEnabled OBJECT-TYPE
      SYNTAX      OCTET STRING
      MAX-ACCESS  read-only
      STATUS      current
      DESCRIPTION "Enables JMX clients to use the deprecated MBeanHome interface. Prior to 9.0, WebLogic Server supported a typed API layer over its JMX layer. Your JMX application classes could import type-safe interfaces for WebLogic Server MBeans, retrieve a reference to the MBeans through the weblogic.management.MBeanHome interface, and invoke the MBean methods directly."
      ::= { jmxEntry 4  }
   
   
   jmxManagementEJBEnabled OBJECT-TYPE
      SYNTAX      OCTET STRING
      MAX-ACCESS  read-only
      STATUS      current
      DESCRIPTION "Enables access to the Management EJB (MEJB), which is part of the J2EE Management APIs (JSR-77).  The Management API specification provides a standardized management data model for common resources on J2EE Web application servers.  The MEJB provides access to J2EE Managed Objects (JMOs), which describe the common J2EE resources. If you set this attribute to false, WebLogic Server does not register the MEJB in the JNDI tree, and effectively disables the J2EE Management APIs for the domain."
      ::= { jmxEntry 5  }
   
   
   jmxPlatformMBeanServerEnabled OBJECT-TYPE
      SYNTAX      OCTET STRING
      MAX-ACCESS  read-only
      STATUS      current
      DESCRIPTION "Causes each WebLogic Server instance to initialize the JDK's platform MBean server and to use the platform MBean server as the Runtime MBean Server.  As of JDK 1.5, JVMs provide a platform MBean server that local processes can instantiate. There can be only one instance of the platform MBean server for each JVM. When a process instantiates this MBean server, the JVM creates several platform MBeans that provide monitoring data for the JVM itself.  If you set this attribute to true, each WebLogic Server instance invokes the method java.lang.management.ManagementFactory.getPlatformMBeanServer() and thus causes the initialization of the JVM's MBeans. In this case, the server's Runtime MBean Server uses the MBeanServer returned by this method as its MBeanServer. This makes it possible to access the WebLogic Server MBeans and the JVM platform MBeans from a single MBean server. In addition, if you enable the Runtime MBean Server to be the platform MBean server, local processes in the JVM can directly access this MBean server through the MBeanServer interface that java.lang.management.ManagementFactory.getPlatformMBeanServer() returns. With this local access, there are no WebLogic Server security checks to make sure that only authorized users can access WebLogic Server MBeans. Any application that is running in the JVM can access any of the WebLogic Server MBeans in the Runtime MBean Server/JDK Platform MBean Server. Do not use this configuration if you cannot control or cannot trust the applications that are running within a JVM."
      ::= { jmxEntry 6  }
   
   
   jmxInvocationTimeoutSeconds OBJECT-TYPE
      SYNTAX      Integer32
      MAX-ACCESS  read-only
      STATUS      current
      DESCRIPTION "The number of seconds that internal WebLogic Server processes wait to connect to an MBean server, invoke an MBean server method, and return the results of the invocation. If the MBean server method does not complete (return) within the timeout period, WebLogic Server abandons its invocation attempt. Some internal management processes within WebLogic Server require a server instance to connect to MBean servers in other WebLogic Server instances and invoke an MBean server method. The timeout period prevents the internal process from locking up if an MBean server cannot successfully return a method invocation. A value of 0 (zero) prevents the method invocation from timing out. With such a value, the internal process will wait indefinitely until the MBean server's method returns."
      ::= { jmxEntry 7  }
   
   
   jmxRuntimeMBeanServerEnabled OBJECT-TYPE
      SYNTAX      OCTET STRING
      MAX-ACCESS  read-only
      STATUS      current
      DESCRIPTION "Specifies whether each server instance in the domain initializes its Runtime MBean Server, which provides access to a server's runtime MBeans and read-only configuration MBeans.  The Administration Console and the WebLogic Scripting Tool use this MBean server for some (but not all) of their read operations.  If RuntimeMBeanServerEnabled is true, each server starts its Runtime MBean Server during the server's startup cycle. If this attribute is false, no server instance in the domain will start its Runtime MBean Server."
      ::= { jmxEntry 8  }
   
   
   jmxDomainMBeanServerEnabled OBJECT-TYPE
      SYNTAX      OCTET STRING
      MAX-ACCESS  read-only
      STATUS      current
      DESCRIPTION "Specifies whether the Administration Server initializes the Domain MBean Server, which provides federated access to all runtime MBeans and read-only configuration MBeans in the domain. Through it, JMX clients can access all MBeans in a domain through a single connection.  The Administration Console and the WebLogic Scripting Tool use this MBean server for many (but not all) of their read operations.  This MBean server exists only on the Administration Server. The Administration Server initializes it the first time a JMX client requests a connection to it. If you set this attribute to false, the Administration Server will not start this MBean server and JMX clients cannot connect to it.  While this MBean server is instantiated lazily (only when requested), once it is instantiated it does use some memory and network traffic. Disabling this MBean server can conserve a minimal amount of resources, but the trade off is that JMX clients must maintain separate connections for each WebLogic Server's Runtime MBean Server."
      ::= { jmxEntry 9  }
   
   
   jmxName OBJECT-TYPE
      SYNTAX      OCTET STRING
      MAX-ACCESS  read-only
      STATUS      current
      DESCRIPTION "The user-specified name of this MBean instance.  This name is included as one of the key properties in the MBean's javax.management.ObjectName: Name=user-specified-name"
      ::= { jmxEntry 10  }
   
   
   jmxEditMBeanServerEnabled OBJECT-TYPE
      SYNTAX      OCTET STRING
      MAX-ACCESS  read-only
      STATUS      current
      DESCRIPTION "Specifies whether the Administration Server initializes the Edit MBean Server, which contains the hierarchy of MBeans used to make modifications to the domain's configuration. All JMX clients, including utilities such as the Administration Console and the WebLogic Scripting Tool, use the Edit MBean Server to modify a domain's configuration.  This MBean server exists only on the Administration Server. By default, when the Administration Server starts, it starts the Edit MBean Server. If you set the EditMBeanServerEnabled attribute to false, the Administration Server will not start this MBean server. If you disable this MBean server, JMX clients cannot modify the domain's configuration. You can, however, modify the domain configuration through the offline editing feature of WebLogic Scripting Tool.   Note:   Disabling the Edit MBean Server is not sufficient to prevent changes to a domain configuration. Because the WebLogic Server deployment service does not use JMX, the Administration Console and WLST can deploy or undeploy applications even if you have disabled the Edit MBean Server."
      ::= { jmxEntry 11  }
   
   
   jtaMigratableTargetTable OBJECT-TYPE
      SYNTAX      SEQUENCE OF JtaMigratableTargetEntry
      MAX-ACCESS  not-accessible
      STATUS      current
      DESCRIPTION "The target that is used internally to register the JTA recovery manager to the Migration Manager.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 980  }
      
   
   jtaMigratableTargetEntry OBJECT-TYPE
      SYNTAX      JtaMigratableTargetEntry
      MAX-ACCESS  not-accessible
      STATUS      current
      DESCRIPTION "Generated SNMP Table Entry."
      INDEX { jtaMigratableTargetIndex}
      ::= { jtaMigratableTargetTable 1 }
      
   JtaMigratableTargetEntry ::=
      SEQUENCE
      {
         jtaMigratableTargetIndex OCTET STRING,
         jtaMigratableTargetObjectName OCTET STRING,
         jtaMigratableTargetType OCTET STRING,
         jtaMigratableTargetPostScript OCTET STRING,
         jtaMigratableTargetMillisToSleepBetweenAttempts Integer32,
         jtaMigratableTargetNonLocalPostAllowed OCTET STRING,
         jtaMigratableTargetSecondsBetweenRestarts Integer32,
         jtaMigratableTargetPostScriptFailureFatal OCTET STRING,
         jtaMigratableTargetPreScript OCTET STRING,
         jtaMigratableTargetMigrationPolicy OCTET STRING,
         jtaMigratableTargetRestartOnFailure OCTET STRING,
         jtaMigratableTargetStrictOwnershipCheck OCTET STRING,
         jtaMigratableTargetName OCTET STRING,
         jtaMigratableTargetAdditionalMigrationAttempts Integer32,
         jtaMigratableTargetNumberOfRestartAttempts Integer32
      }
      
   
   jtaMigratableTargetIndex OBJECT-TYPE
      SYNTAX      OCTET STRING
      MAX-ACCESS  not-accessible
      STATUS      current
      DESCRIPTION "Index column"
      ::= { jtaMigratableTargetEntry 1  }
   
   
   jtaMigratableTargetObjectName OBJECT-TYPE
      SYNTAX      OCTET STRING
      MAX-ACCESS  read-only
      STATUS      current
      DESCRIPTION "ObjectName column"
      ::= { jtaMigratableTargetEntry 2  }
   
   
   jtaMigratableTargetType OBJECT-TYPE
      SYNTAX      OCTET STRING
      MAX-ACCESS  read-only
      STATUS      current
      DESCRIPTION "Returns the type of the MBean."
      ::= { jtaMigratableTargetEntry 3  }
   
   
   jtaMigratableTargetPostScript OBJECT-TYPE
      SYNTAX      OCTET STRING
      MAX-ACCESS  read-only
      STATUS      current
      DESCRIPTION "Specifies the path to the post-migration script to run after a migratable target is fully deactivated. The script must be in the BEA_HOME/user_projects/domains/mydomain/bin/service_migration directory.  After the migratable target is deactivated, if there is a script specified, and Node Manager is available, then the sript will run. Specfiying a script without an available Node Manager will result in an error upon migration."
      ::= { jtaMigratableTargetEntry 4  }
   
   
   jtaMigratableTargetMillisToSleepBetweenAttempts OBJECT-TYPE
      SYNTAX      Integer32
      MAX-ACCESS  read-only
      STATUS      current
      DESCRIPTION "Controls how long of a pause there should be between the migration attempts described in getAdditionalMigrationAttempts(). Note that this delay only happens when the service has failed to come up on every server. It does not cause any sort of delay between attempts to migrate otherwise."
      ::= { jtaMigratableTargetEntry 5  }
   
   
   jtaMigratableTargetNonLocalPostAllowed OBJECT-TYPE
      SYNTAX      OCTET STRING
      MAX-ACCESS  read-only
      STATUS      current
      DESCRIPTION "Specifies whether or not the post-deactivation script is allowed to run on a different machine.  Normally, when automigration occurs, the post-deactivation script will be run on the service's current location, and the pre-activation script on the service's new location. If the current location is unreachable for some reason, this value will be checked to see if it is safe to run it on the service's new machine.  This is useful if the post-deactivation script controls access to a networked resource and does not need any data from the current machine."
      ::= { jtaMigratableTargetEntry 6  }
   
   
   jtaMigratableTargetSecondsBetweenRestarts OBJECT-TYPE
      SYNTAX      Integer32
      MAX-ACCESS  read-only
      STATUS      current
      DESCRIPTION "Specifies how many seconds to wait in between attempts to restart the failed service."
      ::= { jtaMigratableTargetEntry 7  }
   
   
   jtaMigratableTargetPostScriptFailureFatal OBJECT-TYPE
      SYNTAX      OCTET STRING
      MAX-ACCESS  read-only
      STATUS      current
      DESCRIPTION "Specifies whether or not a failure during execution of the post-deactivation script is fatal to the migration.  If it is fatal, the migratable target will not be automatically migrated until an administrator manually migrates it to a server, thus reactivating it.  Note: Enabling this value will result in weakening the exactly-once guarantee. It is provided to prevent more dangerous data corruption if the post-deactivation script fails. Also if this value is enabled, then the script may be called more than once by the migration framework after the Migratable Target is deactivated or the server or machine hosting the Migratable Target crashed or is network partitioned. The script is expected not to return different exit values when invoked multiple times in such scenarios."
      ::= { jtaMigratableTargetEntry 8  }
   
   
   jtaMigratableTargetPreScript OBJECT-TYPE
      SYNTAX      OCTET STRING
      MAX-ACCESS  read-only
      STATUS      current
      DESCRIPTION "Specifies the path to the pre-migration script to run before a migratable target is actually activated. The script must be in the BEA_HOME/user_projects/domains/mydomain/bin/service_migration directory.  Before the migratable target is activated, if there is a script specified, and Node Manager is available, then the script will run. Specifying a script without an available Node Manager will result in an error upon migration.  If the script fails or cannot be found, migration will not proceed on the current server, and will be tried on the next suitable server. This could be the next server in the candidate server list, or in the cluster, if there is no candidate server list."
      ::= { jtaMigratableTargetEntry 9  }
   
   
   jtaMigratableTargetMigrationPolicy OBJECT-TYPE
      SYNTAX      OCTET STRING
      MAX-ACCESS  read-only
      STATUS      current
      DESCRIPTION ""
      ::= { jtaMigratableTargetEntry 10  }
   
   
   jtaMigratableTargetRestartOnFailure OBJECT-TYPE
      SYNTAX      OCTET STRING
      MAX-ACCESS  read-only
      STATUS      current
      DESCRIPTION "Specifies whether or not a failed service will first be deactivated and reactivated in place, instead of being migrated.  The number of restart attempts is controlled by {@link #getNumberOfRestartAttempts}. Once these restart attempts are exhausted, the service will migrate. A restarting migratable target will deactivate all services on it in order, then reactivate them all."
      ::= { jtaMigratableTargetEntry 11  }
   
   
   jtaMigratableTargetStrictOwnershipCheck OBJECT-TYPE
      SYNTAX      OCTET STRING
      MAX-ACCESS  read-only
      STATUS      current
      DESCRIPTION "Whether continue to boot if cannot find the current owner of TRS to do failback. This attribute is only meaningful for servers in cluster.   If true: server will fail to boot under this situation. If false: server will continue to boot without trying to do failback."
      ::= { jtaMigratableTargetEntry 12  }
   
   
   jtaMigratableTargetName OBJECT-TYPE
      SYNTAX      OCTET STRING
      MAX-ACCESS  read-only
      STATUS      current
      DESCRIPTION "The user-specified name of this MBean instance.  This name is included as one of the key properties in the MBean's javax.management.ObjectName: Name=user-specified-name"
      ::= { jtaMigratableTargetEntry 13  }
   
   
   jtaMigratableTargetAdditionalMigrationAttempts OBJECT-TYPE
      SYNTAX      Integer32
      MAX-ACCESS  read-only
      STATUS      current
      DESCRIPTION "A migratable service could fail to come up on every possible configured server. This attribute controls how many further attempts, after the service has failed on every server at least once, should be tried. Note that each attempt specified here indicates another full circut of migrations amongst all the configured servers. So for a 3-server cluster, and a value of 2, a total of 4 additional migrations will be attempted. (the original server is never a valid destination)"
      ::= { jtaMigratableTargetEntry 14  }
   
   
   jtaMigratableTargetNumberOfRestartAttempts OBJECT-TYPE
      SYNTAX      Integer32
      MAX-ACCESS  read-only
      STATUS      current
      DESCRIPTION "Specfies how many restart attempts to make before migrating the failed service.  Note that these are consecutive attempts. If the value is set to 6, and the service restart fails 5 times before succeeding, but then fails again later, it will not instantly migrate. Each failure gets its own count of restart attempts.  A value of 0 is identical to setting {@link #getRestartOnFailure} to false. A value of -1 indicates the service should never be migrated; instead, it will be restarted until it either works or the server shuts down."
      ::= { jtaMigratableTargetEntry 15  }
   
   
   joltConnectionPoolTable OBJECT-TYPE
      SYNTAX      SEQUENCE OF JoltConnectionPoolEntry
      MAX-ACCESS  not-accessible
      STATUS      current
      DESCRIPTION "This bean defines a Jolt connection pool."
      ::= { wls 985  }
      
   
   joltConnectionPoolEntry OBJECT-TYPE
      SYNTAX      JoltConnectionPoolEntry
      MAX-ACCESS  not-accessible
      STATUS      current
      DESCRIPTION "Generated SNMP Table Entry."
      INDEX { joltConnectionPoolIndex}
      ::= { joltConnectionPoolTable 1 }
      
   JoltConnectionPoolEntry ::=
      SEQUENCE
      {
         joltConnectionPoolIndex OCTET STRING,
         joltConnectionPoolObjectName OCTET STRING,
         joltConnectionPoolType OCTET STRING,
         joltConnectionPoolMinimumPoolSize Integer32,
         joltConnectionPoolMaximumPoolSize Integer32,
         joltConnectionPoolName OCTET STRING,
         joltConnectionPoolUserName OCTET STRING,
         joltConnectionPoolDeploymentOrder Integer32,
         joltConnectionPoolRecvTimeout Integer32,
         joltConnectionPoolSecurityContextEnabled OCTET STRING,
         joltConnectionPoolTrustStoreName OCTET STRING,
         joltConnectionPoolUserRole OCTET STRING,
         joltConnectionPoolKeyStoreName OCTET STRING
      }
      
   
   joltConnectionPoolIndex OBJECT-TYPE
      SYNTAX      OCTET STRING
      MAX-ACCESS  not-accessible
      STATUS      current
      DESCRIPTION "Index column"
      ::= { joltConnectionPoolEntry 1  }
   
   
   joltConnectionPoolObjectName OBJECT-TYPE
      SYNTAX      OCTET STRING
      MAX-ACCESS  read-only
      STATUS      current
      DESCRIPTION "ObjectName column"
      ::= { joltConnectionPoolEntry 2  }
   
   
   joltConnectionPoolType OBJECT-TYPE
      SYNTAX      OCTET STRING
      MAX-ACCESS  read-only
      STATUS      current
      DESCRIPTION "Returns the type of the MBean."
      ::= { joltConnectionPoolEntry 3  }
   
   
   joltConnectionPoolMinimumPoolSize OBJECT-TYPE
      SYNTAX      Integer32
      MAX-ACCESS  read-only
      STATUS      current
      DESCRIPTION "The minimum number of connections to be added to this Jolt connection pool when WebLogic Server starts."
      ::= { joltConnectionPoolEntry 4  }
   
   
   joltConnectionPoolMaximumPoolSize OBJECT-TYPE
      SYNTAX      Integer32
      MAX-ACCESS  read-only
      STATUS      current
      DESCRIPTION "The maximum number of connections that can be made from this Jolt connection pool."
      ::= { joltConnectionPoolEntry 5  }
   
   
   joltConnectionPoolName OBJECT-TYPE
      SYNTAX      OCTET STRING
      MAX-ACCESS  read-only
      STATUS      current
      DESCRIPTION "The user-specified name of this MBean instance.  This name is included as one of the key properties in the MBean's javax.management.ObjectName: Name=user-specified-name"
      ::= { joltConnectionPoolEntry 6  }
   
   
   joltConnectionPoolUserName OBJECT-TYPE
      SYNTAX      OCTET STRING
      MAX-ACCESS  read-only
      STATUS      current
      DESCRIPTION "A user name that applications specify to connect to this Jolt connection pool. If Security Context is enabled, this name must be the name of an authorized Tuxedo user. (Specifying a Tuxedo user name is required if the Tuxedo authentication level is USER_AUTH.)"
      ::= { joltConnectionPoolEntry 7  }
   
   
   joltConnectionPoolDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { joltConnectionPoolEntry 8  }
   
   
   joltConnectionPoolRecvTimeout OBJECT-TYPE
      SYNTAX      Integer32
      MAX-ACCESS  read-only
      STATUS      current
      DESCRIPTION "The number of seconds the client waits to receive a response before timing out."
      ::= { joltConnectionPoolEntry 9  }
   
   
   joltConnectionPoolSecurityContextEnabled OBJECT-TYPE
      SYNTAX      OCTET STRING
      MAX-ACCESS  read-only
      STATUS      current
      DESCRIPTION "Indicates whether this Jolt connection pool passes the connection pool's security context (user name, password and other information) from the WebLogic Server user to the Tuxedo domain.  If you enable the connection pool to pass the security context, you must start the Jolt Service Handler (JSH) with the -a option. When the JSH gets a message with the caller's identity, it calls impersonate_user() to get the appkey for the user. JSH caches the appkey, so the next time the caller makes a request, the appkey is retrieved from the cache and the request is forwarded to the service. A cache is maintained by each JSH, which means that there will be a cache maintained for all the session pools connected to the same JSH.  You must enable Security Context if Tuxedo requires secured connections."
      ::= { joltConnectionPoolEntry 10  }
   
   
   joltConnectionPoolTrustStoreName OBJECT-TYPE
      SYNTAX      OCTET STRING
      MAX-ACCESS  read-only
      STATUS      current
      DESCRIPTION "The path and file name of the keystore containing the trust certificates."
      ::= { joltConnectionPoolEntry 11  }
   
   
   joltConnectionPoolUserRole OBJECT-TYPE
      SYNTAX      OCTET STRING
      MAX-ACCESS  read-only
      STATUS      current
      DESCRIPTION "The Tuxedo user role for this Jolt connection pool. (This is required only when the security level in the Tuxedo domain is USER_AUTH, ACL, or MANDATORY_ACL)."
      ::= { joltConnectionPoolEntry 12  }
   
   
   joltConnectionPoolKeyStoreName OBJECT-TYPE
      SYNTAX      OCTET STRING
      MAX-ACCESS  read-only
      STATUS      current
      DESCRIPTION "The path and file name of the keystore containing the private key used in SSL mutual authentication."
      ::= { joltConnectionPoolEntry 13  }
   
   
   logFilterTable OBJECT-TYPE
      SYNTAX      SEQUENCE OF LogFilterEntry
      MAX-ACCESS  not-accessible
      STATUS      current
      DESCRIPTION "This MBean represents a filter to qualify log messages which are selected by the specified filter expression criteria. A message must meet all the specified criteria to qualify the filter. Multiple instances of this MBean can be defined, if needed. If there are multiple instances, a message must qualify at least one filter to qualify for the log file.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 990  }
      
   
   logFilterEntry OBJECT-TYPE
      SYNTAX      LogFilterEntry
      MAX-ACCESS  not-accessible
      STATUS      current
      DESCRIPTION "Generated SNMP Table Entry."
      INDEX { logFilterIndex}
      ::= { logFilterTable 1 }
      
   LogFilterEntry ::=
      SEQUENCE
      {
         logFilterIndex       OCTET STRING,
         logFilterObjectName  OCTET STRING,
         logFilterType        OCTET STRING,
         logFilterFilterExpression OCTET STRING,
         logFilterName        OCTET STRING
      }
      
   
   logFilterIndex OBJECT-TYPE
      SYNTAX      OCTET STRING
      MAX-ACCESS  not-accessible
      STATUS      current
      DESCRIPTION "Index column"
      ::= { logFilterEntry 1  }
   
   
   logFilterObjectName OBJECT-TYPE
      SYNTAX      OCTET STRING
      MAX-ACCESS  read-only
      STATUS      current
      DESCRIPTION "ObjectName column"
      ::= { logFilterEntry 2  }
   
   
   logFilterType OBJECT-TYPE
      SYNTAX      OCTET STRING
      MAX-ACCESS  read-only
      STATUS      current
      DESCRIPTION "Returns the type of the MBean."
      ::= { logFilterEntry 3  }
   
   
   logFilterFilterExpression OBJECT-TYPE
      SYNTAX      OCTET STRING
      MAX-ACCESS  read-only
      STATUS      current
      DESCRIPTION "The filter expression to be evaluated for qualifying log messages.  The filter expression is specified as a string in the query language. The query language supports Boolean operators: AND, OR, and NOT, and relational operators. You can use the following column names (message attributes) in a query to filter data going to a log destination: RECORDID, DATE, SEVERITY, SUBSYSTEM, MACHINE, SERVER, THREAD, USERID, TXID, CONTEXTID, TIMESTAMP, MSGID, and MESSAGE."
      ::= { logFilterEntry 4  }
   
   
   logFilterName OBJECT-TYPE
      SYNTAX      OCTET STRING
      MAX-ACCESS  read-only
      STATUS      current
      DESCRIPTION "The user-specified name of this MBean instance.  This name is included as one of the key properties in the MBean's javax.management.ObjectName: Name=user-specified-name"
      ::= { logFilterEntry 5  }
   
   
   mailSessionTable OBJECT-TYPE
      SYNTAX      SEQUENCE OF MailSessionEntry
      MAX-ACCESS  not-accessible
      STATUS      current
      DESCRIPTION "Facilitates using the JavaMail APIs, which provide applications and other J2EE modules with access to Internet Message Access Protocol (IMAP)- and Simple Mail Transfer Protocol (SMTP)-capable mail servers on your network or the Internet.  In the reference implementation of JavaMail, applications must instantiate javax.mail.Session objects, which designate mail hosts, transport and store protocols, and a default mail user for connecting to a mail server. In WebLogic Server, you create a mail session, which configures a javax.mail.Session object and registers it in the WebLogic Server JNDI tree. Applications access the mail session through JNDI instead of instantiating their own javax.mail.Session object.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 995  }
      
   
   mailSessionEntry OBJECT-TYPE
      SYNTAX      MailSessionEntry
      MAX-ACCESS  not-accessible
      STATUS      current
      DESCRIPTION "Generated SNMP Table Entry."
      INDEX { mailSessionIndex}
      ::= { mailSessionTable 1 }
      
   MailSessionEntry ::=
      SEQUENCE
      {
         mailSessionIndex     OCTET STRING,
         mailSessionObjectName OCTET STRING,
         mailSessionType      OCTET STRING,
         mailSessionDeploymentOrder Integer32,
         mailSessionJNDIName  OCTET STRING,
         mailSessionName      OCTET STRING
      }
      
   
   mailSessionIndex OBJECT-TYPE
      SYNTAX      OCTET STRING
      MAX-ACCESS  not-accessible
      STATUS      current
      DESCRIPTION "Index column"
      ::= { mailSessionEntry 1  }
   
   
   mailSessionObjectName OBJECT-TYPE
      SYNTAX      OCTET STRING
      MAX-ACCESS  read-only
      STATUS      current
      DESCRIPTION "ObjectName column"
      ::= { mailSessionEntry 2  }
   
   
   mailSessionType OBJECT-TYPE
      SYNTAX      OCTET STRING
      MAX-ACCESS  read-only
      STATUS      current
      DESCRIPTION "Returns the type of the MBean."
      ::= { mailSessionEntry 3  }
   
   
   mailSessionDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { mailSessionEntry 4  }
   
   
   mailSessionJNDIName OBJECT-TYPE
      SYNTAX      OCTET STRING
      MAX-ACCESS  read-only
      STATUS      current
      DESCRIPTION "The JNDI Name associated with this resource."
      ::= { mailSessionEntry 5  }
   
   
   mailSessionName OBJECT-TYPE
      SYNTAX      OCTET STRING
      MAX-ACCESS  read-only
      STATUS      current
      DESCRIPTION "The user-specified name of this MBean instance.  This name is included as one of the key properties in the MBean's javax.management.ObjectName: Name=user-specified-name"
      ::= { mailSessionEntry 6  }
   
   
   maxThreadsConstraintTable OBJECT-TYPE
      SYNTAX      SEQUENCE OF MaxThreadsConstraintEntry
      MAX-ACCESS  not-accessible
      STATUS      current
      DESCRIPTION "This MBean defines the max number of concurrent threads that can execute requests sharing this max constraint.  MaxThreadsConstraint can be used to tell the server that the requests are constrained by an external resource like a database and allocating more threads that the external resource limit is not going to help since the extra threads are just going to wait."
      ::= { wls 1000  }
      
   
   maxThreadsConstraintEntry OBJECT-TYPE
      SYNTAX      MaxThreadsConstraintEntry
      MAX-ACCESS  not-accessible
      STATUS      current
      DESCRIPTION "Generated SNMP Table Entry."
      INDEX { maxThreadsConstraintIndex}
      ::= { maxThreadsConstraintTable 1 }
      
   MaxThreadsConstraintEntry ::=
      SEQUENCE
      {
         maxThreadsConstraintIndex OCTET STRING,
         maxThreadsConstraintObjectName OCTET STRING,
         maxThreadsConstraintType OCTET STRING,
         maxThreadsConstraintDeploymentOrder Integer32,
         maxThreadsConstraintCount Integer32,
         maxThreadsConstraintName OCTET STRING,
         maxThreadsConstraintConnectionPoolName OCTET STRING
      }
      
   
   maxThreadsConstraintIndex OBJECT-TYPE
      SYNTAX      OCTET STRING
      MAX-ACCESS  not-accessible
      STATUS      current
      DESCRIPTION "Index column"
      ::= { maxThreadsConstraintEntry 1  }
   
   
   maxThreadsConstraintObjectName OBJECT-TYPE
      SYNTAX      OCTET STRING
      MAX-ACCESS  read-only
      STATUS      current
      DESCRIPTION "ObjectName column"
      ::= { maxThreadsConstraintEntry 2  }
   
   
   maxThreadsConstraintType OBJECT-TYPE
      SYNTAX      OCTET STRING
      MAX-ACCESS  read-only
      STATUS      current
      DESCRIPTION "Returns the type of the MBean."
      ::= { maxThreadsConstraintEntry 3  }
   
   
   maxThreadsConstraintDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { maxThreadsConstraintEntry 4  }
   
   
   maxThreadsConstraintCount OBJECT-TYPE
      SYNTAX      Integer32
      MAX-ACCESS  read-only
      STATUS      current
      DESCRIPTION "Maximum number of concurrent threads that can execute requests sharing this constraint.  A count of 0 or -1 is treated as if the constraint is not present. This means that no constraint is enforced for these two values. A count > 0 can be dynamically changed to 0 to indicate that constraint enforcement is no longer needed."
      ::= { maxThreadsConstraintEntry 5  }
   
   
   maxThreadsConstraintName OBJECT-TYPE
      SYNTAX      OCTET STRING
      MAX-ACCESS  read-only
      STATUS      current
      DESCRIPTION "The user-specified name of this MBean instance.  This name is included as one of the key properties in the MBean's javax.management.ObjectName: Name=user-specified-name"
      ::= { maxThreadsConstraintEntry 6  }
   
   
   maxThreadsConstraintConnectionPoolName OBJECT-TYPE
      SYNTAX      OCTET STRING
      MAX-ACCESS  read-only
      STATUS      current
      DESCRIPTION "Name of the connection pool whose size is taken as the max constraint.  This can be the name of a JDBC data source. The max capacity of the data source is used as the constraint."
      ::= { maxThreadsConstraintEntry 7  }
   
   
   migratableRMIServiceTable OBJECT-TYPE
      SYNTAX      SEQUENCE OF MigratableRMIServiceEntry
      MAX-ACCESS  not-accessible
      STATUS      current
      DESCRIPTION "TEST SERVICE FOR MIGRATABLE SERVICES"
      ::= { wls 1005  }
      
   
   migratableRMIServiceEntry OBJECT-TYPE
      SYNTAX      MigratableRMIServiceEntry
      MAX-ACCESS  not-accessible
      STATUS      current
      DESCRIPTION "Generated SNMP Table Entry."
      INDEX { migratableRMIServiceIndex}
      ::= { migratableRMIServiceTable 1 }
      
   MigratableRMIServiceEntry ::=
      SEQUENCE
      {
         migratableRMIServiceIndex OCTET STRING,
         migratableRMIServiceObjectName OCTET STRING,
         migratableRMIServiceType OCTET STRING,
         migratableRMIServiceDeploymentOrder Integer32,
         migratableRMIServiceName OCTET STRING
      }
      
   
   migratableRMIServiceIndex OBJECT-TYPE
      SYNTAX      OCTET STRING
      MAX-ACCESS  not-accessible
      STATUS      current
      DESCRIPTION "Index column"
      ::= { migratableRMIServiceEntry 1  }
   
   
   migratableRMIServiceObjectName OBJECT-TYPE
      SYNTAX      OCTET STRING
      MAX-ACCESS  read-only
      STATUS      current
      DESCRIPTION "ObjectName column"
      ::= { migratableRMIServiceEntry 2  }
   
   
   migratableRMIServiceType OBJECT-TYPE
      SYNTAX      OCTET STRING
      MAX-ACCESS  read-only
      STATUS      current
      DESCRIPTION "Returns the type of the MBean."
      ::= { migratableRMIServiceEntry 3  }
   
   
   migratableRMIServiceDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { migratableRMIServiceEntry 4  }
   
   
   migratableRMIServiceName OBJECT-TYPE
      SYNTAX      OCTET STRING
      MAX-ACCESS  read-only
      STATUS      current
      DESCRIPTION "The user-specified name of this MBean instance.  This name is included as one of the key properties in the MBean's javax.management.ObjectName: Name=user-specified-name"
      ::= { migratableRMIServiceEntry 5  }
   
   
   minThreadsConstraintTable OBJECT-TYPE
      SYNTAX      SEQUENCE OF MinThreadsConstraintEntry
      MAX-ACCESS  not-accessible
      STATUS      current
      DESCRIPTION "This MBean defines the minimum number of concurrent threads that should allocated to this constraint provided there are enough pending requests.   Multiple WorkManagers can share a common MinThreadsConstraint. MinThreadsConstraint perform their own bookkeeping and demand a thread when the constraint is not met and there are enough requests.    MinThreadsConstraint should be used to tell the WebLogic Server that a certain number of minimum threads are necessary to prevent server to server deadlocks. Although the server is self-tuning, specifying MinThreadsConstraint ensures that the server guarantees minimum threads to avoid the distributed deadlocks.   Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1010  }
      
   
   minThreadsConstraintEntry OBJECT-TYPE
      SYNTAX      MinThreadsConstraintEntry
      MAX-ACCESS  not-accessible
      STATUS      current
      DESCRIPTION "Generated SNMP Table Entry."
      INDEX { minThreadsConstraintIndex}
      ::= { minThreadsConstraintTable 1 }
      
   MinThreadsConstraintEntry ::=
      SEQUENCE
      {
         minThreadsConstraintIndex OCTET STRING,
         minThreadsConstraintObjectName OCTET STRING,
         minThreadsConstraintType OCTET STRING,
         minThreadsConstraintDeploymentOrder Integer32,
         minThreadsConstraintCount Integer32,
         minThreadsConstraintName OCTET STRING
      }
      
   
   minThreadsConstraintIndex OBJECT-TYPE
      SYNTAX      OCTET STRING
      MAX-ACCESS  not-accessible
      STATUS      current
      DESCRIPTION "Index column"
      ::= { minThreadsConstraintEntry 1  }
   
   
   minThreadsConstraintObjectName OBJECT-TYPE
      SYNTAX      OCTET STRING
      MAX-ACCESS  read-only
      STATUS      current
      DESCRIPTION "ObjectName column"
      ::= { minThreadsConstraintEntry 2  }
   
   
   minThreadsConstraintType OBJECT-TYPE
      SYNTAX      OCTET STRING
      MAX-ACCESS  read-only
      STATUS      current
      DESCRIPTION "Returns the type of the MBean."
      ::= { minThreadsConstraintEntry 3  }
   
   
   minThreadsConstraintDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { minThreadsConstraintEntry 4  }
   
   
   minThreadsConstraintCount OBJECT-TYPE
      SYNTAX      Integer32
      MAX-ACCESS  read-only
      STATUS      current
      DESCRIPTION "Minimum number of concurrent threads executing requests that share this constraint.  A count of 0 or -1 is treated as if the constraint is not present. This means that the constraint is ignored for these two values. A count > 0 can be dynamically changed to 0 to indicate that constraint enforcement is no longer needed."
      ::= { minThreadsConstraintEntry 5  }
   
   
   minThreadsConstraintName OBJECT-TYPE
      SYNTAX      OCTET STRING
      MAX-ACCESS  read-only
      STATUS      current
      DESCRIPTION "The user-specified name of this MBean instance.  This name is included as one of the key properties in the MBean's javax.management.ObjectName: Name=user-specified-name"
      ::= { minThreadsConstraintEntry 6  }
   
   
   overloadProtectionTable OBJECT-TYPE
      SYNTAX      SEQUENCE OF OverloadProtectionEntry
      MAX-ACCESS  not-accessible
      STATUS      current
      DESCRIPTION "This Mbean has attributes concerning server overload protection.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1015  }
      
   
   overloadProtectionEntry OBJECT-TYPE
      SYNTAX      OverloadProtectionEntry
      MAX-ACCESS  not-accessible
      STATUS      current
      DESCRIPTION "Generated SNMP Table Entry."
      INDEX { overloadProtectionIndex}
      ::= { overloadProtectionTable 1 }
      
   OverloadProtectionEntry ::=
      SEQUENCE
      {
         overloadProtectionIndex OCTET STRING,
         overloadProtectionObjectName OCTET STRING,
         overloadProtectionType OCTET STRING,
         overloadProtectionSharedCapacityForWorkManagers Integer32,
         overloadProtectionFreeMemoryPercentLowThreshold Integer32,
         overloadProtectionFailureAction OCTET STRING,
         overloadProtectionFreeMemoryPercentHighThreshold Integer32,
         overloadProtectionName OCTET STRING,
         overloadProtectionPanicAction OCTET STRING
      }
      
   
   overloadProtectionIndex OBJECT-TYPE
      SYNTAX      OCTET STRING
      MAX-ACCESS  not-accessible
      STATUS      current
      DESCRIPTION "Index column"
      ::= { overloadProtectionEntry 1  }
   
   
   overloadProtectionObjectName OBJECT-TYPE
      SYNTAX      OCTET STRING
      MAX-ACCESS  read-only
      STATUS      current
      DESCRIPTION "ObjectName column"
      ::= { overloadProtectionEntry 2  }
   
   
   overloadProtectionType OBJECT-TYPE
      SYNTAX      OCTET STRING
      MAX-ACCESS  read-only
      STATUS      current
      DESCRIPTION "Returns the type of the MBean."
      ::= { overloadProtectionEntry 3  }
   
   
   overloadProtectionSharedCapacityForWorkManagers OBJECT-TYPE
      SYNTAX      Integer32
      MAX-ACCESS  read-only
      STATUS      current
      DESCRIPTION "Total number of requests that can be present in the server. This includes requests that are enqueued and those under execution.  The server performs a differentiated denial of service on reaching the shared capacity. A request with higher priority will be accepted in place of a lower priority request already in the queue. The lower priority request is kept waiting in the queue till all high priority requests are executed. Further enqueues of the low priority requests are rejected right away."
      ::= { overloadProtectionEntry 4  }
   
   
   overloadProtectionFreeMemoryPercentLowThreshold OBJECT-TYPE
      SYNTAX      Integer32
      MAX-ACCESS  read-only
      STATUS      current
      DESCRIPTION "Percentage free memory below which the server is considered overloaded. WorkManagers perform overloadAction once the server is marked as overloaded."
      ::= { overloadProtectionEntry 5  }
   
   
   overloadProtectionFailureAction OBJECT-TYPE
      SYNTAX      OCTET STRING
      MAX-ACCESS  read-only
      STATUS      current
      DESCRIPTION "Enable automatic forceshutdown of the server on failed state. The server self-health monitoring detects fatal failures and mark the server as failed. The server can be restarted using NodeManager or a HA agent."
      ::= { overloadProtectionEntry 6  }
   
   
   overloadProtectionFreeMemoryPercentHighThreshold OBJECT-TYPE
      SYNTAX      Integer32
      MAX-ACCESS  read-only
      STATUS      current
      DESCRIPTION "Percentage free memory after which the server overload condition is cleared. WorkManagers stop performing overloadActions and start regular execution once the overload condition is cleared."
      ::= { overloadProtectionEntry 7  }
   
   
   overloadProtectionName OBJECT-TYPE
      SYNTAX      OCTET STRING
      MAX-ACCESS  read-only
      STATUS      current
      DESCRIPTION "The user-specified name of this MBean instance.  This name is included as one of the key properties in the MBean's javax.management.ObjectName: Name=user-specified-name"
      ::= { overloadProtectionEntry 8  }
   
   
   overloadProtectionPanicAction OBJECT-TYPE
      SYNTAX      OCTET STRING
      MAX-ACCESS  read-only
      STATUS      current
      DESCRIPTION "Exit the server process when the kernel encounters a panic condition like an unhandled OOME. An unhandled OOME could lead to inconsistent state and a server restart is advisable if backed by node manager or a HA agent."
      ::= { overloadProtectionEntry 9  }
   
   
   pathServiceTable OBJECT-TYPE
      SYNTAX      SEQUENCE OF PathServiceEntry
      MAX-ACCESS  not-accessible
      STATUS      current
      DESCRIPTION "This class represents a path service.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1020  }
      
   
   pathServiceEntry OBJECT-TYPE
      SYNTAX      PathServiceEntry
      MAX-ACCESS  not-accessible
      STATUS      current
      DESCRIPTION "Generated SNMP Table Entry."
      INDEX { pathServiceIndex}
      ::= { pathServiceTable 1 }
      
   PathServiceEntry ::=
      SEQUENCE
      {
         pathServiceIndex     OCTET STRING,
         pathServiceObjectName OCTET STRING,
         pathServiceType      OCTET STRING,
         pathServiceDeploymentOrder Integer32,
         pathServiceName      OCTET STRING
      }
      
   
   pathServiceIndex OBJECT-TYPE
      SYNTAX      OCTET STRING
      MAX-ACCESS  not-accessible
      STATUS      current
      DESCRIPTION "Index column"
      ::= { pathServiceEntry 1  }
   
   
   pathServiceObjectName OBJECT-TYPE
      SYNTAX      OCTET STRING
      MAX-ACCESS  read-only
      STATUS      current
      DESCRIPTION "ObjectName column"
      ::= { pathServiceEntry 2  }
   
   
   pathServiceType OBJECT-TYPE
      SYNTAX      OCTET STRING
      MAX-ACCESS  read-only
      STATUS      current
      DESCRIPTION "Returns the type of the MBean."
      ::= { pathServiceEntry 3  }
   
   
   pathServiceDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { pathServiceEntry 4  }
   
   
   pathServiceName OBJECT-TYPE
      SYNTAX      OCTET STRING
      MAX-ACCESS  read-only
      STATUS      current
      DESCRIPTION "The user-specified name of this MBean instance.  This name is included as one of the key properties in the MBean's javax.management.ObjectName: Name=user-specified-name"
      ::= { pathServiceEntry 5  }
   
   
   remoteSAFContextTable OBJECT-TYPE
      SYNTAX      SEQUENCE OF RemoteSAFContextEntry
      MAX-ACCESS  not-accessible
      STATUS      current
      DESCRIPTION "Fake RemoteSAFContextMBean  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1025  }
      
   
   remoteSAFContextEntry OBJECT-TYPE
      SYNTAX      RemoteSAFContextEntry
      MAX-ACCESS  not-accessible
      STATUS      current
      DESCRIPTION "Generated SNMP Table Entry."
      INDEX { remoteSAFContextIndex}
      ::= { remoteSAFContextTable 1 }
      
   RemoteSAFContextEntry ::=
      SEQUENCE
      {
         remoteSAFContextIndex OCTET STRING,
         remoteSAFContextObjectName OCTET STRING,
         remoteSAFContextType OCTET STRING,
         remoteSAFContextProtocol OCTET STRING,
         remoteSAFContextUrl  OCTET STRING,
         remoteSAFContextPassword OCTET STRING,
         remoteSAFContextJndiInitialContextFactory OCTET STRING,
         remoteSAFContextName OCTET STRING,
         remoteSAFContextJndiProperty OCTET STRING,
         remoteSAFContextUsername OCTET STRING
      }
      
   
   remoteSAFContextIndex OBJECT-TYPE
      SYNTAX      OCTET STRING
      MAX-ACCESS  not-accessible
      STATUS      current
      DESCRIPTION "Index column"
      ::= { remoteSAFContextEntry 1  }
   
   
   remoteSAFContextObjectName OBJECT-TYPE
      SYNTAX      OCTET STRING
      MAX-ACCESS  read-only
      STATUS      current
      DESCRIPTION "ObjectName column"
      ::= { remoteSAFContextEntry 2  }
   
   
   remoteSAFContextType OBJECT-TYPE
      SYNTAX      OCTET STRING
      MAX-ACCESS  read-only
      STATUS      current
      DESCRIPTION "Returns the type of the MBean."
      ::= { remoteSAFContextEntry 3  }
   
   
   remoteSAFContextProtocol OBJECT-TYPE
      SYNTAX      OCTET STRING
      MAX-ACCESS  read-only
      STATUS      current
      DESCRIPTION "Protocol"
      ::= { remoteSAFContextEntry 4  }
   
   
   remoteSAFContextUrl OBJECT-TYPE
      SYNTAX      OCTET STRING
      MAX-ACCESS  read-only
      STATUS      current
      DESCRIPTION "URL"
      ::= { remoteSAFContextEntry 5  }
   
   
   remoteSAFContextPassword OBJECT-TYPE
      SYNTAX      OCTET STRING
      MAX-ACCESS  read-only
      STATUS      current
      DESCRIPTION "Password"
      ::= { remoteSAFContextEntry 6  }
   
   
   remoteSAFContextJndiInitialContextFactory OBJECT-TYPE
      SYNTAX      OCTET STRING
      MAX-ACCESS  read-only
      STATUS      current
      DESCRIPTION "JndiInitialContextFactory"
      ::= { remoteSAFContextEntry 7  }
   
   
   remoteSAFContextName OBJECT-TYPE
      SYNTAX      OCTET STRING
      MAX-ACCESS  read-only
      STATUS      current
      DESCRIPTION "The user-specified name of this MBean instance.  This name is included as one of the key properties in the MBean's javax.management.ObjectName: Name=user-specified-name"
      ::= { remoteSAFContextEntry 8  }
   
   
   remoteSAFContextJndiProperty OBJECT-TYPE
      SYNTAX      OCTET STRING
      MAX-ACCESS  read-only
      STATUS      current
      DESCRIPTION "JndiProperty"
      ::= { remoteSAFContextEntry 9  }
   
   
   remoteSAFContextUsername OBJECT-TYPE
      SYNTAX      OCTET STRING
      MAX-ACCESS  read-only
      STATUS      current
      DESCRIPTION "UserName"
      ::= { remoteSAFContextEntry 10  }
   
   
   responseTimeRequestClassTable OBJECT-TYPE
      SYNTAX      SEQUENCE OF ResponseTimeRequestClassEntry
      MAX-ACCESS  not-accessible
      STATUS      current
      DESCRIPTION "This mbean defines the response time goal for this request class.   Response time goals can be used to differentiate request classes. We do not try to meet a response time goal for an individual request. Rather we compute a tolerable waiting time for a request class by subtracting the observed average thread use time. Then we schedule requests so that the average wait for each request class is in proportion to their tolerable waiting time. For example, consider we only have two request classes, A and B, with response time goals 2000ms and 5000ms, respectively, where the time an individual request uses a thread is much smaller. During a period in which both request classes are sufficiently requested, say, zero think time and more clients than threads, we schedule to keep the average response time in the ratio 2:5 so that it is a common fraction or multiple of the stated goal.   Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1030  }
      
   
   responseTimeRequestClassEntry OBJECT-TYPE
      SYNTAX      ResponseTimeRequestClassEntry
      MAX-ACCESS  not-accessible
      STATUS      current
      DESCRIPTION "Generated SNMP Table Entry."
      INDEX { responseTimeRequestClassIndex}
      ::= { responseTimeRequestClassTable 1 }
      
   ResponseTimeRequestClassEntry ::=
      SEQUENCE
      {
         responseTimeRequestClassIndex OCTET STRING,
         responseTimeRequestClassObjectName OCTET STRING,
         responseTimeRequestClassType OCTET STRING,
         responseTimeRequestClassDeploymentOrder Integer32,
         responseTimeRequestClassGoalMs Integer32,
         responseTimeRequestClassName OCTET STRING
      }
      
   
   responseTimeRequestClassIndex OBJECT-TYPE
      SYNTAX      OCTET STRING
      MAX-ACCESS  not-accessible
      STATUS      current
      DESCRIPTION "Index column"
      ::= { responseTimeRequestClassEntry 1  }
   
   
   responseTimeRequestClassObjectName OBJECT-TYPE
      SYNTAX      OCTET STRING
      MAX-ACCESS  read-only
      STATUS      current
      DESCRIPTION "ObjectName column"
      ::= { responseTimeRequestClassEntry 2  }
   
   
   responseTimeRequestClassType OBJECT-TYPE
      SYNTAX      OCTET STRING
      MAX-ACCESS  read-only
      STATUS      current
      DESCRIPTION "Returns the type of the MBean."
      ::= { responseTimeRequestClassEntry 3  }
   
   
   responseTimeRequestClassDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { responseTimeRequestClassEntry 4  }
   
   
   responseTimeRequestClassGoalMs OBJECT-TYPE
      SYNTAX      Integer32
      MAX-ACCESS  read-only
      STATUS      current
      DESCRIPTION "Response time goal"
      ::= { responseTimeRequestClassEntry 5  }
   
   
   responseTimeRequestClassName OBJECT-TYPE
      SYNTAX      OCTET STRING
      MAX-ACCESS  read-only
      STATUS      current
      DESCRIPTION "The user-specified name of this MBean instance.  This name is included as one of the key properties in the MBean's javax.management.ObjectName: Name=user-specified-name"
      ::= { responseTimeRequestClassEntry 6  }
   
   
   safAgentTable OBJECT-TYPE
      SYNTAX      SEQUENCE OF SafAgentEntry
      MAX-ACCESS  not-accessible
      STATUS      current
      DESCRIPTION "This class represents a Store-and-Forward (SAF) agent. A SAF sending agent takes care of storing messages to a persistent storage, forwarding messages to the receiving side, and re-transmitting messages when acknowledgements do not come back in time. A SAF receiving agent takes care of detecting and eliminating duplicate messages sent by the receiving agent, and deliver messages to the final endpoint.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1035  }
      
   
   safAgentEntry OBJECT-TYPE
      SYNTAX      SafAgentEntry
      MAX-ACCESS  not-accessible
      STATUS      current
      DESCRIPTION "Generated SNMP Table Entry."
      INDEX { safAgentIndex}
      ::= { safAgentTable 1 }
      
   SafAgentEntry ::=
      SEQUENCE
      {
         safAgentIndex        OCTET STRING,
         safAgentObjectName   OCTET STRING,
         safAgentType         OCTET STRING,
         safAgentForwardingPausedAtStartup OCTET STRING,
         safAgentDefaultRetryDelayMultiplier OCTET STRING,
         safAgentLoggingEnabled OCTET STRING,
         safAgentBytesThresholdHigh Counter64,
         safAgentWindowInterval Counter64,
         safAgentBytesMaximum Counter64,
         safAgentServiceType  OCTET STRING,
         safAgentMessagesThresholdLow Counter64,
         safAgentMessagesThresholdHigh Counter64,
         safAgentIncomingPausedAtStartup OCTET STRING,
         safAgentReceivingPausedAtStartup OCTET STRING,
         safAgentMessagesMaximum Counter64,
         safAgentName         OCTET STRING,
         safAgentConversationIdleTimeMaximum Counter64,
         safAgentDefaultRetryDelayMaximum Counter64,
         safAgentMaximumMessageSize Integer32,
         safAgentAcknowledgeInterval Counter64,
         safAgentDeploymentOrder Integer32,
         safAgentMessageBufferSize Counter64,
         safAgentWindowSize   Integer32,
         safAgentDefaultTimeToLive Counter64,
         safAgentPagingDirectory OCTET STRING,
         safAgentBytesThresholdLow Counter64,
         safAgentDefaultRetryDelayBase Counter64
      }
      
   
   safAgentIndex OBJECT-TYPE
      SYNTAX      OCTET STRING
      MAX-ACCESS  not-accessible
      STATUS      current
      DESCRIPTION "Index column"
      ::= { safAgentEntry 1  }
   
   
   safAgentObjectName OBJECT-TYPE
      SYNTAX      OCTET STRING
      MAX-ACCESS  read-only
      STATUS      current
      DESCRIPTION "ObjectName column"
      ::= { safAgentEntry 2  }
   
   
   safAgentType OBJECT-TYPE
      SYNTAX      OCTET STRING
      MAX-ACCESS  read-only
      STATUS      current
      DESCRIPTION "Returns the type of the MBean."
      ::= { safAgentEntry 3  }
   
   
   safAgentForwardingPausedAtStartup OBJECT-TYPE
      SYNTAX      OCTET STRING
      MAX-ACCESS  read-only
      STATUS      current
      DESCRIPTION "Specifies whether the agent is paused for forwarding messages at the startup time.  When enabled, the sending agent forwards messages. Otherwise, the sending agent does not forward any messages."
      ::= { safAgentEntry 4  }
   
   
   safAgentDefaultRetryDelayMultiplier OBJECT-TYPE
      SYNTAX      OCTET STRING
      MAX-ACCESS  read-only
      STATUS      current
      DESCRIPTION "The factor used to multiply the previous delay time to calculate the next delay time to be used.    Applies only to agents with sending capability.    Updating DefaultRetryDelayMuliplier causes connections starting after the update to use the new value.    Range of Values: &gt;= 1."
      ::= { safAgentEntry 5  }
   
   
   safAgentLoggingEnabled OBJECT-TYPE
      SYNTAX      OCTET STRING
      MAX-ACCESS  read-only
      STATUS      current
      DESCRIPTION "Specifies whether a message is logged in the server log file when a message fails to be forwarded.    If selected, this applies to messages that fail to be forwarded and delivered to the final destination when there is no error handling in a SAF application or the application's error handling fails.    Applies only to agents with receiving capability.    Updating LoggingEnabled causes connections starting after the update to use the new value."
      ::= { safAgentEntry 6  }
   
   
   safAgentBytesThresholdHigh OBJECT-TYPE
      SYNTAX      Counter64
      MAX-ACCESS  read-only
      STATUS      current
      DESCRIPTION "The upper threshold value that triggers events based on the number of bytes stored in the SAF agent.    The default value of -1  disables the events for this SAF agent.     Applies only to agents with sending capability.    Updating BytesThresholdHigh affects only new requests.    If the number of bytes exceeds this threshold, the triggered events are:   Log Messages: A message is logged on the server indicating a high threshold condition.   Flow Control: The agent becomes armed and instructs producers to begin decreasing their message flow.      Range of Values: &lt;= BytesMaximum; &gt;= BytesThresholdLow"
      ::= { safAgentEntry 7  }
   
   
   safAgentWindowInterval OBJECT-TYPE
      SYNTAX      Counter64
      MAX-ACCESS  read-only
      STATUS      current
      DESCRIPTION "The maximum amount of time, in milliseconds, that a JMS sending agent will wait before forwarding messages in a single batch.  A sending agent will wait to forward the message batch until either: (A) the source destination message count is greater than or equal to the configured Window Size; (B) it has waited a specified Window Interval, whichever comes first."
      ::= { safAgentEntry 8  }
   
   
   safAgentBytesMaximum OBJECT-TYPE
      SYNTAX      Counter64
      MAX-ACCESS  read-only
      STATUS      current
      DESCRIPTION "The maximum bytes quota (total amount of bytes) that can be stored in this SAF agent.    The default value of -1 specifies that there is no WebLogic-imposed limit on the number of bytes that can be stored. However, excessive bytes volume can cause memory saturation, so this value should correspond to the total amount of available system memory relative to the rest of your application load.    Applies only to agents with sending capability.    Updating BytesMaximum affects only new requests.    Range of Values: &gt;= BytesThresholdHigh"
      ::= { safAgentEntry 9  }
   
   
   safAgentServiceType OBJECT-TYPE
      SYNTAX      OCTET STRING
      MAX-ACCESS  read-only
      STATUS      current
      DESCRIPTION "The type of service that this SAF agent provides.  Range of Values: Sending-only, Receiving-only, or Both."
      ::= { safAgentEntry 10  }
   
   
   safAgentMessagesThresholdLow OBJECT-TYPE
      SYNTAX      Counter64
      MAX-ACCESS  read-only
      STATUS      current
      DESCRIPTION "The low threshold that triggers events based on the number of messages stored in the SAF agent.    The default value of -1 disables the events for this SAF agent.     Applies only to agents with sending capability.    Updating MessagesThresholdLow affects only new requests.    If the number of messages falls below this threshold, the triggered events are:   Log Messages: A message is logged on the server indicating that the threshold condition has cleared.   Flow Control: The agent becomes disarmed and instructs producers to begin increasing their message flow.      Range of Values: &lt;= MessagesThresholdHigh."
      ::= { safAgentEntry 11  }
   
   
   safAgentMessagesThresholdHigh OBJECT-TYPE
      SYNTAX      Counter64
      MAX-ACCESS  read-only
      STATUS      current
      DESCRIPTION "The upper threshold that triggers events based on the number of messages stored in the SAF agent.    The default value of -1 disables the events for this SAF agent.     Applies only to agents with sending capability.    Updating MessagesThresholdHigh affects only new requests.    If the number of messages exceeds this threshold, the triggered events are:   Log Messages: A message is logged on the server indicating a high threshold condition.   Flow Control: The agent becomes armed and instructs producers to begin decreasing their message flow.      Range of Values: &lt;= MessagesMaximum; &gt;= MessagesThresholdLow"
      ::= { safAgentEntry 12  }
   
   
   safAgentIncomingPausedAtStartup OBJECT-TYPE
      SYNTAX      OCTET STRING
      MAX-ACCESS  read-only
      STATUS      current
      DESCRIPTION "Specifies whether the agent is paused for incoming messages at startup time.  When enabled, the sending agent accepts new messages. Otherwise, the sending agent does not accept any new messages."
      ::= { safAgentEntry 13  }
   
   
   safAgentReceivingPausedAtStartup OBJECT-TYPE
      SYNTAX      OCTET STRING
      MAX-ACCESS  read-only
      STATUS      current
      DESCRIPTION "Specifies whether the agent is paused for receiving messages at the startup time.  When enabled, the sending agent receives messages. Otherwise, the sending agent does not receive any messages."
      ::= { safAgentEntry 14  }
   
   
   safAgentMessagesMaximum OBJECT-TYPE
      SYNTAX      Counter64
      MAX-ACCESS  read-only
      STATUS      current
      DESCRIPTION "The maximum message quota (total amount of messages) that can be stored in this SAF agent.    The default value of -1 specifies that the server instance has no limit on the number of messages that can be stored. However, excessive message volume can cause memory saturation, so this value should correspond to the total amount of available system memory relative to the rest of your application load.    Applies only to sending agents.    Updating the maximum message quota resets the message count so that only requests arriving after the update are charged against the new quota.    Range of Values: &gt;= MessagesThresholdHigh"
      ::= { safAgentEntry 15  }
   
   
   safAgentName OBJECT-TYPE
      SYNTAX      OCTET STRING
      MAX-ACCESS  read-only
      STATUS      current
      DESCRIPTION "The user-specified name of this MBean instance.  This name is included as one of the key properties in the MBean's javax.management.ObjectName: Name=user-specified-name"
      ::= { safAgentEntry 16  }
   
   
   safAgentConversationIdleTimeMaximum OBJECT-TYPE
      SYNTAX      Counter64
      MAX-ACCESS  read-only
      STATUS      current
      DESCRIPTION "The maximum amount of time allowed before a sending side releases the resources used by a conversation.    If there is no activity for a conversation for the specified amount of time, the sending agent releases all resources for that conversation and notifies the receiving agent to do the same.    A value of 0 specifies that resources for a conversation are not released unless the application explicitly closes the conversation.    Updating ConversationIdleTimeMaximum causes connections starting after the update to use the new value."
      ::= { safAgentEntry 17  }
   
   
   safAgentDefaultRetryDelayMaximum OBJECT-TYPE
      SYNTAX      Counter64
      MAX-ACCESS  read-only
      STATUS      current
      DESCRIPTION "The maximum amount of time, in milliseconds, between two successive delivery retry attempts.    Applies only to agents with sending capability.    Updating DefaultRetryDelayMaximum causes connections starting after the update to use the new value.    Range of Values: &gt; = RetryDelayBase if RetryDelayMultiplier is not 1.0."
      ::= { safAgentEntry 18  }
   
   
   safAgentMaximumMessageSize OBJECT-TYPE
      SYNTAX      Integer32
      MAX-ACCESS  read-only
      STATUS      current
      DESCRIPTION "The maximum number of bytes allowed in individual messages on this SAF agent.    The message size includes the message body, any user-defined properties, and the user-defined JMS header fields: JMSCorrelationID and JMSType.    Producers sending messages that exceed the configured maximum message size for the SAF agent will receive a ResourceAllocationException.    The maximum message size is only enforced for the initial production of a message. Messages that are redirected to an error destination or forwarded to a member of a distributed destination are not checked for size. For instance, if a destination and its corresponding error destination are configured with a maximum message size of 128K bytes and 64K bytes, respectively, a message of 96K bytes could be redirected to the error destination (even though it exceeds the 64K byte maximum), but a producer could not directly send the 96K byte message to the error destination.    Applies only to agents with sending capability.    Updating MaximumMessageSize affects only incoming messages; stored messages are not affected."
      ::= { safAgentEntry 19  }
   
   
   safAgentAcknowledgeInterval OBJECT-TYPE
      SYNTAX      Counter64
      MAX-ACCESS  read-only
      STATUS      current
      DESCRIPTION "The maximum interval between two successive acknowledgements sent by the receiving side.    Applies only to agents with receiving capability.    A value of -1 specifies that there is no time limit between successive acknowledgement.    Updating AcknowlegeInterval causes connections starting after the update to use the new value."
      ::= { safAgentEntry 20  }
   
   
   safAgentDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { safAgentEntry 21  }
   
   
   safAgentMessageBufferSize OBJECT-TYPE
      SYNTAX      Counter64
      MAX-ACCESS  read-only
      STATUS      current
      DESCRIPTION "The amount of memory used to store message bodies in memory before they are paged out to disk.   A value of -1 (the default) specifies that the server will automatically determine a size based on the maximum heap size of the JVM. This default will be set to either one-third the maximum heap size, or 512 megabytes, whichever is larger.    The larger the buffer, the more memory JMS will consume when many messages are waiting on queues or topics. Once the buffer is surpassed, JMS may write message bodies to the directory specified by PagingDirectory in an effort to reduce memory usage below this buffer.    Surpassing the buffer size does not stop the JMS server from accepting new messages. It is still possible to run out of memory if messages are arriving faster than they can be written to disk. Users with high messaging loads who wish to support the highest possible availability should consider setting a quota or setting a threshold and enabling flow control.    Applies only to agents with sending capability.    Paging is always supported.     Updating the memory size resets the message count so that only requests arriving after the update are charged against the new memory size."
      ::= { safAgentEntry 22  }
   
   
   safAgentWindowSize OBJECT-TYPE
      SYNTAX      Integer32
      MAX-ACCESS  read-only
      STATUS      current
      DESCRIPTION "For JMS messages, the number of messages in a batch. A sending agent waits to forward a message batch until the source destination message count is greater than or equal to this value. For WSRM, the maximum number of unacknowledged messages allowed between a source destination and a target destination during a conversation."
      ::= { safAgentEntry 23  }
   
   
   safAgentDefaultTimeToLive OBJECT-TYPE
      SYNTAX      Counter64
      MAX-ACCESS  read-only
      STATUS      current
      DESCRIPTION "The default amount of time, in milliseconds, that the agent guarantees to reliably send messages.    A value of 0 means the agent guarantees to reliably send messages for the duration of the conversation.    Updating DefaultTimeToLive causes conversations starting after the update to use the new value."
      ::= { safAgentEntry 24  }
   
   
   safAgentPagingDirectory OBJECT-TYPE
      SYNTAX      OCTET STRING
      MAX-ACCESS  read-only
      STATUS      current
      DESCRIPTION "Specifies where message bodies are written when the size of the message bodies in the JMS server exceeds the message buffer size. If unspecified, messages are written to the tmp directory in the host WebLogic Server instance's directory. For example, domainName/servers/servername/tmp.     For best performance, this directory should not be the same as the directory used by the SAF agent's persistent store.    Applies only to agents with sending capability."
      ::= { safAgentEntry 25  }
   
   
   safAgentBytesThresholdLow OBJECT-TYPE
      SYNTAX      Counter64
      MAX-ACCESS  read-only
      STATUS      current
      DESCRIPTION "The lower threshold that triggers events based on the number of bytes stored in the SAF agent.    The default value of -1  disables the events for this SAF agent.     Applies only to agents with sending capability.    Updating BytesThresholdLow affects only new requests.    If the number of bytes falls below this threshold, the triggered events are:   Log Messages: A message is logged on the server indicating that the threshold condition has cleared.   Flow Control: The agent becomes disarmed and instructs producers to beging increasing their message flow.      Range of Values: &lt;= BytesThresholdHigh"
      ::= { safAgentEntry 26  }
   
   
   safAgentDefaultRetryDelayBase OBJECT-TYPE
      SYNTAX      Counter64
      MAX-ACCESS  read-only
      STATUS      current
      DESCRIPTION "The amount of time, in milliseconds, between the original delivery attempt and the first retry.    If RetryDelayMultiplier is set to 1, this defines the interval between any two successive retry attempts.    Applies only to agents with sending capability.    Updating DefaultRetryDelayBase causes connections starting after the update to use the new value.    Range of Values: &lt;= RetryDelayMaximum if RetryDelayMultiplier is not 1.0."
      ::= { safAgentEntry 27  }
   
   
   wlssnmpAgentDeploymentTable OBJECT-TYPE
      SYNTAX      SEQUENCE OF WlssnmpAgentDeploymentEntry
      MAX-ACCESS  not-accessible
      STATUS      current
      DESCRIPTION "This MBean is an SNMP agent that can be targeted to instances of WebLogic Server.  With SNMP, you configure agents to gather and send data about managed resources in response to a request from managers. You can also configure agents to issue unsolicited reports to managers when they detect predefined thresholds or conditions on a managed resource. In a WebLogic Server domain, you can choose a centralized or de-centralized model for SNMP monitoring and communication: In a centralized model, you create an instance of this MBean and target it only to the Administration Server. This agent communicates with all Managed Servers in the domain. SNMP managers communicate only with the SNMP agent on the Administration Server. This model is convenient but introduces performance overhead in WebLogic Server. In addition, if the Administration Server is unavailable, you cannot monitor the domain through SNMP. In a de-centralized model, you create an instance of this MBean and target it to each Managed Server that you want to monitor. (Alternatively, you can create multiple instances of this MBean and target each instance to an individual Managed Server.) Your SNMP manager must communicate with the agents on individual Managed Servers. To support domains that were created with WebLogic Server release 9.2 and earlier, a domain also hosts a singleton SNMP agent whose scope is the entire domain (see {@link SNMPAgentMBean}). SNMPAgentMBean offers the same features as an instance of this MBean (SNMPAgentDeploymentMBean) that you have targeted as described in the centralized model above. However, the underlying implementation of SNMPAgentMBean is different and it will eventually be deprecated. SNMPAgentMBean is overridden if you target an instance of this MBean to the Administration Server."
      ::= { wls 1040  }
      
   
   wlssnmpAgentDeploymentEntry OBJECT-TYPE
      SYNTAX      WlssnmpAgentDeploymentEntry
      MAX-ACCESS  not-accessible
      STATUS      current
      DESCRIPTION "Generated SNMP Table Entry."
      INDEX { wlssnmpAgentDeploymentIndex}
      ::= { wlssnmpAgentDeploymentTable 1 }
      
   WlssnmpAgentDeploymentEntry ::=
      SEQUENCE
      {
         wlssnmpAgentDeploymentIndex OCTET STRING,
         wlssnmpAgentDeploymentObjectName OCTET STRING,
         wlssnmpAgentDeploymentType OCTET STRING,
         wlssnmpAgentDeploymentCommunityPrefix OCTET STRING,
         wlssnmpAgentDeploymentAuthenticationProtocol OCTET STRING,
         wlssnmpAgentDeploymentSNMPPort Integer32,
         wlssnmpAgentDeploymentSNMPEngineId OCTET STRING,
         wlssnmpAgentDeploymentSNMPAccessForUserMBeansEnabled OCTET STRING,
         wlssnmpAgentDeploymentLocalizedKeyCacheInvalidationInterval Counter64,
         wlssnmpAgentDeploymentEnabled OCTET STRING,
         wlssnmpAgentDeploymentName OCTET STRING,
         wlssnmpAgentDeploymentInformEnabled OCTET STRING,
         wlssnmpAgentDeploymentSendAutomaticTrapsEnabled OCTET STRING,
         wlssnmpAgentDeploymentInformRetryInterval Integer32,
         wlssnmpAgentDeploymentDeploymentOrder Integer32,
         wlssnmpAgentDeploymentPrivacyProtocol OCTET STRING,
         wlssnmpAgentDeploymentMasterAgentXPort Integer32,
         wlssnmpAgentDeploymentSNMPTrapVersion Integer32,
         wlssnmpAgentDeploymentMaxInformRetryCount Integer32,
         wlssnmpAgentDeploymentCommunityBasedAccessEnabled OCTET STRING
      }
      
   
   wlssnmpAgentDeploymentIndex OBJECT-TYPE
      SYNTAX      OCTET STRING
      MAX-ACCESS  not-accessible
      STATUS      current
      DESCRIPTION "Index column"
      ::= { wlssnmpAgentDeploymentEntry 1  }
   
   
   wlssnmpAgentDeploymentObjectName OBJECT-TYPE
      SYNTAX      OCTET STRING
      MAX-ACCESS  read-only
      STATUS      current
      DESCRIPTION "ObjectName column"
      ::= { wlssnmpAgentDeploymentEntry 2  }
   
   
   wlssnmpAgentDeploymentType OBJECT-TYPE
      SYNTAX      OCTET STRING
      MAX-ACCESS  read-only
      STATUS      current
      DESCRIPTION "Returns the type of the MBean."
      ::= { wlssnmpAgentDeploymentEntry 3  }
   
   
   wlssnmpAgentDeploymentCommunityPrefix OBJECT-TYPE
      SYNTAX      OCTET STRING
      MAX-ACCESS  read-only
      STATUS      current
      DESCRIPTION "The password (community name) that you want this SNMP agent to use to secure SNMPv1 or v2 communication with SNMP managers. Requires you to enable community based access for this agent.  SNMPv3 does not use community names. Instead, it encrypts user names and passwords in its PDUs.   When you use SNMPv1 or v2, there are two community names that are needed when the WebLogic SNMP agent and SNMP managers interact:    The name that you specify in this community prefix. All SNMP managers must send this name when connecting to this SNMP agent.    The community name that the SNMP manager defines. The SNMP agent must send this name when connecting to the manager. (You supply this community name when you configure a trap destination.)    In addition to using the community prefix as a password, an SNMP agent on an Administration Server uses the prefix to qualify requests from SNMP managers. Because the Administration Server can access data for all WebLogic Server instances in a domain, a request that specifies only an attribute name is potentially ambiguous. For example, the attribute serverUptime exists for each WebLogic Server instance in a domain. To clarify requests that you send to SNMP agents on Administration Servers, use the community prefix as follows:    To request the value of an attribute on a specific Managed Server, when you send a request from an SNMP manager, append the name of the server instance to the community prefix: community_prefix@server_name.    To request the value of an attribute for all server instances in a domain, send a community name with the following form: community_prefix    To secure access to the values of the WebLogic attributes when using the SNMPv1 or v2 protocols, it is recommended that you set community prefix to a value other than public.  You cannot specify a null (empty) value for the community prefix. If you delete the prefix value, WebLogic Server resets the value to public. If you do not want this agent to receive SNMPv1 or v2 requests, instead of trying to set the community prefix to a null value, disable community based access. With community based access disabled, WebLogic Server ignores the community prefix value."
      ::= { wlssnmpAgentDeploymentEntry 4  }
   
   
   wlssnmpAgentDeploymentAuthenticationProtocol OBJECT-TYPE
      SYNTAX      OCTET STRING
      MAX-ACCESS  read-only
      STATUS      current
      DESCRIPTION "The protocol that this SNMP agent uses to ensure that only authorized users can request or receive information about your WebLogic Server domain. Applicable only with SNMPv3. The protocol also ensures message integrity and prevents masquerading and reordered, delayed, or replayed messages. To use this protocol when receiving requests from SNMP managers, you must configure credential mapping in the WebLogic Server security realm. To use this protocol when sending responses or notifications, you must configure the security level of your trap destinations. If you do not choose an authentication protocol, then the SNMP agent does not authenticate incoming SNMPv3 requests; anyone can use SNMPv3 to retrieve information about your WebLogic Server domain."
      ::= { wlssnmpAgentDeploymentEntry 5  }
   
   
   wlssnmpAgentDeploymentSNMPPort OBJECT-TYPE
      SYNTAX      Integer32
      MAX-ACCESS  read-only
      STATUS      current
      DESCRIPTION "The port on which you want this SNMP agent to listen for incoming requests from SNMP managers that use the UDP protocol.  SNMP managers can use this port to ping the SNMP agent and request the status of specific attributes.  If you target this SNMP agent to multiple server instances, and if two or more servers are running on the same computer, WebLogic Server will automatically increment this UDP port value by 1 for each agent. WebLogic Server never assigns port 162 because it is the default port that an agent uses to send notifications. In addition, if any port is already in use, WebLogic Server skips the port and assigns the next available port. For example, if you use the default value of this attribute and then target this agent to ManagedServer1 and ManagedServer2, and if both servers are running on the same computer, then the agent on ManagedServer1 will listen on UDP port 161 and the agent on ManagedServer2 will listen on UDP port 163. The incremented port number is not persisted in the domain's configuration; when WebLogic Server increments port numbers, it does so in the order in which servers are started on the same computer. If WebLogic Server re-assigns the UDP port for an SNMP agent, look in the agent's SNMPAgentRuntimeMBean to see the agent's runtime UDP port. SNMP agents can also communicate through the host server's TCP listen port (7001 by default) or through a TCP port that is configured by a custom network channel."
      ::= { wlssnmpAgentDeploymentEntry 6  }
   
   
   wlssnmpAgentDeploymentSNMPEngineId OBJECT-TYPE
      SYNTAX      OCTET STRING
      MAX-ACCESS  read-only
      STATUS      current
      DESCRIPTION "An identifier for this SNMP agent that is unique amongst all other SNMP agents in the current WebLogic Server domain. If you use SNMPv3 to send messages to this SNMP agent, you must specify the SNMP engine ID when you configure the SNMP manager. For an SNMP agent on an Administration Server, the default value is the name of the WebLogic Server domain. For an agent on a Managed Server, the default is the name of the server."
      ::= { wlssnmpAgentDeploymentEntry 7  }
   
   
   wlssnmpAgentDeploymentSNMPAccessForUserMBeansEnabled OBJECT-TYPE
      SYNTAX      OCTET STRING
      MAX-ACCESS  read-only
      STATUS      current
      DESCRIPTION "Configures this SNMP agent to provide read-only access to MBean types that you have created and registered (custom MBeans). If you enable this access, when you register a custom MBean in a WebLogic Server MBeanServer, this SNMP agent dynamically updates a runtime MIB module that WebLogic Server maintains for custom MBeans.  For each custom MBean type, WebLogic Server adds a table to the MIB module. For each instance of the custom MBean, it adds a table row. While WebLogic Server does not persist the MIB as a file or other data structure, the OIDs in the MIB remain constant across server sessions. The MIB module for custom MBeans is managed by a subAgent. Its master agent is this WebLogic Server SNMP agent and it communicates with the master agent through the AgentX port."
      ::= { wlssnmpAgentDeploymentEntry 8  }
   
   
   wlssnmpAgentDeploymentLocalizedKeyCacheInvalidationInterval OBJECT-TYPE
      SYNTAX      Counter64
      MAX-ACCESS  read-only
      STATUS      current
      DESCRIPTION "The number of milliseconds after which WebLogic Server invalidates its cache of SNMP security keys. Setting a high value creates a risk that users whose credentials have been removed can still access SNMP data. An SNMP security key is an encrypted version of an SNMP agent's engine ID and an authentication password or privacy password. WebLogic Server generates one security key for each entry that you create in the SNMP credential map. When a WebLogic Server SNMP agent receives an SNMPv3 request, it compares the key that is in the request with its WebLogic Server keys. If it finds a match, it processes the request. The SNMP agent also encodes these keys in its responses and notifications. (You configure which keys are encoded when you create a trap destination.) Instead of regenerating the keys for each SNMPv3 communication, WebLogic Server caches the keys. To make sure that the cache contains the latest set of SNMP credentials, WebLogic Server periodically invalidates the cache. After the cache is invalidated, the next time an SNMP agent requests credentials, WebLogic Server regenerates the cache. Note that making a change to the credential map does not automatically update the cache. Instead, the cache is updated only after it has been invalidated. For example, if you update a privacy password in an existing entry in the SNMP credential map, the SNMP agent is not aware of the new password until the key cache is invalidated and regenerated. An SNMP user with the old security password can still access WebLogic Server data until the cache is invalidated. You can invalidate a key immediately instead of waiting for this invalidation interval to expire."
      ::= { wlssnmpAgentDeploymentEntry 9  }
   
   
   wlssnmpAgentDeploymentEnabled OBJECT-TYPE
      SYNTAX      OCTET STRING
      MAX-ACCESS  read-only
      STATUS      current
      DESCRIPTION "Specifies whether this SNMP agent is enabled."
      ::= { wlssnmpAgentDeploymentEntry 10  }
   
   
   wlssnmpAgentDeploymentName OBJECT-TYPE
      SYNTAX      OCTET STRING
      MAX-ACCESS  read-only
      STATUS      current
      DESCRIPTION "The user-specified name of this MBean instance.  This name is included as one of the key properties in the MBean's javax.management.ObjectName: Name=user-specified-name"
      ::= { wlssnmpAgentDeploymentEntry 11  }
   
   
   wlssnmpAgentDeploymentInformEnabled OBJECT-TYPE
      SYNTAX      OCTET STRING
      MAX-ACCESS  read-only
      STATUS      current
      DESCRIPTION "Configures this SNMP agent to send notifications as an INFORM instead of a TRAP. Requires you to specify the agent's SNMPTrapVersion as SNMPv2 or SNMPv3. When an agent sends an INFORM notification, it waits for a confirmation response from the SNMP manager. If it does not receive a response, it resends the INFORM notification."
      ::= { wlssnmpAgentDeploymentEntry 12  }
   
   
   wlssnmpAgentDeploymentSendAutomaticTrapsEnabled OBJECT-TYPE
      SYNTAX      OCTET STRING
      MAX-ACCESS  read-only
      STATUS      current
      DESCRIPTION "Specifies whether this SNMP agent sends automatically generated notifications to SNMP managers.  The SNMP agent generates automatic notifications when any of the following events occur:   The WebLogic Server instance that is hosting the SNMP agent starts. This type of notification (coldStart) has no variable bindings.  A server instance starts or stops. An SNMP agent on a Managed Server generates these notifications only when its host Managed Server starts or stops. An SNMP agent on an Administration Server generates these notifications when any server in the domain starts or stops. These notification types (serverStart and serverShutdown) contain variable bindings to identify the server that started or stopped and the time at which the notification was generated."
      ::= { wlssnmpAgentDeploymentEntry 13  }
   
   
   wlssnmpAgentDeploymentInformRetryInterval OBJECT-TYPE
      SYNTAX      Integer32
      MAX-ACCESS  read-only
      STATUS      current
      DESCRIPTION "The number of milliseconds that this SNMP agent will wait for a response to an INFORM notification. If the agent does not receive a response within the specified interval, it will resend the notification."
      ::= { wlssnmpAgentDeploymentEntry 14  }
   
   
   wlssnmpAgentDeploymentDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { wlssnmpAgentDeploymentEntry 15  }
   
   
   wlssnmpAgentDeploymentPrivacyProtocol OBJECT-TYPE
      SYNTAX      OCTET STRING
      MAX-ACCESS  read-only
      STATUS      current
      DESCRIPTION "The protocol that this SNMP agent uses to encrypt and unencrypt messages. Applicable only with SNMPv3. Requires you to also use an authentication protocol. To use this protocol when sending responses or notifications, you must also configure the security level of your trap destinations. If you do not choose a privacy protocol, then communication between this agent and managers can be viewed (but not altered) by unauthorized users."
      ::= { wlssnmpAgentDeploymentEntry 16  }
   
   
   wlssnmpAgentDeploymentMasterAgentXPort OBJECT-TYPE
      SYNTAX      Integer32
      MAX-ACCESS  read-only
      STATUS      current
      DESCRIPTION "The port that this SNMP agent uses to communicate with its subagents. The agent uses subagents to provide access to custom MBeans (MBeans that you create and register) and to other BEA software components. WebLogic Server SNMP agents do not enable users to register their own subagents."
      ::= { wlssnmpAgentDeploymentEntry 17  }
   
   
   wlssnmpAgentDeploymentSNMPTrapVersion OBJECT-TYPE
      SYNTAX      Integer32
      MAX-ACCESS  read-only
      STATUS      current
      DESCRIPTION "The SNMP notification version that this SNMP agent generates."
      ::= { wlssnmpAgentDeploymentEntry 18  }
   
   
   wlssnmpAgentDeploymentMaxInformRetryCount OBJECT-TYPE
      SYNTAX      Integer32
      MAX-ACCESS  read-only
      STATUS      current
      DESCRIPTION "The maximum number of times that this SNMP agent will resend INFORM notifications for which it has not received a response."
      ::= { wlssnmpAgentDeploymentEntry 19  }
   
   
   wlssnmpAgentDeploymentCommunityBasedAccessEnabled OBJECT-TYPE
      SYNTAX      OCTET STRING
      MAX-ACCESS  read-only
      STATUS      current
      DESCRIPTION "Specifies whether this SNMP agent supports SNMPv1 and v2. SNMPv1 and v2 use community strings for authentication. If you disable community strings for this SNMP agent, the agent will process only SNMPv3 requests. If an SNMP manager sends a v1 or v2 message, the agent discards the message and returns an error code to the manager."
      ::= { wlssnmpAgentDeploymentEntry 20  }
   
   
   wlssnmpAttributeChangeTable OBJECT-TYPE
      SYNTAX      SEQUENCE OF WlssnmpAttributeChangeEntry
      MAX-ACCESS  not-accessible
      STATUS      current
      DESCRIPTION "This class describes the settings to receive MBean-attribute change notification.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1045  }
      
   
   wlssnmpAttributeChangeEntry OBJECT-TYPE
      SYNTAX      WlssnmpAttributeChangeEntry
      MAX-ACCESS  not-accessible
      STATUS      current
      DESCRIPTION "Generated SNMP Table Entry."
      INDEX { wlssnmpAttributeChangeIndex}
      ::= { wlssnmpAttributeChangeTable 1 }
      
   WlssnmpAttributeChangeEntry ::=
      SEQUENCE
      {
         wlssnmpAttributeChangeIndex OCTET STRING,
         wlssnmpAttributeChangeObjectName OCTET STRING,
         wlssnmpAttributeChangeType OCTET STRING,
         wlssnmpAttributeChangeAttributeName OCTET STRING,
         wlssnmpAttributeChangeAttributeMBeanName OCTET STRING,
         wlssnmpAttributeChangeAttributeMBeanType OCTET STRING,
         wlssnmpAttributeChangeName OCTET STRING
      }
      
   
   wlssnmpAttributeChangeIndex OBJECT-TYPE
      SYNTAX      OCTET STRING
      MAX-ACCESS  not-accessible
      STATUS      current
      DESCRIPTION "Index column"
      ::= { wlssnmpAttributeChangeEntry 1  }
   
   
   wlssnmpAttributeChangeObjectName OBJECT-TYPE
      SYNTAX      OCTET STRING
      MAX-ACCESS  read-only
      STATUS      current
      DESCRIPTION "ObjectName column"
      ::= { wlssnmpAttributeChangeEntry 2  }
   
   
   wlssnmpAttributeChangeType OBJECT-TYPE
      SYNTAX      OCTET STRING
      MAX-ACCESS  read-only
      STATUS      current
      DESCRIPTION "Returns the type of the MBean."
      ::= { wlssnmpAttributeChangeEntry 3  }
   
   
   wlssnmpAttributeChangeAttributeName OBJECT-TYPE
      SYNTAX      OCTET STRING
      MAX-ACCESS  read-only
      STATUS      current
      DESCRIPTION "The name of the attribute that you want to monitor. This attribute must be in the WebLogic Server MIB."
      ::= { wlssnmpAttributeChangeEntry 4  }
   
   
   wlssnmpAttributeChangeAttributeMBeanName OBJECT-TYPE
      SYNTAX      OCTET STRING
      MAX-ACCESS  read-only
      STATUS      current
      DESCRIPTION "The name of the MBean instance that you want to monitor. If you leave the name undefined, WebLogic Server monitors all instances of the MBean type that you specify in Monitored MBean Type.  Do not enter the full JMX object name of the MBean instance. Instead, enter only the value that you provided when you created the instance. To create unique MBean object names, WebLogic Server encodes several name-value pairs into each object name. One of these pairs is Name=name, and this is the value that you enter for MBean Name. For example: 'MedRec:Name=MedRecServer, Type=ServerRuntime'  In the previous example, specify MedRecServer as the name of the MBean instance."
      ::= { wlssnmpAttributeChangeEntry 5  }
   
   
   wlssnmpAttributeChangeAttributeMBeanType OBJECT-TYPE
      SYNTAX      OCTET STRING
      MAX-ACCESS  read-only
      STATUS      current
      DESCRIPTION "The MBean type that defines the attribute you want to monitor. Do not include the MBean suffix. For example, specify Server to monitor a ServerMBean.  WebLogic Server does not support using Attribute Change notifications to monitor run-time attributes. Runtime MBeans always include the word Runtime in their names. For example, the ServerRuntime MBean provides access to runtime attributes while the Server MBean provides access to configuration attributes. To monitor changes in an MBean that includes Runtime in its name, use a String Monitor, Gauge Monitor, or Counter Monitor."
      ::= { wlssnmpAttributeChangeEntry 6  }
   
   
   wlssnmpAttributeChangeName OBJECT-TYPE
      SYNTAX      OCTET STRING
      MAX-ACCESS  read-only
      STATUS      current
      DESCRIPTION "The user-specified name of this MBean instance.  This name is included as one of the key properties in the MBean's javax.management.ObjectName: Name=user-specified-name"
      ::= { wlssnmpAttributeChangeEntry 7  }
   
   
   wlssnmpCounterMonitorTable OBJECT-TYPE
      SYNTAX      SEQUENCE OF WlssnmpCounterMonitorEntry
      MAX-ACCESS  not-accessible
      STATUS      current
      DESCRIPTION "This class describes the criteria for a Counter-based Monitor. A notification will be generated when this criteria is satisfied.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1050  }
      
   
   wlssnmpCounterMonitorEntry OBJECT-TYPE
      SYNTAX      WlssnmpCounterMonitorEntry
      MAX-ACCESS  not-accessible
      STATUS      current
      DESCRIPTION "Generated SNMP Table Entry."
      INDEX { wlssnmpCounterMonitorIndex}
      ::= { wlssnmpCounterMonitorTable 1 }
      
   WlssnmpCounterMonitorEntry ::=
      SEQUENCE
      {
         wlssnmpCounterMonitorIndex OCTET STRING,
         wlssnmpCounterMonitorObjectName OCTET STRING,
         wlssnmpCounterMonitorType OCTET STRING,
         wlssnmpCounterMonitorMonitoredAttributeName OCTET STRING,
         wlssnmpCounterMonitorMonitoredMBeanType OCTET STRING,
         wlssnmpCounterMonitorOffset Integer32,
         wlssnmpCounterMonitorModulus Integer32,
         wlssnmpCounterMonitorName OCTET STRING,
         wlssnmpCounterMonitorPollingInterval Integer32,
         wlssnmpCounterMonitorThreshold Integer32,
         wlssnmpCounterMonitorMonitoredMBeanName OCTET STRING
      }
      
   
   wlssnmpCounterMonitorIndex OBJECT-TYPE
      SYNTAX      OCTET STRING
      MAX-ACCESS  not-accessible
      STATUS      current
      DESCRIPTION "Index column"
      ::= { wlssnmpCounterMonitorEntry 1  }
   
   
   wlssnmpCounterMonitorObjectName OBJECT-TYPE
      SYNTAX      OCTET STRING
      MAX-ACCESS  read-only
      STATUS      current
      DESCRIPTION "ObjectName column"
      ::= { wlssnmpCounterMonitorEntry 2  }
   
   
   wlssnmpCounterMonitorType OBJECT-TYPE
      SYNTAX      OCTET STRING
      MAX-ACCESS  read-only
      STATUS      current
      DESCRIPTION "Returns the type of the MBean."
      ::= { wlssnmpCounterMonitorEntry 3  }
   
   
   wlssnmpCounterMonitorMonitoredAttributeName OBJECT-TYPE
      SYNTAX      OCTET STRING
      MAX-ACCESS  read-only
      STATUS      current
      DESCRIPTION "The name of an MBean attribute to monitor. This attribute must be in the WebLogic Server MIB."
      ::= { wlssnmpCounterMonitorEntry 4  }
   
   
   wlssnmpCounterMonitorMonitoredMBeanType OBJECT-TYPE
      SYNTAX      OCTET STRING
      MAX-ACCESS  read-only
      STATUS      current
      DESCRIPTION "The MBean type that defines the attribute you want to monitor. Do not include the MBean suffix. For example, ServerRuntime."
      ::= { wlssnmpCounterMonitorEntry 5  }
   
   
   wlssnmpCounterMonitorOffset OBJECT-TYPE
      SYNTAX      Integer32
      MAX-ACCESS  read-only
      STATUS      current
      DESCRIPTION "An integer value to be added to the threshold value each time the observed value equals or exceeds the threshold."
      ::= { wlssnmpCounterMonitorEntry 6  }
   
   
   wlssnmpCounterMonitorModulus OBJECT-TYPE
      SYNTAX      Integer32
      MAX-ACCESS  read-only
      STATUS      current
      DESCRIPTION "An integer value to be subtracted from the threshold value when the threshold value is crossed.  If Modulus is 0, a notification is generated each time the agent polls the monitored attribute and its value still exceeds or equals the threshold value.  If Modulus is larger than 0, the value of the modulus is subtracted from the threshold each time the threshold is crossed."
      ::= { wlssnmpCounterMonitorEntry 7  }
   
   
   wlssnmpCounterMonitorName OBJECT-TYPE
      SYNTAX      OCTET STRING
      MAX-ACCESS  read-only
      STATUS      current
      DESCRIPTION "The user-specified name of this MBean instance.  This name is included as one of the key properties in the MBean's javax.management.ObjectName: Name=user-specified-name"
      ::= { wlssnmpCounterMonitorEntry 8  }
   
   
   wlssnmpCounterMonitorPollingInterval OBJECT-TYPE
      SYNTAX      Integer32
      MAX-ACCESS  read-only
      STATUS      current
      DESCRIPTION "The frequency (in seconds) that WebLogic Server checks the attribute value."
      ::= { wlssnmpCounterMonitorEntry 9  }
   
   
   wlssnmpCounterMonitorThreshold OBJECT-TYPE
      SYNTAX      Integer32
      MAX-ACCESS  read-only
      STATUS      current
      DESCRIPTION "Specifies a value that triggers the Counter Monitor to generate a notification.  The monitor generates a notification the first time the observed value transitions from below the threshold to at or above the threshold. While the observed value remains at or above the threshold, the Counter Monitor does not generate additional notifications. If the observed value falls below the threshold and then later equals or exceeds the threshold, the Counter Monitor does not generate an additional notification.  You can specify an offset value to cause this threshold value to increase each time the observed value equals or exceeds the threshold. The first time the observed value equals or exceeds the new threshold value, this monitor generates a notification and adds the offset value to the new threshold value.  For example, if you set Threshold to 1000 and Offset to 2000, when the observed attribute equals or exceeds 1000, the Counter Monitor sends a notification and increases the threshold to 3000. When the observed attribute equals or exceeds 3000, the Counter Monitor sends a notification and increases the threshold again to 5000."
      ::= { wlssnmpCounterMonitorEntry 10  }
   
   
   wlssnmpCounterMonitorMonitoredMBeanName OBJECT-TYPE
      SYNTAX      OCTET STRING
      MAX-ACCESS  read-only
      STATUS      current
      DESCRIPTION "The name of the MBean instance that you want to monitor. If you leave the name undefined, WebLogic Server monitors all instances of the MBean type that you specify in Monitored MBean Type.  If you target SNMP agents to individual Managed Servers, make sure that the MBean instance you specify is active on the Managed Servers you have targeted. For example, if you specify MServer1 as the name of a ServerRuntimeMBean instance, this monitor will only function if you target an SNMP agent either to the Administration Server or to a Managed Server named MServer1.  Do not enter the full JMX object name of the MBean instance. Instead, enter only the value of the object name's Name=name name-value pair. To create unique MBean object names, WebLogic Server encodes several name-value pairs into each object name. One of these pairs is Name=name. For example: 'MedRec:Name=MedRecServer, Type=ServerRuntime'  In the previous example, specify MedRecServer as the name of the MBean instance."
      ::= { wlssnmpCounterMonitorEntry 11  }
   
   
   wlssnmpGaugeMonitorTable OBJECT-TYPE
      SYNTAX      SEQUENCE OF WlssnmpGaugeMonitorEntry
      MAX-ACCESS  not-accessible
      STATUS      current
      DESCRIPTION "This class describes the criteria for a Gauge-based Monitor. A notification will be generated when this criteria is satisfied.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1055  }
      
   
   wlssnmpGaugeMonitorEntry OBJECT-TYPE
      SYNTAX      WlssnmpGaugeMonitorEntry
      MAX-ACCESS  not-accessible
      STATUS      current
      DESCRIPTION "Generated SNMP Table Entry."
      INDEX { wlssnmpGaugeMonitorIndex}
      ::= { wlssnmpGaugeMonitorTable 1 }
      
   WlssnmpGaugeMonitorEntry ::=
      SEQUENCE
      {
         wlssnmpGaugeMonitorIndex OCTET STRING,
         wlssnmpGaugeMonitorObjectName OCTET STRING,
         wlssnmpGaugeMonitorType OCTET STRING,
         wlssnmpGaugeMonitorThresholdLow Integer32,
         wlssnmpGaugeMonitorMonitoredAttributeName OCTET STRING,
         wlssnmpGaugeMonitorThresholdHigh Integer32,
         wlssnmpGaugeMonitorMonitoredMBeanType OCTET STRING,
         wlssnmpGaugeMonitorName OCTET STRING,
         wlssnmpGaugeMonitorPollingInterval Integer32,
         wlssnmpGaugeMonitorMonitoredMBeanName OCTET STRING
      }
      
   
   wlssnmpGaugeMonitorIndex OBJECT-TYPE
      SYNTAX      OCTET STRING
      MAX-ACCESS  not-accessible
      STATUS      current
      DESCRIPTION "Index column"
      ::= { wlssnmpGaugeMonitorEntry 1  }
   
   
   wlssnmpGaugeMonitorObjectName OBJECT-TYPE
      SYNTAX      OCTET STRING
      MAX-ACCESS  read-only
      STATUS      current
      DESCRIPTION "ObjectName column"
      ::= { wlssnmpGaugeMonitorEntry 2  }
   
   
   wlssnmpGaugeMonitorType OBJECT-TYPE
      SYNTAX      OCTET STRING
      MAX-ACCESS  read-only
      STATUS      current
      DESCRIPTION "Returns the type of the MBean."
      ::= { wlssnmpGaugeMonitorEntry 3  }
   
   
   wlssnmpGaugeMonitorThresholdLow OBJECT-TYPE
      SYNTAX      Integer32
      MAX-ACCESS  read-only
      STATUS      current
      DESCRIPTION "The low threshold at which a notification should be generated. A notification is generated the first time the monitored value is less than or equal to this value.  Subsequent crossings of the low threshold value do not cause additional notifications unless the attribute value becomes equal to or greater than the high threshold value."
      ::= { wlssnmpGaugeMonitorEntry 4  }
   
   
   wlssnmpGaugeMonitorMonitoredAttributeName OBJECT-TYPE
      SYNTAX      OCTET STRING
      MAX-ACCESS  read-only
      STATUS      current
      DESCRIPTION "The name of an MBean attribute to monitor. This attribute must be in the WebLogic Server MIB."
      ::= { wlssnmpGaugeMonitorEntry 5  }
   
   
   wlssnmpGaugeMonitorThresholdHigh OBJECT-TYPE
      SYNTAX      Integer32
      MAX-ACCESS  read-only
      STATUS      current
      DESCRIPTION "The high threshold at which a notification should be generated. A notification is generated the first time the monitored value is equal to or greater than this value. Subsequent crossings of the high threshold value do not cause additional notifications unless the attribute value becomes equal to or less than the low threshold value."
      ::= { wlssnmpGaugeMonitorEntry 6  }
   
   
   wlssnmpGaugeMonitorMonitoredMBeanType OBJECT-TYPE
      SYNTAX      OCTET STRING
      MAX-ACCESS  read-only
      STATUS      current
      DESCRIPTION "The MBean type that defines the attribute you want to monitor. Do not include the MBean suffix. For example, ServerRuntime."
      ::= { wlssnmpGaugeMonitorEntry 7  }
   
   
   wlssnmpGaugeMonitorName OBJECT-TYPE
      SYNTAX      OCTET STRING
      MAX-ACCESS  read-only
      STATUS      current
      DESCRIPTION "The user-specified name of this MBean instance.  This name is included as one of the key properties in the MBean's javax.management.ObjectName: Name=user-specified-name"
      ::= { wlssnmpGaugeMonitorEntry 8  }
   
   
   wlssnmpGaugeMonitorPollingInterval OBJECT-TYPE
      SYNTAX      Integer32
      MAX-ACCESS  read-only
      STATUS      current
      DESCRIPTION "The frequency (in seconds) that WebLogic Server checks the attribute value."
      ::= { wlssnmpGaugeMonitorEntry 9  }
   
   
   wlssnmpGaugeMonitorMonitoredMBeanName OBJECT-TYPE
      SYNTAX      OCTET STRING
      MAX-ACCESS  read-only
      STATUS      current
      DESCRIPTION "The name of the MBean instance that you want to monitor. If you leave the name undefined, WebLogic Server monitors all instances of the MBean type that you specify in Monitored MBean Type.  If you target SNMP agents to individual Managed Servers, make sure that the MBean instance you specify is active on the Managed Servers you have targeted. For example, if you specify MServer1 as the name of a ServerRuntimeMBean instance, this monitor will only function if you target an SNMP agent either to the Administration Server or to a Managed Server named MServer1.  Do not enter the full JMX object name of the MBean instance. Instead, enter only the value of the object name's Name=name name-value pair. To create unique MBean object names, WebLogic Server encodes several name-value pairs into each object name. One of these pairs is Name=name. For example: 'MedRec:Name=MedRecServer, Type=ServerRuntime'  In the previous example, specify MedRecServer as the name of the MBean instance."
      ::= { wlssnmpGaugeMonitorEntry 10  }
   
   
   wlssnmpLogFilterTable OBJECT-TYPE
      SYNTAX      SEQUENCE OF WlssnmpLogFilterEntry
      MAX-ACCESS  not-accessible
      STATUS      current
      DESCRIPTION "This MBean represents a filter to qualify log messages which are logged to the server logfile. A message must qualify criteria specified as a filter in order to generate a notification. Multiple instances of this MBean can be defined, if needed. If there are multiple instances, a message must qualify atleast one filter to qualify for the server logfile.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1060  }
      
   
   wlssnmpLogFilterEntry OBJECT-TYPE
      SYNTAX      WlssnmpLogFilterEntry
      MAX-ACCESS  not-accessible
      STATUS      current
      DESCRIPTION "Generated SNMP Table Entry."
      INDEX { wlssnmpLogFilterIndex}
      ::= { wlssnmpLogFilterTable 1 }
      
   WlssnmpLogFilterEntry ::=
      SEQUENCE
      {
         wlssnmpLogFilterIndex OCTET STRING,
         wlssnmpLogFilterObjectName OCTET STRING,
         wlssnmpLogFilterType OCTET STRING,
         wlssnmpLogFilterSeverityLevel OCTET STRING,
         wlssnmpLogFilterMessageSubstring OCTET STRING,
         wlssnmpLogFilterName OCTET STRING
      }
      
   
   wlssnmpLogFilterIndex OBJECT-TYPE
      SYNTAX      OCTET STRING
      MAX-ACCESS  not-accessible
      STATUS      current
      DESCRIPTION "Index column"
      ::= { wlssnmpLogFilterEntry 1  }
   
   
   wlssnmpLogFilterObjectName OBJECT-TYPE
      SYNTAX      OCTET STRING
      MAX-ACCESS  read-only
      STATUS      current
      DESCRIPTION "ObjectName column"
      ::= { wlssnmpLogFilterEntry 2  }
   
   
   wlssnmpLogFilterType OBJECT-TYPE
      SYNTAX      OCTET STRING
      MAX-ACCESS  read-only
      STATUS      current
      DESCRIPTION "Returns the type of the MBean."
      ::= { wlssnmpLogFilterEntry 3  }
   
   
   wlssnmpLogFilterSeverityLevel OBJECT-TYPE
      SYNTAX      OCTET STRING
      MAX-ACCESS  read-only
      STATUS      current
      DESCRIPTION "The minimum severity of a message that causes a WebLogic Server SNMP agent to generate a notification."
      ::= { wlssnmpLogFilterEntry 4  }
   
   
   wlssnmpLogFilterMessageSubstring OBJECT-TYPE
      SYNTAX      OCTET STRING
      MAX-ACCESS  read-only
      STATUS      current
      DESCRIPTION "A string that is searched for in the message text. Only messages that contain the string are selected. If a string is not specified, all messages are selected."
      ::= { wlssnmpLogFilterEntry 5  }
   
   
   wlssnmpLogFilterName OBJECT-TYPE
      SYNTAX      OCTET STRING
      MAX-ACCESS  read-only
      STATUS      current
      DESCRIPTION "The user-specified name of this MBean instance.  This name is included as one of the key properties in the MBean's javax.management.ObjectName: Name=user-specified-name"
      ::= { wlssnmpLogFilterEntry 6  }
   
   
   wlssnmpProxyTable OBJECT-TYPE
      SYNTAX      SEQUENCE OF WlssnmpProxyEntry
      MAX-ACCESS  not-accessible
      STATUS      current
      DESCRIPTION "This MBean represents an SNMP agent that is proxied by a WebLogic Server SNMP agent.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1065  }
      
   
   wlssnmpProxyEntry OBJECT-TYPE
      SYNTAX      WlssnmpProxyEntry
      MAX-ACCESS  not-accessible
      STATUS      current
      DESCRIPTION "Generated SNMP Table Entry."
      INDEX { wlssnmpProxyIndex}
      ::= { wlssnmpProxyTable 1 }
      
   WlssnmpProxyEntry ::=
      SEQUENCE
      {
         wlssnmpProxyIndex    OCTET STRING,
         wlssnmpProxyObjectName OCTET STRING,
         wlssnmpProxyType     OCTET STRING,
         wlssnmpProxyTimeout  Counter64,
         wlssnmpProxySecurityName OCTET STRING,
         wlssnmpProxyPort     Integer32,
         wlssnmpProxySecurityLevel OCTET STRING,
         wlssnmpProxyOidRoot  OCTET STRING,
         wlssnmpProxyCommunity OCTET STRING,
         wlssnmpProxyName     OCTET STRING
      }
      
   
   wlssnmpProxyIndex OBJECT-TYPE
      SYNTAX      OCTET STRING
      MAX-ACCESS  not-accessible
      STATUS      current
      DESCRIPTION "Index column"
      ::= { wlssnmpProxyEntry 1  }
   
   
   wlssnmpProxyObjectName OBJECT-TYPE
      SYNTAX      OCTET STRING
      MAX-ACCESS  read-only
      STATUS      current
      DESCRIPTION "ObjectName column"
      ::= { wlssnmpProxyEntry 2  }
   
   
   wlssnmpProxyType OBJECT-TYPE
      SYNTAX      OCTET STRING
      MAX-ACCESS  read-only
      STATUS      current
      DESCRIPTION "Returns the type of the MBean."
      ::= { wlssnmpProxyEntry 3  }
   
   
   wlssnmpProxyTimeout OBJECT-TYPE
      SYNTAX      Counter64
      MAX-ACCESS  read-only
      STATUS      current
      DESCRIPTION "The number of milliseconds that the WebLogic Server SNMP agent waits for a response to requests that it forwards to this proxy agent.  If the interval elapses without a response, the WebLogic SNMP agent sends an error to the requesting manager."
      ::= { wlssnmpProxyEntry 4  }
   
   
   wlssnmpProxySecurityName OBJECT-TYPE
      SYNTAX      OCTET STRING
      MAX-ACCESS  read-only
      STATUS      current
      DESCRIPTION "The user name on whose behalf the WebLogic SNMP agent forwards v3 requests.  If not specified, the request is forwarded as a v1 request.  If you specify a security name, you must also specify a security level that is equal to or lower than the security level that is configured for communication between the WebLogic SNMP agent and SNMP managers. For example, if the WebLogic SNMP agent requires incoming SNMPv3 requests to use the authentication protocol but no privacy protocol, the security level for this proxy must be either Authentication Only or None.  Note that if you want to use the authorization  or privacy protocols, you must configure credential mapping in the WebLogic Server security realm.  The WebLogic SNMP agent cannot forward or pass through the credentials that are contained in SNMPv3 requests from SNMP managers. Instead, the agent authenticates and performs other security operations on incoming requests, and then constructs a new request to forward to a proxied agent."
      ::= { wlssnmpProxyEntry 5  }
   
   
   wlssnmpProxyPort OBJECT-TYPE
      SYNTAX      Integer32
      MAX-ACCESS  read-only
      STATUS      current
      DESCRIPTION "The port number on which this proxied SNMP agent is listening."
      ::= { wlssnmpProxyEntry 6  }
   
   
   wlssnmpProxySecurityLevel OBJECT-TYPE
      SYNTAX      OCTET STRING
      MAX-ACCESS  read-only
      STATUS      current
      DESCRIPTION "The security level that the proxied SNMP agent expects for the specified security name."
      ::= { wlssnmpProxyEntry 7  }
   
   
   wlssnmpProxyOidRoot OBJECT-TYPE
      SYNTAX      OCTET STRING
      MAX-ACCESS  read-only
      STATUS      current
      DESCRIPTION "The root of the object identifier (OID) tree that this proxied SNMP agent controls."
      ::= { wlssnmpProxyEntry 8  }
   
   
   wlssnmpProxyCommunity OBJECT-TYPE
      SYNTAX      OCTET STRING
      MAX-ACCESS  read-only
      STATUS      current
      DESCRIPTION "The community name to be passed on for all SNMPv1 requests to this proxied SNMP agent.  If you specify a security name for this proxied agent, the WebLogic SNMP agent ignores this community name. Instead, the agent encodes the security name in an SNMPv3 request and forwards the SNMPv3 request to this proxied agent."
      ::= { wlssnmpProxyEntry 9  }
   
   
   wlssnmpProxyName OBJECT-TYPE
      SYNTAX      OCTET STRING
      MAX-ACCESS  read-only
      STATUS      current
      DESCRIPTION "The user-specified name of this MBean instance.  This name is included as one of the key properties in the MBean's javax.management.ObjectName: Name=user-specified-name"
      ::= { wlssnmpProxyEntry 10  }
   
   
   wlssnmpStringMonitorTable OBJECT-TYPE
      SYNTAX      SEQUENCE OF WlssnmpStringMonitorEntry
      MAX-ACCESS  not-accessible
      STATUS      current
      DESCRIPTION "This class describes the criteria for a String-based Monitor. A notification is generated when this criteria is satisfied.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1070  }
      
   
   wlssnmpStringMonitorEntry OBJECT-TYPE
      SYNTAX      WlssnmpStringMonitorEntry
      MAX-ACCESS  not-accessible
      STATUS      current
      DESCRIPTION "Generated SNMP Table Entry."
      INDEX { wlssnmpStringMonitorIndex}
      ::= { wlssnmpStringMonitorTable 1 }
      
   WlssnmpStringMonitorEntry ::=
      SEQUENCE
      {
         wlssnmpStringMonitorIndex OCTET STRING,
         wlssnmpStringMonitorObjectName OCTET STRING,
         wlssnmpStringMonitorType OCTET STRING,
         wlssnmpStringMonitorMonitoredAttributeName OCTET STRING,
         wlssnmpStringMonitorMonitoredMBeanType OCTET STRING,
         wlssnmpStringMonitorNotifyDiffer OCTET STRING,
         wlssnmpStringMonitorNotifyMatch OCTET STRING,
         wlssnmpStringMonitorStringToCompare OCTET STRING,
         wlssnmpStringMonitorName OCTET STRING,
         wlssnmpStringMonitorPollingInterval Integer32,
         wlssnmpStringMonitorMonitoredMBeanName OCTET STRING
      }
      
   
   wlssnmpStringMonitorIndex OBJECT-TYPE
      SYNTAX      OCTET STRING
      MAX-ACCESS  not-accessible
      STATUS      current
      DESCRIPTION "Index column"
      ::= { wlssnmpStringMonitorEntry 1  }
   
   
   wlssnmpStringMonitorObjectName OBJECT-TYPE
      SYNTAX      OCTET STRING
      MAX-ACCESS  read-only
      STATUS      current
      DESCRIPTION "ObjectName column"
      ::= { wlssnmpStringMonitorEntry 2  }
   
   
   wlssnmpStringMonitorType OBJECT-TYPE
      SYNTAX      OCTET STRING
      MAX-ACCESS  read-only
      STATUS      current
      DESCRIPTION "Returns the type of the MBean."
      ::= { wlssnmpStringMonitorEntry 3  }
   
   
   wlssnmpStringMonitorMonitoredAttributeName OBJECT-TYPE
      SYNTAX      OCTET STRING
      MAX-ACCESS  read-only
      STATUS      current
      DESCRIPTION "The name of an MBean attribute to monitor. This attribute must be in the WebLogic Server MIB."
      ::= { wlssnmpStringMonitorEntry 4  }
   
   
   wlssnmpStringMonitorMonitoredMBeanType OBJECT-TYPE
      SYNTAX      OCTET STRING
      MAX-ACCESS  read-only
      STATUS      current
      DESCRIPTION "The MBean type that defines the attribute you want to monitor. Do not include the MBean suffix. For example, ServerRuntime."
      ::= { wlssnmpStringMonitorEntry 5  }
   
   
   wlssnmpStringMonitorNotifyDiffer OBJECT-TYPE
      SYNTAX      OCTET STRING
      MAX-ACCESS  read-only
      STATUS      current
      DESCRIPTION "Generates a notification if the value of the monitored attribute and the value of String to Compare are different."
      ::= { wlssnmpStringMonitorEntry 6  }
   
   
   wlssnmpStringMonitorNotifyMatch OBJECT-TYPE
      SYNTAX      OCTET STRING
      MAX-ACCESS  read-only
      STATUS      current
      DESCRIPTION "Generates a notification if the value of the monitored attribute and the value of String to Compare are the same."
      ::= { wlssnmpStringMonitorEntry 7  }
   
   
   wlssnmpStringMonitorStringToCompare OBJECT-TYPE
      SYNTAX      OCTET STRING
      MAX-ACCESS  read-only
      STATUS      current
      DESCRIPTION "The string against which the value of the monitored attribute will be compared.  A notification is generated when the criteria specified by Notify Match or Notify Differ is satisfied."
      ::= { wlssnmpStringMonitorEntry 8  }
   
   
   wlssnmpStringMonitorName OBJECT-TYPE
      SYNTAX      OCTET STRING
      MAX-ACCESS  read-only
      STATUS      current
      DESCRIPTION "The user-specified name of this MBean instance.  This name is included as one of the key properties in the MBean's javax.management.ObjectName: Name=user-specified-name"
      ::= { wlssnmpStringMonitorEntry 9  }
   
   
   wlssnmpStringMonitorPollingInterval OBJECT-TYPE
      SYNTAX      Integer32
      MAX-ACCESS  read-only
      STATUS      current
      DESCRIPTION "The frequency (in seconds) that WebLogic Server checks the attribute value."
      ::= { wlssnmpStringMonitorEntry 10  }
   
   
   wlssnmpStringMonitorMonitoredMBeanName OBJECT-TYPE
      SYNTAX      OCTET STRING
      MAX-ACCESS  read-only
      STATUS      current
      DESCRIPTION "The name of the MBean instance that you want to monitor. If you leave the name undefined, WebLogic Server monitors all instances of the MBean type that you specify in Monitored MBean Type.  If you target SNMP agents to individual Managed Servers, make sure that the MBean instance you specify is active on the Managed Servers you have targeted. For example, if you specify MServer1 as the name of a ServerRuntimeMBean instance, this monitor will only function if you target an SNMP agent either to the Administration Server or to a Managed Server named MServer1.  Do not enter the full JMX object name of the MBean instance. Instead, enter only the value of the object name's Name=name name-value pair. To create unique MBean object names, WebLogic Server encodes several name-value pairs into each object name. One of these pairs is Name=name. For example: 'MedRec:Name=MedRecServer, Type=ServerRuntime'  In the previous example, specify MedRecServer as the name of the MBean instance."
      ::= { wlssnmpStringMonitorEntry 11  }
   
   
   wlssnmpTrapDestinationTable OBJECT-TYPE
      SYNTAX      SEQUENCE OF WlssnmpTrapDestinationEntry
      MAX-ACCESS  not-accessible
      STATUS      current
      DESCRIPTION "This MBean describes a destination to which an SNMP agent sends SNMP TRAP and INFORM notifications.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1075  }
      
   
   wlssnmpTrapDestinationEntry OBJECT-TYPE
      SYNTAX      WlssnmpTrapDestinationEntry
      MAX-ACCESS  not-accessible
      STATUS      current
      DESCRIPTION "Generated SNMP Table Entry."
      INDEX { wlssnmpTrapDestinationIndex}
      ::= { wlssnmpTrapDestinationTable 1 }
      
   WlssnmpTrapDestinationEntry ::=
      SEQUENCE
      {
         wlssnmpTrapDestinationIndex OCTET STRING,
         wlssnmpTrapDestinationObjectName OCTET STRING,
         wlssnmpTrapDestinationType OCTET STRING,
         wlssnmpTrapDestinationHost OCTET STRING,
         wlssnmpTrapDestinationSecurityName OCTET STRING,
         wlssnmpTrapDestinationPort Integer32,
         wlssnmpTrapDestinationSecurityLevel OCTET STRING,
         wlssnmpTrapDestinationCommunity OCTET STRING,
         wlssnmpTrapDestinationName OCTET STRING
      }
      
   
   wlssnmpTrapDestinationIndex OBJECT-TYPE
      SYNTAX      OCTET STRING
      MAX-ACCESS  not-accessible
      STATUS      current
      DESCRIPTION "Index column"
      ::= { wlssnmpTrapDestinationEntry 1  }
   
   
   wlssnmpTrapDestinationObjectName OBJECT-TYPE
      SYNTAX      OCTET STRING
      MAX-ACCESS  read-only
      STATUS      current
      DESCRIPTION "ObjectName column"
      ::= { wlssnmpTrapDestinationEntry 2  }
   
   
   wlssnmpTrapDestinationType OBJECT-TYPE
      SYNTAX      OCTET STRING
      MAX-ACCESS  read-only
      STATUS      current
      DESCRIPTION "Returns the type of the MBean."
      ::= { wlssnmpTrapDestinationEntry 3  }
   
   
   wlssnmpTrapDestinationHost OBJECT-TYPE
      SYNTAX      OCTET STRING
      MAX-ACCESS  read-only
      STATUS      current
      DESCRIPTION "The DNS name or IP address of the computer on which the SNMP manager is running.  The WebLogic SNMP agent sends trap notifications to the host and port that you specify."
      ::= { wlssnmpTrapDestinationEntry 4  }
   
   
   wlssnmpTrapDestinationSecurityName OBJECT-TYPE
      SYNTAX      OCTET STRING
      MAX-ACCESS  read-only
      STATUS      current
      DESCRIPTION "Specifies the user name that the WebLogic Server SNMP agent encodes into SNMPv3 responses or notifications. Requires you to create a credential map for this user name in the WebLogic Server security realm. The credential map contains an authentication password and an optional privacy password for this user. The user name and passwords must match the credentials required by the SNMP manager that this trap destination represents."
      ::= { wlssnmpTrapDestinationEntry 5  }
   
   
   wlssnmpTrapDestinationPort OBJECT-TYPE
      SYNTAX      Integer32
      MAX-ACCESS  read-only
      STATUS      current
      DESCRIPTION "The UDP port on which the SNMP manager is listening."
      ::= { wlssnmpTrapDestinationEntry 6  }
   
   
   wlssnmpTrapDestinationSecurityLevel OBJECT-TYPE
      SYNTAX      OCTET STRING
      MAX-ACCESS  read-only
      STATUS      current
      DESCRIPTION "Specifies the security protocols that the SNMP agent uses when sending SNMPv3 responses or notifications to the SNMP manager that this trap destination represents. Requires you to specify a security name for this trap destination."
      ::= { wlssnmpTrapDestinationEntry 7  }
   
   
   wlssnmpTrapDestinationCommunity OBJECT-TYPE
      SYNTAX      OCTET STRING
      MAX-ACCESS  read-only
      STATUS      current
      DESCRIPTION "The password (community name) that a WebLogic Server SNMP agent sends to the SNMP manager when the agent generates SNMPv1 or SNMPv2 notifications. The community name that you enter in this trap destination must match the name that the SNMP manager defines."
      ::= { wlssnmpTrapDestinationEntry 8  }
   
   
   wlssnmpTrapDestinationName OBJECT-TYPE
      SYNTAX      OCTET STRING
      MAX-ACCESS  read-only
      STATUS      current
      DESCRIPTION "The user-specified name of this MBean instance.  This name is included as one of the key properties in the MBean's javax.management.ObjectName: Name=user-specified-name"
      ::= { wlssnmpTrapDestinationEntry 9  }
   
   
   securityConfigurationTable OBJECT-TYPE
      SYNTAX      SEQUENCE OF SecurityConfigurationEntry
      MAX-ACCESS  not-accessible
      STATUS      current
      DESCRIPTION "Provides domain-wide security configuration information.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1080  }
      
   
   securityConfigurationEntry OBJECT-TYPE
      SYNTAX      SecurityConfigurationEntry
      MAX-ACCESS  not-accessible
      STATUS      current
      DESCRIPTION "Generated SNMP Table Entry."
      INDEX { securityConfigurationIndex}
      ::= { securityConfigurationTable 1 }
      
   SecurityConfigurationEntry ::=
      SEQUENCE
      {
         securityConfigurationIndex OCTET STRING,
         securityConfigurationObjectName OCTET STRING,
         securityConfigurationType OCTET STRING,
         securityConfigurationWebAppFilesCaseInsensitive OCTET STRING,
         securityConfigurationCrossDomainSecurityEnabled OCTET STRING,
         securityConfigurationEnforceStrictURLPattern OCTET STRING,
         securityConfigurationConnectionFilter OCTET STRING,
         securityConfigurationConsoleFullDelegationEnabled OCTET STRING,
         securityConfigurationDowngradeUntrustedPrincipals OCTET STRING,
         securityConfigurationName OCTET STRING,
         securityConfigurationConnectionLoggerEnabled OCTET STRING,
         securityConfigurationEnforceValidBasicAuthCredentials OCTET STRING,
         securityConfigurationNodeManagerUsername OCTET STRING,
         securityConfigurationAnonymousAdminLookupEnabled OCTET STRING,
         securityConfigurationCompatibilityConnectionFiltersEnabled OCTET STRING
      }
      
   
   securityConfigurationIndex OBJECT-TYPE
      SYNTAX      OCTET STRING
      MAX-ACCESS  not-accessible
      STATUS      current
      DESCRIPTION "Index column"
      ::= { securityConfigurationEntry 1  }
   
   
   securityConfigurationObjectName OBJECT-TYPE
      SYNTAX      OCTET STRING
      MAX-ACCESS  read-only
      STATUS      current
      DESCRIPTION "ObjectName column"
      ::= { securityConfigurationEntry 2  }
   
   
   securityConfigurationType OBJECT-TYPE
      SYNTAX      OCTET STRING
      MAX-ACCESS  read-only
      STATUS      current
      DESCRIPTION "Returns the type of the MBean."
      ::= { securityConfigurationEntry 3  }
   
   
   securityConfigurationWebAppFilesCaseInsensitive OBJECT-TYPE
      SYNTAX      OCTET STRING
      MAX-ACCESS  read-only
      STATUS      current
      DESCRIPTION "This property defines the case sensitive URL-pattern matching behavior for security constraints, servlets, filters, virtual-hosts, etc. in the WebApp container and external security policies.  When the value is set to 'os', the pattern matching will be case- sensitive on all platforms except the Windows file system.  Note that on non-Windows file systems, WebLogic doesn't enforce case sensitivity and relies on the file system for optimization. Therefore, if you have a Windows Samba mount from UNIX or Mac OS that has been installed in case-insensitive mode, there is a chance of security risk. In that case, please specify case-insensitive lookups by setting this attribute to true.  Note that this property is used to preserve backward compatibility on Windows file systems. In prior releases, WebLogic was case- insensitive on Windows. Starting with 9.0 release the URL-pattern matching will be strictly enforced.  During the upgrade of older domains the value of this parameter is explicitly set to 'os' by the upgrade plug-in, in order to preserve backward compatibility."
      ::= { securityConfigurationEntry 4  }
   
   
   securityConfigurationCrossDomainSecurityEnabled OBJECT-TYPE
      SYNTAX      OCTET STRING
      MAX-ACCESS  read-only
      STATUS      current
      DESCRIPTION "Indicates whether or not cross-domain security is enabled"
      ::= { securityConfigurationEntry 5  }
   
   
   securityConfigurationEnforceStrictURLPattern OBJECT-TYPE
      SYNTAX      OCTET STRING
      MAX-ACCESS  read-only
      STATUS      current
      DESCRIPTION "Whether or not the system should enforce strict URL pattern or not."
      ::= { securityConfigurationEntry 6  }
   
   
   securityConfigurationConnectionFilter OBJECT-TYPE
      SYNTAX      OCTET STRING
      MAX-ACCESS  read-only
      STATUS      current
      DESCRIPTION "The name of the Java class that implements a connection filter (that is, the weblogic.security.net.ConnectionFilter interface). If no class name is specified, no connection filter will be used.   This attribute replaces the deprecated ConnectionFilter attribute on the SecurityMBean."
      ::= { securityConfigurationEntry 7  }
   
   
   securityConfigurationConsoleFullDelegationEnabled OBJECT-TYPE
      SYNTAX      OCTET STRING
      MAX-ACCESS  read-only
      STATUS      current
      DESCRIPTION "Indicates whether the console is enabled for fully delegate authorization."
      ::= { securityConfigurationEntry 8  }
   
   
   securityConfigurationDowngradeUntrustedPrincipals OBJECT-TYPE
      SYNTAX      OCTET STRING
      MAX-ACCESS  read-only
      STATUS      current
      DESCRIPTION "Whether or not to downgrade to anonymous principals that cannot be verified. This is useful for server-server communication between untrusted domains."
      ::= { securityConfigurationEntry 9  }
   
   
   securityConfigurationName OBJECT-TYPE
      SYNTAX      OCTET STRING
      MAX-ACCESS  read-only
      STATUS      current
      DESCRIPTION "The user-specified name of this MBean instance.  This name is included as one of the key properties in the MBean's javax.management.ObjectName: Name=user-specified-name"
      ::= { securityConfigurationEntry 10  }
   
   
   securityConfigurationConnectionLoggerEnabled OBJECT-TYPE
      SYNTAX      OCTET STRING
      MAX-ACCESS  read-only
      STATUS      current
      DESCRIPTION "Specifies whether this WebLogic Server domain should log accepted connections.  This attribute can be used by a system administrator to dynamically check the incoming connections in the log file to determine if filtering needs to be performed.   This attribute replaces the deprecated ConnectionLoggerEnabled attribute on the SecurityMBean."
      ::= { securityConfigurationEntry 11  }
   
   
   securityConfigurationEnforceValidBasicAuthCredentials OBJECT-TYPE
      SYNTAX      OCTET STRING
      MAX-ACCESS  read-only
      STATUS      current
      DESCRIPTION "Whether or not the system should allow requests with invalid Basic Authentication credentials to access unsecure resources."
      ::= { securityConfigurationEntry 12  }
   
   
   securityConfigurationNodeManagerUsername OBJECT-TYPE
      SYNTAX      OCTET STRING
      MAX-ACCESS  read-only
      STATUS      current
      DESCRIPTION "The user name that the Administration Server uses to communicate with Node Manager when starting, stopping, or restarting Managed Servers."
      ::= { securityConfigurationEntry 13  }
   
   
   securityConfigurationAnonymousAdminLookupEnabled OBJECT-TYPE
      SYNTAX      OCTET STRING
      MAX-ACCESS  read-only
      STATUS      current
      DESCRIPTION "Returns true if anonymous JNDI access for Admin MBean home is permitted. This is overridden by the Java property -Dweblogic.management.anonymousAdminLookupEnabled."
      ::= { securityConfigurationEntry 14  }
   
   
   securityConfigurationCompatibilityConnectionFiltersEnabled OBJECT-TYPE
      SYNTAX      OCTET STRING
      MAX-ACCESS  read-only
      STATUS      current
      DESCRIPTION "Specifies whether this WebLogic Server domain enables compatiblity with previous connection filters.  This attribute changes the protocols names used when filtering needs to be performed."
      ::= { securityConfigurationEntry 15  }
   
   
   selfTuningTable OBJECT-TYPE
      SYNTAX      SEQUENCE OF SelfTuningEntry
      MAX-ACCESS  not-accessible
      STATUS      current
      DESCRIPTION "SelfTuningMBean holds global work manager component mbeans."
      ::= { wls 1085  }
      
   
   selfTuningEntry OBJECT-TYPE
      SYNTAX      SelfTuningEntry
      MAX-ACCESS  not-accessible
      STATUS      current
      DESCRIPTION "Generated SNMP Table Entry."
      INDEX { selfTuningIndex}
      ::= { selfTuningTable 1 }
      
   SelfTuningEntry ::=
      SEQUENCE
      {
         selfTuningIndex      OCTET STRING,
         selfTuningObjectName OCTET STRING,
         selfTuningType       OCTET STRING,
         selfTuningName       OCTET STRING
      }
      
   
   selfTuningIndex OBJECT-TYPE
      SYNTAX      OCTET STRING
      MAX-ACCESS  not-accessible
      STATUS      current
      DESCRIPTION "Index column"
      ::= { selfTuningEntry 1  }
   
   
   selfTuningObjectName OBJECT-TYPE
      SYNTAX      OCTET STRING
      MAX-ACCESS  read-only
      STATUS      current
      DESCRIPTION "ObjectName column"
      ::= { selfTuningEntry 2  }
   
   
   selfTuningType OBJECT-TYPE
      SYNTAX      OCTET STRING
      MAX-ACCESS  read-only
      STATUS      current
      DESCRIPTION "Returns the type of the MBean."
      ::= { selfTuningEntry 3  }
   
   
   selfTuningName OBJECT-TYPE
      SYNTAX      OCTET STRING
      MAX-ACCESS  read-only
      STATUS      current
      DESCRIPTION "The user-specified name of this MBean instance.  This name is included as one of the key properties in the MBean's javax.management.ObjectName: Name=user-specified-name"
      ::= { selfTuningEntry 4  }
   
   
   serverDebugTable OBJECT-TYPE
      SYNTAX      SEQUENCE OF ServerDebugEntry
      MAX-ACCESS  not-accessible
      STATUS      current
      DESCRIPTION "Defines the debug attributes that are specific to WebLogic Server. While all attributes will be supported in adherence with the standard WebLogic Server deprecation policies, the resultant debug content is free to change in both form and content across releases."
      ::= { wls 1090  }
      
   
   serverDebugEntry OBJECT-TYPE
      SYNTAX      ServerDebugEntry
      MAX-ACCESS  not-accessible
      STATUS      current
      DESCRIPTION "Generated SNMP Table Entry."
      INDEX { serverDebugIndex}
      ::= { serverDebugTable 1 }
      
   ServerDebugEntry ::=
      SEQUENCE
      {
         serverDebugIndex     OCTET STRING,
         serverDebugObjectName OCTET STRING,
         serverDebugDebugJDBCSQL OCTET STRING,
         serverDebugDebugIIOPConnection OCTET STRING,
         serverDebugDebugJAXPIncludeTime OCTET STRING,
         serverDebugDebugMessagingBridgeRuntime OCTET STRING,
         serverDebugDebugWebAppSecurity OCTET STRING,
         serverDebugDebugMuxerDetail OCTET STRING,
         serverDebugDebugXMLRegistryIncludeLocation OCTET STRING,
         serverDebugDebugJMXRuntime OCTET STRING,
         serverDebugDebugJNDIFactories OCTET STRING,
         serverDebugDebugDiagnosticInstrumentationWeaving OCTET STRING,
         serverDebugDebugJTARecovery OCTET STRING,
         serverDebugClassLoader OCTET STRING,
         serverDebugDebugRADeployment OCTET STRING,
         serverDebugDebugMessagingKernel OCTET STRING,
         serverDebugDebugJTAAPI OCTET STRING,
         serverDebugDebugEjbLocking OCTET STRING,
         serverDebugDebugDescriptor OCTET STRING,
         serverDebugDebugDiagnosticsHarvesterTreeBeanPlugin OCTET STRING,
         serverDebugDebugSAFTransport OCTET STRING,
         serverDebugDebugStoreIOPhysicalVerbose OCTET STRING,
         serverDebugDebugStoreIOPhysical OCTET STRING,
         serverDebugDebugJNDI OCTET STRING,
         serverDebugDebugJTALLR OCTET STRING,
         serverDebugDebugJTARecoveryStackTrace OCTET STRING,
         serverDebugDebugJTATransactionName OCTET STRING,
         serverDebugDebugRAPooling OCTET STRING,
         serverDebugDebugDeploymentServiceTransportHttp OCTET STRING,
         serverDebugDebugDiagnosticCollections OCTET STRING,
         serverDebugDebugJMXCompatibility OCTET STRING,
         serverDebugDebugDRSMessages OCTET STRING,
         serverDebugDebugMessagingBridgeRuntimeVerbose OCTET STRING,
         serverDebugDebugSecurityJACCNonPolicy OCTET STRING,
         serverDebugClassLoaderVerbose OCTET STRING,
         serverDebugDebugXMLEntityCacheUseShortClass OCTET STRING,
         serverDebugDebugJMSWrappers OCTET STRING,
         serverDebugDebugEmbeddedLDAP OCTET STRING,
         serverDebugDebugLeaderElection OCTET STRING,
         serverDebugDebugDiagnosticAccessor OCTET STRING,
         serverDebugDebugDiagnosticWatch OCTET STRING,
         serverDebugDebugJTAJDBC OCTET STRING,
         serverDebugDebugMessagingBridgeStartup OCTET STRING,
         serverDebugDebugXMLRegistryDebugLevel Integer32,
         serverDebugDebugWTCCorbaEx OCTET STRING,
         serverDebugDebugSAFSendingAgent OCTET STRING,
         serverDebugForceGCEachDGCPeriod OCTET STRING,
         serverDebugDebugDiagnosticInstrumentation OCTET STRING,
         serverDebugDebugIIOPReplacer OCTET STRING,
         serverDebugDebugFileDistributionServlet OCTET STRING,
         serverDebugDebugJTAPropagate OCTET STRING,
         serverDebugDebugXMLRegistryIncludeClass OCTET STRING,
         serverDebugDebugXMLEntityCacheDebugLevel Integer32,
         serverDebugDebugJTAHealth OCTET STRING,
         serverDebugDebugEjbSecurity OCTET STRING,
         serverDebugDebugIIOPTransport OCTET STRING,
         serverDebugDebugJDBCRMI OCTET STRING,
         serverDebugDebugJMSCDS OCTET STRING,
         serverDebugDebugXMLEntityCacheDebugName OCTET STRING,
         serverDebugDebugEjbCaching OCTET STRING,
         serverDebugDebugRAXAwork OCTET STRING,
         serverDebugDebugServerMigration OCTET STRING,
         serverDebugDebugEmbeddedLDAPLogToConsole OCTET STRING,
         serverDebugDebugJAXPDebugName OCTET STRING,
         serverDebugDebugRAConnEvents OCTET STRING,
         serverDebugDebugRAXAin OCTET STRING,
         serverDebugDebugJMSConfig OCTET STRING,
         serverDebugClassloaderWebApp OCTET STRING,
         serverDebugDebugJDBCInternal OCTET STRING,
         serverDebugDebugJpaProfile OCTET STRING,
         serverDebugDebugMessagingKernelBoot OCTET STRING,
         serverDebugWebModule OCTET STRING,
         serverDebugDebugReplication OCTET STRING,
         serverDebugDebugFailOver OCTET STRING,
         serverDebugDebugXMLEntityCacheIncludeName OCTET STRING,
         serverDebugDebugSNMPAgent OCTET STRING,
         serverDebugDebugDRSStateTransitions OCTET STRING,
         serverDebugDebugJpaManage OCTET STRING,
         serverDebugDebugJMSCommon OCTET STRING,
         serverDebugDebugJpaRuntime OCTET STRING,
         serverDebugDebugEmbeddedLDAPLogLevel Integer32,
         serverDebugDebugSecurityAdjudicator OCTET STRING,
         serverDebugDebugSAFAdmin OCTET STRING,
         serverDebugDebugEjbPooling OCTET STRING,
         serverDebugDebugWTCtBridgeEx OCTET STRING,
         serverDebugDebugSecuritySAMLLib OCTET STRING,
         serverDebugDebugDiagnosticArchive OCTET STRING,
         serverDebugDebugURLResolution OCTET STRING,
         serverDebugDebugLoadBalancing OCTET STRING,
         serverDebugDebugWebAppModule OCTET STRING,
         serverDebugDebugSecurityService OCTET STRING,
         serverDebugDebugRC4  OCTET STRING,
         serverDebugDebugXMLRegistryIncludeTime OCTET STRING,
         serverDebugDebugJAXPIncludeLocation OCTET STRING,
         serverDebugDebugLoggingConfiguration OCTET STRING,
         serverDebugDebugHttp OCTET STRING,
         serverDebugDebugDiagnosticFileArchive OCTET STRING,
         serverDebugDebugJTAXA OCTET STRING,
         serverDebugDebugIIOPSecurity OCTET STRING,
         serverDebugDebugRAXAout OCTET STRING,
         serverDebugDebugJAXPIncludeName OCTET STRING,
         serverDebugDebugDiagnosticsModule OCTET STRING,
         serverDebugApplicationContainer OCTET STRING,
         serverDebugDebugDeploy OCTET STRING,
         serverDebugDebugDeploymentServiceTransport OCTET STRING,
         serverDebugDebugWTCTDomPdu OCTET STRING,
         serverDebugDebugJTALifecycle OCTET STRING,
         serverDebugDebugJTATLOG OCTET STRING,
         serverDebugDebugRAParsing OCTET STRING,
         serverDebugDebugServerLifeCycle OCTET STRING,
         serverDebugDebugSAFReceivingAgent OCTET STRING,
         serverDebugDebugConnection OCTET STRING,
         serverDebugDebugJMSBoot OCTET STRING,
         serverDebugDebugJMSSAF OCTET STRING,
         serverDebugDebugDiagnosticImage OCTET STRING,
         serverDebugDebugJpaJdbcSchema OCTET STRING,
         serverDebugDebugTunnelingConnection OCTET STRING,
         serverDebugDebugClusterHeartbeats OCTET STRING,
         serverDebugDebugRSA  OCTET STRING,
         serverDebugDebugSecurityEEngine OCTET STRING,
         serverDebugDebugSecurityKeyStore OCTET STRING,
         serverDebugDebugXMLEntityCacheIncludeTime OCTET STRING,
         serverDebugDebugJMSPauseResume OCTET STRING,
         serverDebugDebugLibraries OCTET STRING,
         serverDebugDebugSecurityCredMap OCTET STRING,
         serverDebugDebugConfigurationRuntime OCTET STRING,
         serverDebugDebugDiagnosticLifecycleHandlers OCTET STRING,
         serverDebugDebugConfigurationEdit OCTET STRING,
         serverDebugDebugDiagnosticWlstoreArchive OCTET STRING,
         serverDebugDebugSecurityPasswordPolicy OCTET STRING,
         serverDebugDebugEjbCompilation OCTET STRING,
         serverDebugDebugJpaQuery OCTET STRING,
         serverDebugDebugSSL  OCTET STRING,
         serverDebugDebugRouting OCTET STRING,
         serverDebugDebugJpaDataCache OCTET STRING,
         serverDebugDebugConsensusLeasing OCTET STRING,
         serverDebugDebugDiagnosticInstrumentationEvents OCTET STRING,
         serverDebugDebugStoreIOLogicalBoot OCTET STRING,
         serverDebugDebugEjbSwapping OCTET STRING,
         serverDebugDebugJTANonXA OCTET STRING,
         serverDebugDebugDiagnosticInstrumentationConfig OCTET STRING,
         serverDebugDebugMessaging OCTET STRING,
         serverDebugDebugSecurityCertPath OCTET STRING,
         serverDebugDebugJNDIResolution OCTET STRING,
         serverDebugDebugSNMPProtocolTCP OCTET STRING,
         serverDebugDebugRALocalOut OCTET STRING,
         serverDebugDebugJMXDomain OCTET STRING,
         serverDebugDebugDiagnosticsHarvesterData OCTET STRING,
         serverDebugDebugSecurityRoleMap OCTET STRING,
         serverDebugDebugEjbDeployment OCTET STRING,
         serverDebugDebugSNMPToolkit OCTET STRING,
         serverDebugDebugMuxer OCTET STRING,
         serverDebugMasterDeployer OCTET STRING,
         serverDebugDebugSecuritySAMLCredMap OCTET STRING,
         serverDebugDiagnosticContextDebugMode OCTET STRING,
         serverDebugDebugSecuritySSL OCTET STRING,
         serverDebugDebugDiagnosticJdbcArchive OCTET STRING,
         serverDebugSlaveDeployer OCTET STRING,
         serverDebugDebugJTAXAStackTrace OCTET STRING,
         serverDebugDebugSecurityJACC OCTET STRING,
         serverDebugDebugEjbCmpDeployment OCTET STRING,
         serverDebugType      OCTET STRING,
         serverDebugDebugEmbeddedLDAPWriteOverrideProps OCTET STRING,
         serverDebugDebugSecurityJACCPolicy OCTET STRING,
         serverDebugDebugJMSDispatcher OCTET STRING,
         serverDebugDebugClusterAnnouncements OCTET STRING,
         serverDebugClasspathServlet OCTET STRING,
         serverDebugDebugIIOPTunneling OCTET STRING,
         serverDebugDebugJAXPDebugLevel Integer32,
         serverDebugDebugJ2EEManagement OCTET STRING,
         serverDebugDebugJTAResourceName OCTET STRING,
         serverDebugDebugSecurityEncryptionService OCTET STRING,
         serverDebugDebugJDBCConn OCTET STRING,
         serverDebugDebugDRSUpdateStatus OCTET STRING,
         serverDebugDebugDeploymentServiceStatusUpdates OCTET STRING,
         serverDebugDebugMuxerTimeout OCTET STRING,
         serverDebugDebugSAFStore OCTET STRING,
         serverDebugName      OCTET STRING,
         serverDebugDebugDomainLogHandler OCTET STRING,
         serverDebugDebugWTCConfig OCTET STRING,
         serverDebugDebugJTAGatewayStackTrace OCTET STRING,
         serverDebugDebugMuxerException OCTET STRING,
         serverDebugDebugDRSHeartbeats OCTET STRING,
         serverDebugDebugJTA2PCStackTrace OCTET STRING,
         serverDebugDebugJMSBackEnd OCTET STRING,
         serverDebugDebugXMLEntityCacheIncludeClass OCTET STRING,
         serverDebugDebugCluster OCTET STRING,
         serverDebugDebugJTAResourceHealth OCTET STRING,
         serverDebugDebugRASecurityCtx OCTET STRING,
         serverDebugDebugStoreAdmin OCTET STRING,
         serverDebugClassFinder OCTET STRING,
         serverDebugDebugDeploymentService OCTET STRING,
         serverDebugDebugHttpSessions OCTET STRING,
         serverDebugDebugJMXEdit OCTET STRING,
         serverDebugDebugClusterFragments OCTET STRING,
         serverDebugDebugWTCJatmiEx OCTET STRING,
         serverDebugDebugWTCUData OCTET STRING,
         serverDebugDebugDeploymentServiceInternal OCTET STRING,
         serverDebugDebugSecurityAuditor OCTET STRING,
         serverDebugDebugJpaJdbcSql OCTET STRING,
         serverDebugDebugEjbInvoke OCTET STRING,
         serverDebugDebugRAWork OCTET STRING,
         serverDebugDebugDRSCalls OCTET STRING,
         serverDebugDebugSecurityPredicate OCTET STRING,
         serverDebugDebugXMLRegistryUseShortClass OCTET STRING,
         serverDebugDebugSecurityUserLockout OCTET STRING,
         serverDebugDebugJTANamingStackTrace OCTET STRING,
         serverDebugListenThreadDebug OCTET STRING,
         serverDebugDebugJpaMetaData OCTET STRING,
         serverDebugDebugJTA2PC OCTET STRING,
         serverDebugDebugAppContainer OCTET STRING,
         serverDebugDebugJAXPUseShortClass OCTET STRING,
         serverDebugDebugEventManager OCTET STRING,
         serverDebugDebugJpaEnhance OCTET STRING,
         serverDebugDebugTunnelingConnectionTimeout OCTET STRING,
         serverDebugDebugSecuritySAMLAtn OCTET STRING,
         serverDebugDebugSecurityAtn OCTET STRING,
         serverDebugLogDGCStatistics OCTET STRING,
         serverDebugDebugDiagnosticQuery OCTET STRING,
         serverDebugDebugJMX  OCTET STRING,
         serverDebugDebugXMLRegistryIncludeName OCTET STRING,
         serverDebugDebugDiagnosticInstrumentationWeavingMatches OCTET STRING,
         serverDebugDebugAbbreviation OCTET STRING,
         serverDebugDebugJAXPIncludeClass OCTET STRING,
         serverDebugDebugHttpLogging OCTET STRING,
         serverDebugDebugJpaJdbcJdbc OCTET STRING,
         serverDebugDebugSAFManager OCTET STRING,
         serverDebugDebugPathSvcVerbose OCTET STRING,
         serverDebugDebugWTCGwtEx OCTET STRING,
         serverDebugDebugConnectorService OCTET STRING,
         serverDebugDebugJMSMessagePath OCTET STRING,
         serverDebugDebugJTAMigration OCTET STRING,
         serverDebugDebugSecurityRealm OCTET STRING,
         serverDebugDebugIIOPStartup OCTET STRING,
         serverDebugDebugJDBCDriverLogging OCTET STRING,
         serverDebugDebugJMSModule OCTET STRING,
         serverDebugDebugEjbCmpRuntime OCTET STRING,
         serverDebugDebugWANReplicationDetails OCTET STRING,
         serverDebugDebugJMST3Server OCTET STRING,
         serverDebugDebugXMLEntityCacheIncludeLocation OCTET STRING,
         serverDebugDebugSAFVerbose OCTET STRING,
         serverDebugDebugDRSQueues OCTET STRING,
         serverDebugDebugDiagnosticInstrumentationActions OCTET STRING,
         serverDebugDebugDiagnosticsHarvester OCTET STRING,
         serverDebugDebugEjbMdbConnection OCTET STRING,
         serverDebugDebugJTANaming OCTET STRING,
         serverDebugDebugSecuritySSLEaten OCTET STRING,
         serverDebugDebugEjbTimers OCTET STRING,
         serverDebugDebugJMXCore OCTET STRING,
         serverDebugDebugJpaTool OCTET STRING,
         serverDebugDebugIIOPNaming OCTET STRING,
         serverDebugDebugJTARMI OCTET STRING,
         serverDebugDebugJMSFrontEnd OCTET STRING,
         serverDebugDebugSecuritySAMLService OCTET STRING,
         serverDebugDebugRA   OCTET STRING,
         serverDebugDebugXMLRegistryDebugName OCTET STRING,
         serverDebugDebugSelfTuning OCTET STRING,
         serverDebugDebugIIOPMarshal OCTET STRING,
         serverDebugDebugSecurityAtz OCTET STRING,
         serverDebugDebugIIOPOTS OCTET STRING,
         serverDebugDebugDeployment OCTET STRING,
         serverDebugDebugRAWorkEvents OCTET STRING,
         serverDebugDebugJTAGateway OCTET STRING,
         serverDebugDebugWebAppIdentityAssertion OCTET STRING,
         serverDebugDebugMuxerConnection OCTET STRING,
         serverDebugDebugDiagnosticArchiveRetirement OCTET STRING,
         serverDebugDebugRAPoolVerbose OCTET STRING,
         serverDebugDebugStoreIOLogical OCTET STRING,
         serverDebugDebugRAConnections OCTET STRING,
         serverDebugDebugReplicationDetails OCTET STRING,
         serverDebugDebugDiagnosticsHarvesterMBeanPlugin OCTET STRING,
         serverDebugDebugRALifecycle OCTET STRING,
         serverDebugDebugJMSDistTopic OCTET STRING,
         serverDebugDebugDGCEnrollment OCTET STRING,
         serverDebugDebugPathSvc OCTET STRING,
         serverDebugDebugDiagnosticContext OCTET STRING
      }
      
   
   serverDebugIndex OBJECT-TYPE
      SYNTAX      OCTET STRING
      MAX-ACCESS  not-accessible
      STATUS      current
      DESCRIPTION "Index column"
      ::= { serverDebugEntry 1  }
   
   
   serverDebugObjectName OBJECT-TYPE
      SYNTAX      OCTET STRING
      MAX-ACCESS  read-only
      STATUS      current
      DESCRIPTION "ObjectName column"
      ::= { serverDebugEntry 2  }
   
   
   serverDebugDebugJDBCSQL OBJECT-TYPE
      SYNTAX      OCTET STRING
      MAX-ACCESS  read-only
      STATUS      current
      DESCRIPTION "Debug JDBC SQL processing"
      ::= { serverDebugEntry 3  }
   
   
   serverDebugDebugIIOPConnection OBJECT-TYPE
      SYNTAX      OCTET STRING
      MAX-ACCESS  read-only
      STATUS      current
      DESCRIPTION "Debug IIOP connection management processing"
      ::= { serverDebugEntry 4  }
   
   
   serverDebugDebugJAXPIncludeTime OBJECT-TYPE
      SYNTAX      OCTET STRING
      MAX-ACCESS  read-only
      STATUS      current
      DESCRIPTION "JAXP debugging option: Debug IncludeTime"
      ::= { serverDebugEntry 5  }
   
   
   serverDebugDebugMessagingBridgeRuntime OBJECT-TYPE
      SYNTAX      OCTET STRING
      MAX-ACCESS  read-only
      STATUS      current
      DESCRIPTION "Debug Messaging Bridge runtime processing"
      ::= { serverDebugEntry 6  }
   
   
   serverDebugDebugWebAppSecurity OBJECT-TYPE
      SYNTAX      OCTET STRING
      MAX-ACCESS  read-only
      STATUS      current
      DESCRIPTION "Debug webapp security"
      ::= { serverDebugEntry 7  }
   
   
   serverDebugDebugMuxerDetail OBJECT-TYPE
      SYNTAX      OCTET STRING
      MAX-ACCESS  read-only
      STATUS      current
      DESCRIPTION "Detailed debug for Muxer processing"
      ::= { serverDebugEntry 8  }
   
   
   serverDebugDebugXMLRegistryIncludeLocation OBJECT-TYPE
      SYNTAX      OCTET STRING
      MAX-ACCESS  read-only
      STATUS      current
      DESCRIPTION "XML Registry debugging option: Debug IncludeLocation"
      ::= { serverDebugEntry 9  }
   
   
   serverDebugDebugJMXRuntime OBJECT-TYPE
      SYNTAX      OCTET STRING
      MAX-ACCESS  read-only
      STATUS      current
      DESCRIPTION "Debug JMX runtime service processing"
      ::= { serverDebugEntry 10  }
   
   
   serverDebugDebugJNDIFactories OBJECT-TYPE
      SYNTAX      OCTET STRING
      MAX-ACCESS  read-only
      STATUS      current
      DESCRIPTION "Debug JNDI state and object factories."
      ::= { serverDebugEntry 11  }
   
   
   serverDebugDebugDiagnosticInstrumentationWeaving OBJECT-TYPE
      SYNTAX      OCTET STRING
      MAX-ACCESS  read-only
      STATUS      current
      DESCRIPTION "Debug instrumentation weaving"
      ::= { serverDebugEntry 12  }
   
   
   serverDebugDebugJTARecovery OBJECT-TYPE
      SYNTAX      OCTET STRING
      MAX-ACCESS  read-only
      STATUS      current
      DESCRIPTION "Debug JTA Recovery processing"
      ::= { serverDebugEntry 13  }
   
   
   serverDebugClassLoader OBJECT-TYPE
      SYNTAX      OCTET STRING
      MAX-ACCESS  read-only
      STATUS      current
      DESCRIPTION "Debug ClassLoader processing"
      ::= { serverDebugEntry 14  }
   
   
   serverDebugDebugRADeployment OBJECT-TYPE
      SYNTAX      OCTET STRING
      MAX-ACCESS  read-only
      STATUS      current
      DESCRIPTION "Debug Resource Adapter (un)deploy, security id settings"
      ::= { serverDebugEntry 15  }
   
   
   serverDebugDebugMessagingKernel OBJECT-TYPE
      SYNTAX      OCTET STRING
      MAX-ACCESS  read-only
      STATUS      current
      DESCRIPTION "Debugging for the messaging kernel. The messaging kernel is low- level messaging code that is used by the JMS and store and forward subsystems."
      ::= { serverDebugEntry 16  }
   
   
   serverDebugDebugJTAAPI OBJECT-TYPE
      SYNTAX      OCTET STRING
      MAX-ACCESS  read-only
      STATUS      current
      DESCRIPTION "Debug JTA external API"
      ::= { serverDebugEntry 17  }
   
   
   serverDebugDebugEjbLocking OBJECT-TYPE
      SYNTAX      OCTET STRING
      MAX-ACCESS  read-only
      STATUS      current
      DESCRIPTION "Debug EJB locking"
      ::= { serverDebugEntry 18  }
   
   
   serverDebugDebugDescriptor OBJECT-TYPE
      SYNTAX      OCTET STRING
      MAX-ACCESS  read-only
      STATUS      current
      DESCRIPTION "Debug descriptor framework processing"
      ::= { serverDebugEntry 19  }
   
   
   serverDebugDebugDiagnosticsHarvesterTreeBeanPlugin OBJECT-TYPE
      SYNTAX      OCTET STRING
      MAX-ACCESS  read-only
      STATUS      current
      DESCRIPTION "Debug tree bean harvester processing"
      ::= { serverDebugEntry 20  }
   
   
   serverDebugDebugSAFTransport OBJECT-TYPE
      SYNTAX      OCTET STRING
      MAX-ACCESS  read-only
      STATUS      current
      DESCRIPTION "Debug Messaging SAF Transport."
      ::= { serverDebugEntry 21  }
   
   
   serverDebugDebugStoreIOPhysicalVerbose OBJECT-TYPE
      SYNTAX      OCTET STRING
      MAX-ACCESS  read-only
      STATUS      current
      DESCRIPTION "Detailed debug for persistent store low-level physical operations which typically directly correspond to file or JDBC operations. This will produce a great deal of debugging for every disk I/O performed by the store. Multiple logical operations may occur in a single physical operation."
      ::= { serverDebugEntry 22  }
   
   
   serverDebugDebugStoreIOPhysical OBJECT-TYPE
      SYNTAX      OCTET STRING
      MAX-ACCESS  read-only
      STATUS      current
      DESCRIPTION "Debugging for persistent store low-level physical operations which typically directly correspond to file or JDBC operations. Multiple logical operations may occur in a single physical operation."
      ::= { serverDebugEntry 23  }
   
   
   serverDebugDebugJNDI OBJECT-TYPE
      SYNTAX      OCTET STRING
      MAX-ACCESS  read-only
      STATUS      current
      DESCRIPTION "Debug basic naming service machinery."
      ::= { serverDebugEntry 24  }
   
   
   serverDebugDebugJTALLR OBJECT-TYPE
      SYNTAX      OCTET STRING
      MAX-ACCESS  read-only
      STATUS      current
      DESCRIPTION "Debug JTA Logging Last Resource"
      ::= { serverDebugEntry 25  }
   
   
   serverDebugDebugJTARecoveryStackTrace OBJECT-TYPE
      SYNTAX      OCTET STRING
      MAX-ACCESS  read-only
      STATUS      current
      DESCRIPTION "Detailed debug of JTA Recovery processing"
      ::= { serverDebugEntry 26  }
   
   
   serverDebugDebugJTATransactionName OBJECT-TYPE
      SYNTAX      OCTET STRING
      MAX-ACCESS  read-only
      STATUS      current
      DESCRIPTION "Debug JTA Transaction name filter processing"
      ::= { serverDebugEntry 27  }
   
   
   serverDebugDebugRAPooling OBJECT-TYPE
      SYNTAX      OCTET STRING
      MAX-ACCESS  read-only
      STATUS      current
      DESCRIPTION "Debug Resource Adapter operations on a connection pool (proxy testing)"
      ::= { serverDebugEntry 28  }
   
   
   serverDebugDebugDeploymentServiceTransportHttp OBJECT-TYPE
      SYNTAX      OCTET STRING
      MAX-ACCESS  read-only
      STATUS      current
      DESCRIPTION "Debug deployment service HTTP transport processing"
      ::= { serverDebugEntry 29  }
   
   
   serverDebugDebugDiagnosticCollections OBJECT-TYPE
      SYNTAX      OCTET STRING
      MAX-ACCESS  read-only
      STATUS      current
      DESCRIPTION "Debug diagnostic collection processing"
      ::= { serverDebugEntry 30  }
   
   
   serverDebugDebugJMXCompatibility OBJECT-TYPE
      SYNTAX      OCTET STRING
      MAX-ACCESS  read-only
      STATUS      current
      DESCRIPTION "Debug JMX CompatibilityMBeanServer service processing"
      ::= { serverDebugEntry 31  }
   
   
   serverDebugDebugDRSMessages OBJECT-TYPE
      SYNTAX      OCTET STRING
      MAX-ACCESS  read-only
      STATUS      current
      DESCRIPTION "Debug DRS Message traffic."
      ::= { serverDebugEntry 32  }
   
   
   serverDebugDebugMessagingBridgeRuntimeVerbose OBJECT-TYPE
      SYNTAX      OCTET STRING
      MAX-ACCESS  read-only
      STATUS      current
      DESCRIPTION "Detailed debug of Messaging Bridge runtime processing"
      ::= { serverDebugEntry 33  }
   
   
   serverDebugDebugSecurityJACCNonPolicy OBJECT-TYPE
      SYNTAX      OCTET STRING
      MAX-ACCESS  read-only
      STATUS      current
      DESCRIPTION "Debug Security Framework JACC nonPolicy processing"
      ::= { serverDebugEntry 34  }
   
   
   serverDebugClassLoaderVerbose OBJECT-TYPE
      SYNTAX      OCTET STRING
      MAX-ACCESS  read-only
      STATUS      current
      DESCRIPTION "Detailed debug of ClassLoader processing"
      ::= { serverDebugEntry 35  }
   
   
   serverDebugDebugXMLEntityCacheUseShortClass OBJECT-TYPE
      SYNTAX      OCTET STRING
      MAX-ACCESS  read-only
      STATUS      current
      DESCRIPTION "XMLEntityCache debugging option: Debug UseShortClass"
      ::= { serverDebugEntry 36  }
   
   
   serverDebugDebugJMSWrappers OBJECT-TYPE
      SYNTAX      OCTET STRING
      MAX-ACCESS  read-only
      STATUS      current
      DESCRIPTION "Debug the pooling and wrapping of JMS connections, sessions, and other objects. This feature is enabled when a JMS connection factory, from any vendor, is used inside an EJB or a servlet using the 'resource-reference' element in the deployment descriptor."
      ::= { serverDebugEntry 37  }
   
   
   serverDebugDebugEmbeddedLDAP OBJECT-TYPE
      SYNTAX      OCTET STRING
      MAX-ACCESS  read-only
      STATUS      current
      DESCRIPTION "Debug Embedded LDAP processing"
      ::= { serverDebugEntry 38  }
   
   
   serverDebugDebugLeaderElection OBJECT-TYPE
      SYNTAX      OCTET STRING
      MAX-ACCESS  read-only
      STATUS      current
      DESCRIPTION "Debug the cluster leader election messages."
      ::= { serverDebugEntry 39  }
   
   
   serverDebugDebugDiagnosticAccessor OBJECT-TYPE
      SYNTAX      OCTET STRING
      MAX-ACCESS  read-only
      STATUS      current
      DESCRIPTION "Debug diagnostic accessor processing"
      ::= { serverDebugEntry 40  }
   
   
   serverDebugDebugDiagnosticWatch OBJECT-TYPE
      SYNTAX      OCTET STRING
      MAX-ACCESS  read-only
      STATUS      current
      DESCRIPTION "Debug diagnostic watch processing"
      ::= { serverDebugEntry 41  }
   
   
   serverDebugDebugJTAJDBC OBJECT-TYPE
      SYNTAX      OCTET STRING
      MAX-ACCESS  read-only
      STATUS      current
      DESCRIPTION "Debug JTA JDBC processing"
      ::= { serverDebugEntry 42  }
   
   
   serverDebugDebugMessagingBridgeStartup OBJECT-TYPE
      SYNTAX      OCTET STRING
      MAX-ACCESS  read-only
      STATUS      current
      DESCRIPTION "Debug Messaging Bridge start up processing"
      ::= { serverDebugEntry 43  }
   
   
   serverDebugDebugXMLRegistryDebugLevel OBJECT-TYPE
      SYNTAX      Integer32
      MAX-ACCESS  read-only
      STATUS      current
      DESCRIPTION "XML Registry debugging option: Debug levels"
      ::= { serverDebugEntry 44  }
   
   
   serverDebugDebugWTCCorbaEx OBJECT-TYPE
      SYNTAX      OCTET STRING
      MAX-ACCESS  read-only
      STATUS      current
      DESCRIPTION "Debug WTC corba execution"
      ::= { serverDebugEntry 45  }
   
   
   serverDebugDebugSAFSendingAgent OBJECT-TYPE
      SYNTAX      OCTET STRING
      MAX-ACCESS  read-only
      STATUS      current
      DESCRIPTION "Debug Messaging SAF SendingAgent."
      ::= { serverDebugEntry 46  }
   
   
   serverDebugForceGCEachDGCPeriod OBJECT-TYPE
      SYNTAX      OCTET STRING
      MAX-ACCESS  read-only
      STATUS      current
      DESCRIPTION "Force VM garbage collection on each DGC interval"
      ::= { serverDebugEntry 47  }
   
   
   serverDebugDebugDiagnosticInstrumentation OBJECT-TYPE
      SYNTAX      OCTET STRING
      MAX-ACCESS  read-only
      STATUS      current
      DESCRIPTION "Debug diagnostic instrumentation processing"
      ::= { serverDebugEntry 48  }
   
   
   serverDebugDebugIIOPReplacer OBJECT-TYPE
      SYNTAX      OCTET STRING
      MAX-ACCESS  read-only
      STATUS      current
      DESCRIPTION "Debug IIOP object replacement processing"
      ::= { serverDebugEntry 49  }
   
   
   serverDebugDebugFileDistributionServlet OBJECT-TYPE
      SYNTAX      OCTET STRING
      MAX-ACCESS  read-only
      STATUS      current
      DESCRIPTION "Debug the file distribution servlet that runs on the Admin Server and is invoked over HTTP by a booting managed server."
      ::= { serverDebugEntry 50  }
   
   
   serverDebugDebugJTAPropagate OBJECT-TYPE
      SYNTAX      OCTET STRING
      MAX-ACCESS  read-only
      STATUS      current
      DESCRIPTION "Debug JTA transaction propagation"
      ::= { serverDebugEntry 51  }
   
   
   serverDebugDebugXMLRegistryIncludeClass OBJECT-TYPE
      SYNTAX      OCTET STRING
      MAX-ACCESS  read-only
      STATUS      current
      DESCRIPTION "XML Registry debugging option: Debug IncludeClass"
      ::= { serverDebugEntry 52  }
   
   
   serverDebugDebugXMLEntityCacheDebugLevel OBJECT-TYPE
      SYNTAX      Integer32
      MAX-ACCESS  read-only
      STATUS      current
      DESCRIPTION "XMLEntityCache debugging option: Debug level"
      ::= { serverDebugEntry 53  }
   
   
   serverDebugDebugJTAHealth OBJECT-TYPE
      SYNTAX      OCTET STRING
      MAX-ACCESS  read-only
      STATUS      current
      DESCRIPTION "Debug JTA Health Monitoring"
      ::= { serverDebugEntry 54  }
   
   
   serverDebugDebugEjbSecurity OBJECT-TYPE
      SYNTAX      OCTET STRING
      MAX-ACCESS  read-only
      STATUS      current
      DESCRIPTION "Debug EJB Security"
      ::= { serverDebugEntry 55  }
   
   
   serverDebugDebugIIOPTransport OBJECT-TYPE
      SYNTAX      OCTET STRING
      MAX-ACCESS  read-only
      STATUS      current
      DESCRIPTION "Debug IIOP message processing"
      ::= { serverDebugEntry 56  }
   
   
   serverDebugDebugJDBCRMI OBJECT-TYPE
      SYNTAX      OCTET STRING
      MAX-ACCESS  read-only
      STATUS      current
      DESCRIPTION "Debug JDBC RMI processing"
      ::= { serverDebugEntry 57  }
   
   
   serverDebugDebugJMSCDS OBJECT-TYPE
      SYNTAX      OCTET STRING
      MAX-ACCESS  read-only
      STATUS      current
      DESCRIPTION "Debug JMS CDS processing"
      ::= { serverDebugEntry 58  }
   
   
   serverDebugDebugXMLEntityCacheDebugName OBJECT-TYPE
      SYNTAX      OCTET STRING
      MAX-ACCESS  read-only
      STATUS      current
      DESCRIPTION "XMLEntityCache debugging option: Debug name"
      ::= { serverDebugEntry 59  }
   
   
   serverDebugDebugEjbCaching OBJECT-TYPE
      SYNTAX      OCTET STRING
      MAX-ACCESS  read-only
      STATUS      current
      DESCRIPTION "Debug EJB Caching"
      ::= { serverDebugEntry 60  }
   
   
   serverDebugDebugRAXAwork OBJECT-TYPE
      SYNTAX      OCTET STRING
      MAX-ACCESS  read-only
      STATUS      current
      DESCRIPTION "Debug Resource Adapter XA Work request processing"
      ::= { serverDebugEntry 61  }
   
   
   serverDebugDebugServerMigration OBJECT-TYPE
      SYNTAX      OCTET STRING
      MAX-ACCESS  read-only
      STATUS      current
      DESCRIPTION "Debug low-level Server Migration processing"
      ::= { serverDebugEntry 62  }
   
   
   serverDebugDebugEmbeddedLDAPLogToConsole OBJECT-TYPE
      SYNTAX      OCTET STRING
      MAX-ACCESS  read-only
      STATUS      current
      DESCRIPTION "Debug Embedded LDAP processing (output to console)"
      ::= { serverDebugEntry 63  }
   
   
   serverDebugDebugJAXPDebugName OBJECT-TYPE
      SYNTAX      OCTET STRING
      MAX-ACCESS  read-only
      STATUS      current
      DESCRIPTION "JAXP debugging option: Debug name"
      ::= { serverDebugEntry 64  }
   
   
   serverDebugDebugRAConnEvents OBJECT-TYPE
      SYNTAX      OCTET STRING
      MAX-ACCESS  read-only
      STATUS      current
      DESCRIPTION "Debug Resource Adapter connection event processing"
      ::= { serverDebugEntry 65  }
   
   
   serverDebugDebugRAXAin OBJECT-TYPE
      SYNTAX      OCTET STRING
      MAX-ACCESS  read-only
      STATUS      current
      DESCRIPTION "Debug Resource Adapter XA incoming message processing"
      ::= { serverDebugEntry 66  }
   
   
   serverDebugDebugJMSConfig OBJECT-TYPE
      SYNTAX      OCTET STRING
      MAX-ACCESS  read-only
      STATUS      current
      DESCRIPTION "Debug JMSConfig processing"
      ::= { serverDebugEntry 67  }
   
   
   serverDebugClassloaderWebApp OBJECT-TYPE
      SYNTAX      OCTET STRING
      MAX-ACCESS  read-only
      STATUS      current
      DESCRIPTION "Debug WebApp ClassLoader processing"
      ::= { serverDebugEntry 68  }
   
   
   serverDebugDebugJDBCInternal OBJECT-TYPE
      SYNTAX      OCTET STRING
      MAX-ACCESS  read-only
      STATUS      current
      DESCRIPTION "Debug JDBC Internal processing"
      ::= { serverDebugEntry 69  }
   
   
   serverDebugDebugJpaProfile OBJECT-TYPE
      SYNTAX      OCTET STRING
      MAX-ACCESS  read-only
      STATUS      current
      DESCRIPTION "Debug JPA profiling"
      ::= { serverDebugEntry 70  }
   
   
   serverDebugDebugMessagingKernelBoot OBJECT-TYPE
      SYNTAX      OCTET STRING
      MAX-ACCESS  read-only
      STATUS      current
      DESCRIPTION "Debugging for the messaging kernel as the server is being rebooted. This provides detailed information on every persistent message that is recovered."
      ::= { serverDebugEntry 71  }
   
   
   serverDebugWebModule OBJECT-TYPE
      SYNTAX      OCTET STRING
      MAX-ACCESS  read-only
      STATUS      current
      DESCRIPTION "Debug WebModule processing"
      ::= { serverDebugEntry 72  }
   
   
   serverDebugDebugReplication OBJECT-TYPE
      SYNTAX      OCTET STRING
      MAX-ACCESS  read-only
      STATUS      current
      DESCRIPTION "Debug cluster replication information."
      ::= { serverDebugEntry 73  }
   
   
   serverDebugDebugFailOver OBJECT-TYPE
      SYNTAX      OCTET STRING
      MAX-ACCESS  read-only
      STATUS      current
      DESCRIPTION "Debug stub-level fail-over processing"
      ::= { serverDebugEntry 74  }
   
   
   serverDebugDebugXMLEntityCacheIncludeName OBJECT-TYPE
      SYNTAX      OCTET STRING
      MAX-ACCESS  read-only
      STATUS      current
      DESCRIPTION "XMLEntityCache debugging option: Debug IncludeName"
      ::= { serverDebugEntry 75  }
   
   
   serverDebugDebugSNMPAgent OBJECT-TYPE
      SYNTAX      OCTET STRING
      MAX-ACCESS  read-only
      STATUS      current
      DESCRIPTION "Debug the SNMP agent framework."
      ::= { serverDebugEntry 76  }
   
   
   serverDebugDebugDRSStateTransitions OBJECT-TYPE
      SYNTAX      OCTET STRING
      MAX-ACCESS  read-only
      STATUS      current
      DESCRIPTION "Debug DRS State transitions."
      ::= { serverDebugEntry 77  }
   
   
   serverDebugDebugJpaManage OBJECT-TYPE
      SYNTAX      OCTET STRING
      MAX-ACCESS  read-only
      STATUS      current
      DESCRIPTION "Debug JPA management and monitoring"
      ::= { serverDebugEntry 78  }
   
   
   serverDebugDebugJMSCommon OBJECT-TYPE
      SYNTAX      OCTET STRING
      MAX-ACCESS  read-only
      STATUS      current
      DESCRIPTION "Debug JMSCommon processing"
      ::= { serverDebugEntry 79  }
   
   
   serverDebugDebugJpaRuntime OBJECT-TYPE
      SYNTAX      OCTET STRING
      MAX-ACCESS  read-only
      STATUS      current
      DESCRIPTION "Debug JPA runtime diagnostics"
      ::= { serverDebugEntry 80  }
   
   
   serverDebugDebugEmbeddedLDAPLogLevel OBJECT-TYPE
      SYNTAX      Integer32
      MAX-ACCESS  read-only
      STATUS      current
      DESCRIPTION "Debug Embedded LDAP processing (log level)"
      ::= { serverDebugEntry 81  }
   
   
   serverDebugDebugSecurityAdjudicator OBJECT-TYPE
      SYNTAX      OCTET STRING
      MAX-ACCESS  read-only
      STATUS      current
      DESCRIPTION "Debug Security Framework Adjudication processing"
      ::= { serverDebugEntry 82  }
   
   
   serverDebugDebugSAFAdmin OBJECT-TYPE
      SYNTAX      OCTET STRING
      MAX-ACCESS  read-only
      STATUS      current
      DESCRIPTION "Debug Messaging SAF Admin."
      ::= { serverDebugEntry 83  }
   
   
   serverDebugDebugEjbPooling OBJECT-TYPE
      SYNTAX      OCTET STRING
      MAX-ACCESS  read-only
      STATUS      current
      DESCRIPTION "Debug EJB pooling"
      ::= { serverDebugEntry 84  }
   
   
   serverDebugDebugWTCtBridgeEx OBJECT-TYPE
      SYNTAX      OCTET STRING
      MAX-ACCESS  read-only
      STATUS      current
      DESCRIPTION "Debug WTC tBridge execution"
      ::= { serverDebugEntry 85  }
   
   
   serverDebugDebugSecuritySAMLLib OBJECT-TYPE
      SYNTAX      OCTET STRING
      MAX-ACCESS  read-only
      STATUS      current
      DESCRIPTION "Debug Security Framework SAML library processing"
      ::= { serverDebugEntry 86  }
   
   
   serverDebugDebugDiagnosticArchive OBJECT-TYPE
      SYNTAX      OCTET STRING
      MAX-ACCESS  read-only
      STATUS      current
      DESCRIPTION "Debug diagnostic archive processing"
      ::= { serverDebugEntry 87  }
   
   
   serverDebugDebugURLResolution OBJECT-TYPE
      SYNTAX      OCTET STRING
      MAX-ACCESS  read-only
      STATUS      current
      DESCRIPTION "Debug URL resolution for incoming http requests"
      ::= { serverDebugEntry 88  }
   
   
   serverDebugDebugLoadBalancing OBJECT-TYPE
      SYNTAX      OCTET STRING
      MAX-ACCESS  read-only
      STATUS      current
      DESCRIPTION "Debug stub-level load-balancing processing"
      ::= { serverDebugEntry 89  }
   
   
   serverDebugDebugWebAppModule OBJECT-TYPE
      SYNTAX      OCTET STRING
      MAX-ACCESS  read-only
      STATUS      current
      DESCRIPTION "Debug WebApp Module deployment callbacks"
      ::= { serverDebugEntry 90  }
   
   
   serverDebugDebugSecurityService OBJECT-TYPE
      SYNTAX      OCTET STRING
      MAX-ACCESS  read-only
      STATUS      current
      DESCRIPTION "Debug Security Service"
      ::= { serverDebugEntry 91  }
   
   
   serverDebugDebugRC4 OBJECT-TYPE
      SYNTAX      OCTET STRING
      MAX-ACCESS  read-only
      STATUS      current
      DESCRIPTION "Debug RC4 cipher processing"
      ::= { serverDebugEntry 92  }
   
   
   serverDebugDebugXMLRegistryIncludeTime OBJECT-TYPE
      SYNTAX      OCTET STRING
      MAX-ACCESS  read-only
      STATUS      current
      DESCRIPTION "XML Registry debugging option: Debug IncludeTime"
      ::= { serverDebugEntry 93  }
   
   
   serverDebugDebugJAXPIncludeLocation OBJECT-TYPE
      SYNTAX      OCTET STRING
      MAX-ACCESS  read-only
      STATUS      current
      DESCRIPTION "JAXP debugging option: Debug IncludeLocation"
      ::= { serverDebugEntry 94  }
   
   
   serverDebugDebugLoggingConfiguration OBJECT-TYPE
      SYNTAX      OCTET STRING
      MAX-ACCESS  read-only
      STATUS      current
      DESCRIPTION "Debug log configuration processing"
      ::= { serverDebugEntry 95  }
   
   
   serverDebugDebugHttp OBJECT-TYPE
      SYNTAX      OCTET STRING
      MAX-ACCESS  read-only
      STATUS      current
      DESCRIPTION "Debug WebApp Container HTTP processing."
      ::= { serverDebugEntry 96  }
   
   
   serverDebugDebugDiagnosticFileArchive OBJECT-TYPE
      SYNTAX      OCTET STRING
      MAX-ACCESS  read-only
      STATUS      current
      DESCRIPTION "Debug diagnostic file archive processing"
      ::= { serverDebugEntry 97  }
   
   
   serverDebugDebugJTAXA OBJECT-TYPE
      SYNTAX      OCTET STRING
      MAX-ACCESS  read-only
      STATUS      current
      DESCRIPTION "Debug JTA XA resources"
      ::= { serverDebugEntry 98  }
   
   
   serverDebugDebugIIOPSecurity OBJECT-TYPE
      SYNTAX      OCTET STRING
      MAX-ACCESS  read-only
      STATUS      current
      DESCRIPTION "Debug IIOP security processing"
      ::= { serverDebugEntry 99  }
   
   
   serverDebugDebugRAXAout OBJECT-TYPE
      SYNTAX      OCTET STRING
      MAX-ACCESS  read-only
      STATUS      current
      DESCRIPTION "Debug Resource Adapter XA outgoing message processing"
      ::= { serverDebugEntry 100  }
   
   
   serverDebugDebugJAXPIncludeName OBJECT-TYPE
      SYNTAX      OCTET STRING
      MAX-ACCESS  read-only
      STATUS      current
      DESCRIPTION "JAXP debugging option: Debug IncludeName"
      ::= { serverDebugEntry 101  }
   
   
   serverDebugDebugDiagnosticsModule OBJECT-TYPE
      SYNTAX      OCTET STRING
      MAX-ACCESS  read-only
      STATUS      current
      DESCRIPTION "Debug diagnostic module processing"
      ::= { serverDebugEntry 102  }
   
   
   serverDebugApplicationContainer OBJECT-TYPE
      SYNTAX      OCTET STRING
      MAX-ACCESS  read-only
      STATUS      current
      DESCRIPTION "Debug Application Container deployment processing"
      ::= { serverDebugEntry 103  }
   
   
   serverDebugDebugDeploy OBJECT-TYPE
      SYNTAX      OCTET STRING
      MAX-ACCESS  read-only
      STATUS      current
      DESCRIPTION "Debug deploy command processing"
      ::= { serverDebugEntry 104  }
   
   
   serverDebugDebugDeploymentServiceTransport OBJECT-TYPE
      SYNTAX      OCTET STRING
      MAX-ACCESS  read-only
      STATUS      current
      DESCRIPTION "Debug deployment service transport processing"
      ::= { serverDebugEntry 105  }
   
   
   serverDebugDebugWTCTDomPdu OBJECT-TYPE
      SYNTAX      OCTET STRING
      MAX-ACCESS  read-only
      STATUS      current
      DESCRIPTION "Debug WTC XATMI Message processing"
      ::= { serverDebugEntry 106  }
   
   
   serverDebugDebugJTALifecycle OBJECT-TYPE
      SYNTAX      OCTET STRING
      MAX-ACCESS  read-only
      STATUS      current
      DESCRIPTION "Debug JTA ServerLifecycle"
      ::= { serverDebugEntry 107  }
   
   
   serverDebugDebugJTATLOG OBJECT-TYPE
      SYNTAX      OCTET STRING
      MAX-ACCESS  read-only
      STATUS      current
      DESCRIPTION "Debug JTA transaction log processing"
      ::= { serverDebugEntry 108  }
   
   
   serverDebugDebugRAParsing OBJECT-TYPE
      SYNTAX      OCTET STRING
      MAX-ACCESS  read-only
      STATUS      current
      DESCRIPTION "Debug Resource Adapter descriptor parsing"
      ::= { serverDebugEntry 109  }
   
   
   serverDebugDebugServerLifeCycle OBJECT-TYPE
      SYNTAX      OCTET STRING
      MAX-ACCESS  read-only
      STATUS      current
      DESCRIPTION "Debug Server ServerLifeCycle processing"
      ::= { serverDebugEntry 110  }
   
   
   serverDebugDebugSAFReceivingAgent OBJECT-TYPE
      SYNTAX      OCTET STRING
      MAX-ACCESS  read-only
      STATUS      current
      DESCRIPTION "Debug Messaging SAF ReceivingAgent."
      ::= { serverDebugEntry 111  }
   
   
   serverDebugDebugConnection OBJECT-TYPE
      SYNTAX      OCTET STRING
      MAX-ACCESS  read-only
      STATUS      current
      DESCRIPTION "Debug JVM to JVM connections"
      ::= { serverDebugEntry 112  }
   
   
   serverDebugDebugJMSBoot OBJECT-TYPE
      SYNTAX      OCTET STRING
      MAX-ACCESS  read-only
      STATUS      current
      DESCRIPTION "Debug JMS boot operations"
      ::= { serverDebugEntry 113  }
   
   
   serverDebugDebugJMSSAF OBJECT-TYPE
      SYNTAX      OCTET STRING
      MAX-ACCESS  read-only
      STATUS      current
      DESCRIPTION "Debug JMS SAF processing"
      ::= { serverDebugEntry 114  }
   
   
   serverDebugDebugDiagnosticImage OBJECT-TYPE
      SYNTAX      OCTET STRING
      MAX-ACCESS  read-only
      STATUS      current
      DESCRIPTION "Debug diagnostic image processing"
      ::= { serverDebugEntry 115  }
   
   
   serverDebugDebugJpaJdbcSchema OBJECT-TYPE
      SYNTAX      OCTET STRING
      MAX-ACCESS  read-only
      STATUS      current
      DESCRIPTION "Debug JPA RDBMS schema manipulation"
      ::= { serverDebugEntry 116  }
   
   
   serverDebugDebugTunnelingConnection OBJECT-TYPE
      SYNTAX      OCTET STRING
      MAX-ACCESS  read-only
      STATUS      current
      DESCRIPTION "Debug HTTP tunneling connection open/close processing."
      ::= { serverDebugEntry 117  }
   
   
   serverDebugDebugClusterHeartbeats OBJECT-TYPE
      SYNTAX      OCTET STRING
      MAX-ACCESS  read-only
      STATUS      current
      DESCRIPTION "Debug each cluster Heartbeat that is sent or received by multicast."
      ::= { serverDebugEntry 118  }
   
   
   serverDebugDebugRSA OBJECT-TYPE
      SYNTAX      OCTET STRING
      MAX-ACCESS  read-only
      STATUS      current
      DESCRIPTION "Debug RSA security processing"
      ::= { serverDebugEntry 119  }
   
   
   serverDebugDebugSecurityEEngine OBJECT-TYPE
      SYNTAX      OCTET STRING
      MAX-ACCESS  read-only
      STATUS      current
      DESCRIPTION "Debug Security Framework Entitlements Engine processing"
      ::= { serverDebugEntry 120  }
   
   
   serverDebugDebugSecurityKeyStore OBJECT-TYPE
      SYNTAX      OCTET STRING
      MAX-ACCESS  read-only
      STATUS      current
      DESCRIPTION "Debug Security Framework KeyStore processing"
      ::= { serverDebugEntry 121  }
   
   
   serverDebugDebugXMLEntityCacheIncludeTime OBJECT-TYPE
      SYNTAX      OCTET STRING
      MAX-ACCESS  read-only
      STATUS      current
      DESCRIPTION "XMLEntityCache debugging option: Debug IncludeTime"
      ::= { serverDebugEntry 122  }
   
   
   serverDebugDebugJMSPauseResume OBJECT-TYPE
      SYNTAX      OCTET STRING
      MAX-ACCESS  read-only
      STATUS      current
      DESCRIPTION "Debug JMS Pause/Resume processing"
      ::= { serverDebugEntry 123  }
   
   
   serverDebugDebugLibraries OBJECT-TYPE
      SYNTAX      OCTET STRING
      MAX-ACCESS  read-only
      STATUS      current
      DESCRIPTION "Debug application library processing"
      ::= { serverDebugEntry 124  }
   
   
   serverDebugDebugSecurityCredMap OBJECT-TYPE
      SYNTAX      OCTET STRING
      MAX-ACCESS  read-only
      STATUS      current
      DESCRIPTION "Debug Security Framework Credential Mapper processing"
      ::= { serverDebugEntry 125  }
   
   
   serverDebugDebugConfigurationRuntime OBJECT-TYPE
      SYNTAX      OCTET STRING
      MAX-ACCESS  read-only
      STATUS      current
      DESCRIPTION "Debug management configuration runtime processing"
      ::= { serverDebugEntry 126  }
   
   
   serverDebugDebugDiagnosticLifecycleHandlers OBJECT-TYPE
      SYNTAX      OCTET STRING
      MAX-ACCESS  read-only
      STATUS      current
      DESCRIPTION "Debug diagnostic lifecycle handler processing"
      ::= { serverDebugEntry 127  }
   
   
   serverDebugDebugConfigurationEdit OBJECT-TYPE
      SYNTAX      OCTET STRING
      MAX-ACCESS  read-only
      STATUS      current
      DESCRIPTION "Debug management configuration edit processing"
      ::= { serverDebugEntry 128  }
   
   
   serverDebugDebugDiagnosticWlstoreArchive OBJECT-TYPE
      SYNTAX      OCTET STRING
      MAX-ACCESS  read-only
      STATUS      current
      DESCRIPTION "Debug diagnostic wlstore archive processing"
      ::= { serverDebugEntry 129  }
   
   
   serverDebugDebugSecurityPasswordPolicy OBJECT-TYPE
      SYNTAX      OCTET STRING
      MAX-ACCESS  read-only
      STATUS      current
      DESCRIPTION "Debug Security Password Guessing"
      ::= { serverDebugEntry 130  }
   
   
   serverDebugDebugEjbCompilation OBJECT-TYPE
      SYNTAX      OCTET STRING
      MAX-ACCESS  read-only
      STATUS      current
      DESCRIPTION "Debug EJB compilation"
      ::= { serverDebugEntry 131  }
   
   
   serverDebugDebugJpaQuery OBJECT-TYPE
      SYNTAX      OCTET STRING
      MAX-ACCESS  read-only
      STATUS      current
      DESCRIPTION "Debug JPA Query processing"
      ::= { serverDebugEntry 132  }
   
   
   serverDebugDebugSSL OBJECT-TYPE
      SYNTAX      OCTET STRING
      MAX-ACCESS  read-only
      STATUS      current
      DESCRIPTION "Debug SSL processing"
      ::= { serverDebugEntry 133  }
   
   
   serverDebugDebugRouting OBJECT-TYPE
      SYNTAX      OCTET STRING
      MAX-ACCESS  read-only
      STATUS      current
      DESCRIPTION "Debug routing of messages over JVM to JVM connections"
      ::= { serverDebugEntry 134  }
   
   
   serverDebugDebugJpaDataCache OBJECT-TYPE
      SYNTAX      OCTET STRING
      MAX-ACCESS  read-only
      STATUS      current
      DESCRIPTION "Debug JPA data cache"
      ::= { serverDebugEntry 135  }
   
   
   serverDebugDebugConsensusLeasing OBJECT-TYPE
      SYNTAX      OCTET STRING
      MAX-ACCESS  read-only
      STATUS      current
      DESCRIPTION "Debug cluster consensus lease processing"
      ::= { serverDebugEntry 136  }
   
   
   serverDebugDebugDiagnosticInstrumentationEvents OBJECT-TYPE
      SYNTAX      OCTET STRING
      MAX-ACCESS  read-only
      STATUS      current
      DESCRIPTION "Debug instrumentation event records"
      ::= { serverDebugEntry 137  }
   
   
   serverDebugDebugStoreIOLogicalBoot OBJECT-TYPE
      SYNTAX      OCTET STRING
      MAX-ACCESS  read-only
      STATUS      current
      DESCRIPTION "Debug persistent store logical boot operations (lists all recovered records)."
      ::= { serverDebugEntry 138  }
   
   
   serverDebugDebugEjbSwapping OBJECT-TYPE
      SYNTAX      OCTET STRING
      MAX-ACCESS  read-only
      STATUS      current
      DESCRIPTION "Debug EJB Swapping"
      ::= { serverDebugEntry 139  }
   
   
   serverDebugDebugJTANonXA OBJECT-TYPE
      SYNTAX      OCTET STRING
      MAX-ACCESS  read-only
      STATUS      current
      DESCRIPTION "Debug JTA non-XA resources"
      ::= { serverDebugEntry 140  }
   
   
   serverDebugDebugDiagnosticInstrumentationConfig OBJECT-TYPE
      SYNTAX      OCTET STRING
      MAX-ACCESS  read-only
      STATUS      current
      DESCRIPTION "Debug instrumentation configuration processing"
      ::= { serverDebugEntry 141  }
   
   
   serverDebugDebugMessaging OBJECT-TYPE
      SYNTAX      OCTET STRING
      MAX-ACCESS  read-only
      STATUS      current
      DESCRIPTION "Debug messages sent over JVM to JVM connections"
      ::= { serverDebugEntry 142  }
   
   
   serverDebugDebugSecurityCertPath OBJECT-TYPE
      SYNTAX      OCTET STRING
      MAX-ACCESS  read-only
      STATUS      current
      DESCRIPTION "Debug Security Framework CertPath processing"
      ::= { serverDebugEntry 143  }
   
   
   serverDebugDebugJNDIResolution OBJECT-TYPE
      SYNTAX      OCTET STRING
      MAX-ACCESS  read-only
      STATUS      current
      DESCRIPTION "Debug naming service name resolution."
      ::= { serverDebugEntry 144  }
   
   
   serverDebugDebugSNMPProtocolTCP OBJECT-TYPE
      SYNTAX      OCTET STRING
      MAX-ACCESS  read-only
      STATUS      current
      DESCRIPTION "Debug the SNMP TCP protocol handler."
      ::= { serverDebugEntry 145  }
   
   
   serverDebugDebugRALocalOut OBJECT-TYPE
      SYNTAX      OCTET STRING
      MAX-ACCESS  read-only
      STATUS      current
      DESCRIPTION "Debug Resource Adapter local tx outgoing message processing"
      ::= { serverDebugEntry 146  }
   
   
   serverDebugDebugJMXDomain OBJECT-TYPE
      SYNTAX      OCTET STRING
      MAX-ACCESS  read-only
      STATUS      current
      DESCRIPTION "Debug JMX domain service processing"
      ::= { serverDebugEntry 147  }
   
   
   serverDebugDebugDiagnosticsHarvesterData OBJECT-TYPE
      SYNTAX      OCTET STRING
      MAX-ACCESS  read-only
      STATUS      current
      DESCRIPTION "Detailed debug of diagnostic harvester processing This should be used in conjunction with DebugDiagnosticsHarvester."
      ::= { serverDebugEntry 148  }
   
   
   serverDebugDebugSecurityRoleMap OBJECT-TYPE
      SYNTAX      OCTET STRING
      MAX-ACCESS  read-only
      STATUS      current
      DESCRIPTION "Debug Security Framework Role Mapping"
      ::= { serverDebugEntry 149  }
   
   
   serverDebugDebugEjbDeployment OBJECT-TYPE
      SYNTAX      OCTET STRING
      MAX-ACCESS  read-only
      STATUS      current
      DESCRIPTION "Debug EJB deployment"
      ::= { serverDebugEntry 150  }
   
   
   serverDebugDebugSNMPToolkit OBJECT-TYPE
      SYNTAX      OCTET STRING
      MAX-ACCESS  read-only
      STATUS      current
      DESCRIPTION "Debug the SNMP vendor toolkit implementation."
      ::= { serverDebugEntry 151  }
   
   
   serverDebugDebugMuxer OBJECT-TYPE
      SYNTAX      OCTET STRING
      MAX-ACCESS  read-only
      STATUS      current
      DESCRIPTION "Debug Muxer processing"
      ::= { serverDebugEntry 152  }
   
   
   serverDebugMasterDeployer OBJECT-TYPE
      SYNTAX      OCTET STRING
      MAX-ACCESS  read-only
      STATUS      current
      DESCRIPTION "Debug Master Deployer processing"
      ::= { serverDebugEntry 153  }
   
   
   serverDebugDebugSecuritySAMLCredMap OBJECT-TYPE
      SYNTAX      OCTET STRING
      MAX-ACCESS  read-only
      STATUS      current
      DESCRIPTION "Debug Security Framework SAML Provider credential mapper processing"
      ::= { serverDebugEntry 154  }
   
   
   serverDebugDiagnosticContextDebugMode OBJECT-TYPE
      SYNTAX      OCTET STRING
      MAX-ACCESS  read-only
      STATUS      current
      DESCRIPTION "Indicates whether or not context based debugging is enabled."
      ::= { serverDebugEntry 155  }
   
   
   serverDebugDebugSecuritySSL OBJECT-TYPE
      SYNTAX      OCTET STRING
      MAX-ACCESS  read-only
      STATUS      current
      DESCRIPTION "Debug Security SSL and TLS processing"
      ::= { serverDebugEntry 156  }
   
   
   serverDebugDebugDiagnosticJdbcArchive OBJECT-TYPE
      SYNTAX      OCTET STRING
      MAX-ACCESS  read-only
      STATUS      current
      DESCRIPTION "Debug diagnostic jdbc archive processing"
      ::= { serverDebugEntry 157  }
   
   
   serverDebugSlaveDeployer OBJECT-TYPE
      SYNTAX      OCTET STRING
      MAX-ACCESS  read-only
      STATUS      current
      DESCRIPTION "Debug Slave Deployer processing"
      ::= { serverDebugEntry 158  }
   
   
   serverDebugDebugJTAXAStackTrace OBJECT-TYPE
      SYNTAX      OCTET STRING
      MAX-ACCESS  read-only
      STATUS      current
      DESCRIPTION "Detailed Debug of JTA XA processing"
      ::= { serverDebugEntry 159  }
   
   
   serverDebugDebugSecurityJACC OBJECT-TYPE
      SYNTAX      OCTET STRING
      MAX-ACCESS  read-only
      STATUS      current
      DESCRIPTION "Debug Security Framework JACC processing"
      ::= { serverDebugEntry 160  }
   
   
   serverDebugDebugEjbCmpDeployment OBJECT-TYPE
      SYNTAX      OCTET STRING
      MAX-ACCESS  read-only
      STATUS      current
      DESCRIPTION "Debug EJB CMP deployment processing"
      ::= { serverDebugEntry 161  }
   
   
   serverDebugType OBJECT-TYPE
      SYNTAX      OCTET STRING
      MAX-ACCESS  read-only
      STATUS      current
      DESCRIPTION "Returns the type of the MBean."
      ::= { serverDebugEntry 162  }
   
   
   serverDebugDebugEmbeddedLDAPWriteOverrideProps OBJECT-TYPE
      SYNTAX      OCTET STRING
      MAX-ACCESS  read-only
      STATUS      current
      DESCRIPTION "Embedded LDAP Write All Overrides to Property Files"
      ::= { serverDebugEntry 163  }
   
   
   serverDebugDebugSecurityJACCPolicy OBJECT-TYPE
      SYNTAX      OCTET STRING
      MAX-ACCESS  read-only
      STATUS      current
      DESCRIPTION "Debug Security Framework JACC Policy processing"
      ::= { serverDebugEntry 164  }
   
   
   serverDebugDebugJMSDispatcher OBJECT-TYPE
      SYNTAX      OCTET STRING
      MAX-ACCESS  read-only
      STATUS      current
      DESCRIPTION "Debug JMS Dispatcher processing"
      ::= { serverDebugEntry 165  }
   
   
   serverDebugDebugClusterAnnouncements OBJECT-TYPE
      SYNTAX      OCTET STRING
      MAX-ACCESS  read-only
      STATUS      current
      DESCRIPTION "Debug each Announcement, StateDump, and Attributes message that is sent or received by multicast."
      ::= { serverDebugEntry 166  }
   
   
   serverDebugClasspathServlet OBJECT-TYPE
      SYNTAX      OCTET STRING
      MAX-ACCESS  read-only
      STATUS      current
      DESCRIPTION "Debug ClassPathServlet processing"
      ::= { serverDebugEntry 167  }
   
   
   serverDebugDebugIIOPTunneling OBJECT-TYPE
      SYNTAX      OCTET STRING
      MAX-ACCESS  read-only
      STATUS      current
      DESCRIPTION "Debug IIOP tunnelling"
      ::= { serverDebugEntry 168  }
   
   
   serverDebugDebugJAXPDebugLevel OBJECT-TYPE
      SYNTAX      Integer32
      MAX-ACCESS  read-only
      STATUS      current
      DESCRIPTION "JAXP debugging option: Debug level"
      ::= { serverDebugEntry 169  }
   
   
   serverDebugDebugJ2EEManagement OBJECT-TYPE
      SYNTAX      OCTET STRING
      MAX-ACCESS  read-only
      STATUS      current
      DESCRIPTION "Debug J2EE management processing"
      ::= { serverDebugEntry 170  }
   
   
   serverDebugDebugJTAResourceName OBJECT-TYPE
      SYNTAX      OCTET STRING
      MAX-ACCESS  read-only
      STATUS      current
      DESCRIPTION "Debug JTA Resource name filter"
      ::= { serverDebugEntry 171  }
   
   
   serverDebugDebugSecurityEncryptionService OBJECT-TYPE
      SYNTAX      OCTET STRING
      MAX-ACCESS  read-only
      STATUS      current
      DESCRIPTION "Debug Security Framework Encryption Service processing"
      ::= { serverDebugEntry 172  }
   
   
   serverDebugDebugJDBCConn OBJECT-TYPE
      SYNTAX      OCTET STRING
      MAX-ACCESS  read-only
      STATUS      current
      DESCRIPTION "Debug JDBC Connection setup/teardown processing"
      ::= { serverDebugEntry 173  }
   
   
   serverDebugDebugDRSUpdateStatus OBJECT-TYPE
      SYNTAX      OCTET STRING
      MAX-ACCESS  read-only
      STATUS      current
      DESCRIPTION "Debug DRS Update status processing."
      ::= { serverDebugEntry 174  }
   
   
   serverDebugDebugDeploymentServiceStatusUpdates OBJECT-TYPE
      SYNTAX      OCTET STRING
      MAX-ACCESS  read-only
      STATUS      current
      DESCRIPTION "Debug deployment service status update processing"
      ::= { serverDebugEntry 175  }
   
   
   serverDebugDebugMuxerTimeout OBJECT-TYPE
      SYNTAX      OCTET STRING
      MAX-ACCESS  read-only
      STATUS      current
      DESCRIPTION "Debug Muxer timeout processing"
      ::= { serverDebugEntry 176  }
   
   
   serverDebugDebugSAFStore OBJECT-TYPE
      SYNTAX      OCTET STRING
      MAX-ACCESS  read-only
      STATUS      current
      DESCRIPTION "Debug Messaging SAF Store."
      ::= { serverDebugEntry 177  }
   
   
   serverDebugName OBJECT-TYPE
      SYNTAX      OCTET STRING
      MAX-ACCESS  read-only
      STATUS      current
      DESCRIPTION "The user-specified name of this MBean instance.  This name is included as one of the key properties in the MBean's javax.management.ObjectName: Name=user-specified-name"
      ::= { serverDebugEntry 178  }
   
   
   serverDebugDebugDomainLogHandler OBJECT-TYPE
      SYNTAX      OCTET STRING
      MAX-ACCESS  read-only
      STATUS      current
      DESCRIPTION "Debug Domain Log Handler processing"
      ::= { serverDebugEntry 179  }
   
   
   serverDebugDebugWTCConfig OBJECT-TYPE
      SYNTAX      OCTET STRING
      MAX-ACCESS  read-only
      STATUS      current
      DESCRIPTION "Debug WTC configuration processing"
      ::= { serverDebugEntry 180  }
   
   
   serverDebugDebugJTAGatewayStackTrace OBJECT-TYPE
      SYNTAX      OCTET STRING
      MAX-ACCESS  read-only
      STATUS      current
      DESCRIPTION "Detailed debug of JTA imported transactions"
      ::= { serverDebugEntry 181  }
   
   
   serverDebugDebugMuxerException OBJECT-TYPE
      SYNTAX      OCTET STRING
      MAX-ACCESS  read-only
      STATUS      current
      DESCRIPTION "Debug Muxer exception processing"
      ::= { serverDebugEntry 182  }
   
   
   serverDebugDebugDRSHeartbeats OBJECT-TYPE
      SYNTAX      OCTET STRING
      MAX-ACCESS  read-only
      STATUS      current
      DESCRIPTION "Debug DRS Heartbeats."
      ::= { serverDebugEntry 183  }
   
   
   serverDebugDebugJTA2PCStackTrace OBJECT-TYPE
      SYNTAX      OCTET STRING
      MAX-ACCESS  read-only
      STATUS      current
      DESCRIPTION "Detailed Debug of JTA 2PC processing"
      ::= { serverDebugEntry 184  }
   
   
   serverDebugDebugJMSBackEnd OBJECT-TYPE
      SYNTAX      OCTET STRING
      MAX-ACCESS  read-only
      STATUS      current
      DESCRIPTION "Debug JMSBackEnd processing"
      ::= { serverDebugEntry 185  }
   
   
   serverDebugDebugXMLEntityCacheIncludeClass OBJECT-TYPE
      SYNTAX      OCTET STRING
      MAX-ACCESS  read-only
      STATUS      current
      DESCRIPTION "XMLEntityCache debugging option: Debug IncludeClass"
      ::= { serverDebugEntry 186  }
   
   
   serverDebugDebugCluster OBJECT-TYPE
      SYNTAX      OCTET STRING
      MAX-ACCESS  read-only
      STATUS      current
      DESCRIPTION "Debug each GroupMessage that is sent or received by multicast."
      ::= { serverDebugEntry 187  }
   
   
   serverDebugDebugJTAResourceHealth OBJECT-TYPE
      SYNTAX      OCTET STRING
      MAX-ACCESS  read-only
      STATUS      current
      DESCRIPTION "Debug JTA resource health"
      ::= { serverDebugEntry 188  }
   
   
   serverDebugDebugRASecurityCtx OBJECT-TYPE
      SYNTAX      OCTET STRING
      MAX-ACCESS  read-only
      STATUS      current
      DESCRIPTION "Debug setup of resource ref processing (container and application managed security set by calling application components)"
      ::= { serverDebugEntry 189  }
   
   
   serverDebugDebugStoreAdmin OBJECT-TYPE
      SYNTAX      OCTET STRING
      MAX-ACCESS  read-only
      STATUS      current
      DESCRIPTION "Debug the persistent store's administration code. This will produce debug events when instances of the store are created and deleted, and when the server is booted."
      ::= { serverDebugEntry 190  }
   
   
   serverDebugClassFinder OBJECT-TYPE
      SYNTAX      OCTET STRING
      MAX-ACCESS  read-only
      STATUS      current
      DESCRIPTION "Debug ClassFinder processing"
      ::= { serverDebugEntry 191  }
   
   
   serverDebugDebugDeploymentService OBJECT-TYPE
      SYNTAX      OCTET STRING
      MAX-ACCESS  read-only
      STATUS      current
      DESCRIPTION "Debug deployment service processing"
      ::= { serverDebugEntry 192  }
   
   
   serverDebugDebugHttpSessions OBJECT-TYPE
      SYNTAX      OCTET STRING
      MAX-ACCESS  read-only
      STATUS      current
      DESCRIPTION "Debug Http Session management in the webapp container."
      ::= { serverDebugEntry 193  }
   
   
   serverDebugDebugJMXEdit OBJECT-TYPE
      SYNTAX      OCTET STRING
      MAX-ACCESS  read-only
      STATUS      current
      DESCRIPTION "Debug JMX edit service processing"
      ::= { serverDebugEntry 194  }
   
   
   serverDebugDebugClusterFragments OBJECT-TYPE
      SYNTAX      OCTET STRING
      MAX-ACCESS  read-only
      STATUS      current
      DESCRIPTION "Debug for each fragment that is sent or received by multicast."
      ::= { serverDebugEntry 195  }
   
   
   serverDebugDebugWTCJatmiEx OBJECT-TYPE
      SYNTAX      OCTET STRING
      MAX-ACCESS  read-only
      STATUS      current
      DESCRIPTION "Debug WTC jatmi execution"
      ::= { serverDebugEntry 196  }
   
   
   serverDebugDebugWTCUData OBJECT-TYPE
      SYNTAX      OCTET STRING
      MAX-ACCESS  read-only
      STATUS      current
      DESCRIPTION "Debug WTC user data processing"
      ::= { serverDebugEntry 197  }
   
   
   serverDebugDebugDeploymentServiceInternal OBJECT-TYPE
      SYNTAX      OCTET STRING
      MAX-ACCESS  read-only
      STATUS      current
      DESCRIPTION "Debug internal deployment service processing"
      ::= { serverDebugEntry 198  }
   
   
   serverDebugDebugSecurityAuditor OBJECT-TYPE
      SYNTAX      OCTET STRING
      MAX-ACCESS  read-only
      STATUS      current
      DESCRIPTION "Debug Security Framework Auditor processing"
      ::= { serverDebugEntry 199  }
   
   
   serverDebugDebugJpaJdbcSql OBJECT-TYPE
      SYNTAX      OCTET STRING
      MAX-ACCESS  read-only
      STATUS      current
      DESCRIPTION "Debug JPA RDBMS SQL interaction"
      ::= { serverDebugEntry 200  }
   
   
   serverDebugDebugEjbInvoke OBJECT-TYPE
      SYNTAX      OCTET STRING
      MAX-ACCESS  read-only
      STATUS      current
      DESCRIPTION "Debug EJB invocation processing"
      ::= { serverDebugEntry 201  }
   
   
   serverDebugDebugRAWork OBJECT-TYPE
      SYNTAX      OCTET STRING
      MAX-ACCESS  read-only
      STATUS      current
      DESCRIPTION "Debug Resource Adapter Work submission and cancel processing"
      ::= { serverDebugEntry 202  }
   
   
   serverDebugDebugDRSCalls OBJECT-TYPE
      SYNTAX      OCTET STRING
      MAX-ACCESS  read-only
      STATUS      current
      DESCRIPTION "Debug Data replication service (DRS) API calls."
      ::= { serverDebugEntry 203  }
   
   
   serverDebugDebugSecurityPredicate OBJECT-TYPE
      SYNTAX      OCTET STRING
      MAX-ACCESS  read-only
      STATUS      current
      DESCRIPTION "Debug Security Framework predicate processing"
      ::= { serverDebugEntry 204  }
   
   
   serverDebugDebugXMLRegistryUseShortClass OBJECT-TYPE
      SYNTAX      OCTET STRING
      MAX-ACCESS  read-only
      STATUS      current
      DESCRIPTION "XML Registry debugging option: Debug UseShortClass"
      ::= { serverDebugEntry 205  }
   
   
   serverDebugDebugSecurityUserLockout OBJECT-TYPE
      SYNTAX      OCTET STRING
      MAX-ACCESS  read-only
      STATUS      current
      DESCRIPTION "Debug Security User Lockout processing"
      ::= { serverDebugEntry 206  }
   
   
   serverDebugDebugJTANamingStackTrace OBJECT-TYPE
      SYNTAX      OCTET STRING
      MAX-ACCESS  read-only
      STATUS      current
      DESCRIPTION "Detailed debug of JTA naming"
      ::= { serverDebugEntry 207  }
   
   
   serverDebugListenThreadDebug OBJECT-TYPE
      SYNTAX      OCTET STRING
      MAX-ACCESS  read-only
      STATUS      current
      DESCRIPTION "Debug listenThread processing"
      ::= { serverDebugEntry 208  }
   
   
   serverDebugDebugJpaMetaData OBJECT-TYPE
      SYNTAX      OCTET STRING
      MAX-ACCESS  read-only
      STATUS      current
      DESCRIPTION "Debug JPA MetaData processing"
      ::= { serverDebugEntry 209  }
   
   
   serverDebugDebugJTA2PC OBJECT-TYPE
      SYNTAX      OCTET STRING
      MAX-ACCESS  read-only
      STATUS      current
      DESCRIPTION "Debug JTA 2PC processing"
      ::= { serverDebugEntry 210  }
   
   
   serverDebugDebugAppContainer OBJECT-TYPE
      SYNTAX      OCTET STRING
      MAX-ACCESS  read-only
      STATUS      current
      DESCRIPTION "Debug Application Container processing"
      ::= { serverDebugEntry 211  }
   
   
   serverDebugDebugJAXPUseShortClass OBJECT-TYPE
      SYNTAX      OCTET STRING
      MAX-ACCESS  read-only
      STATUS      current
      DESCRIPTION "JAXP debugging option: Debug UseShortClass"
      ::= { serverDebugEntry 212  }
   
   
   serverDebugDebugEventManager OBJECT-TYPE
      SYNTAX      OCTET STRING
      MAX-ACCESS  read-only
      STATUS      current
      DESCRIPTION "Debug Event Manager processing"
      ::= { serverDebugEntry 213  }
   
   
   serverDebugDebugJpaEnhance OBJECT-TYPE
      SYNTAX      OCTET STRING
      MAX-ACCESS  read-only
      STATUS      current
      DESCRIPTION "Debug JPA post-compilation"
      ::= { serverDebugEntry 214  }
   
   
   serverDebugDebugTunnelingConnectionTimeout OBJECT-TYPE
      SYNTAX      OCTET STRING
      MAX-ACCESS  read-only
      STATUS      current
      DESCRIPTION "Debug HTTP tunneling connection timed out processing."
      ::= { serverDebugEntry 215  }
   
   
   serverDebugDebugSecuritySAMLAtn OBJECT-TYPE
      SYNTAX      OCTET STRING
      MAX-ACCESS  read-only
      STATUS      current
      DESCRIPTION "Debug Security Framework SAML Provider atn processing"
      ::= { serverDebugEntry 216  }
   
   
   serverDebugDebugSecurityAtn OBJECT-TYPE
      SYNTAX      OCTET STRING
      MAX-ACCESS  read-only
      STATUS      current
      DESCRIPTION "Debug Security Framework Atn processing"
      ::= { serverDebugEntry 217  }
   
   
   serverDebugLogDGCStatistics OBJECT-TYPE
      SYNTAX      OCTET STRING
      MAX-ACCESS  read-only
      STATUS      current
      DESCRIPTION "Debug DGC with Statistics"
      ::= { serverDebugEntry 218  }
   
   
   serverDebugDebugDiagnosticQuery OBJECT-TYPE
      SYNTAX      OCTET STRING
      MAX-ACCESS  read-only
      STATUS      current
      DESCRIPTION "Debug diagnostic query processing"
      ::= { serverDebugEntry 219  }
   
   
   serverDebugDebugJMX OBJECT-TYPE
      SYNTAX      OCTET STRING
      MAX-ACCESS  read-only
      STATUS      current
      DESCRIPTION "Debug JMX processing"
      ::= { serverDebugEntry 220  }
   
   
   serverDebugDebugXMLRegistryIncludeName OBJECT-TYPE
      SYNTAX      OCTET STRING
      MAX-ACCESS  read-only
      STATUS      current
      DESCRIPTION "XML Registry debugging option: Debug IncludeName"
      ::= { serverDebugEntry 221  }
   
   
   serverDebugDebugDiagnosticInstrumentationWeavingMatches OBJECT-TYPE
      SYNTAX      OCTET STRING
      MAX-ACCESS  read-only
      STATUS      current
      DESCRIPTION "Debug instrumentation weaving for matches only"
      ::= { serverDebugEntry 222  }
   
   
   serverDebugDebugAbbreviation OBJECT-TYPE
      SYNTAX      OCTET STRING
      MAX-ACCESS  read-only
      STATUS      current
      DESCRIPTION "Debug abbreviations over JVM to JVM connections"
      ::= { serverDebugEntry 223  }
   
   
   serverDebugDebugJAXPIncludeClass OBJECT-TYPE
      SYNTAX      OCTET STRING
      MAX-ACCESS  read-only
      STATUS      current
      DESCRIPTION "JAXP debugging option: Debug IncludeClass"
      ::= { serverDebugEntry 224  }
   
   
   serverDebugDebugHttpLogging OBJECT-TYPE
      SYNTAX      OCTET STRING
      MAX-ACCESS  read-only
      STATUS      current
      DESCRIPTION "Debug log manager in the webapp container."
      ::= { serverDebugEntry 225  }
   
   
   serverDebugDebugJpaJdbcJdbc OBJECT-TYPE
      SYNTAX      OCTET STRING
      MAX-ACCESS  read-only
      STATUS      current
      DESCRIPTION "Debug JPA RDBMS JDBC interaction"
      ::= { serverDebugEntry 226  }
   
   
   serverDebugDebugSAFManager OBJECT-TYPE
      SYNTAX      OCTET STRING
      MAX-ACCESS  read-only
      STATUS      current
      DESCRIPTION "Debug Messaging SAF Manager."
      ::= { serverDebugEntry 227  }
   
   
   serverDebugDebugPathSvcVerbose OBJECT-TYPE
      SYNTAX      OCTET STRING
      MAX-ACCESS  read-only
      STATUS      current
      DESCRIPTION "Detailed debug for the Path Service"
      ::= { serverDebugEntry 228  }
   
   
   serverDebugDebugWTCGwtEx OBJECT-TYPE
      SYNTAX      OCTET STRING
      MAX-ACCESS  read-only
      STATUS      current
      DESCRIPTION "Debug WTC gwt execution"
      ::= { serverDebugEntry 229  }
   
   
   serverDebugDebugConnectorService OBJECT-TYPE
      SYNTAX      OCTET STRING
      MAX-ACCESS  read-only
      STATUS      current
      DESCRIPTION "Debug connector service action processing"
      ::= { serverDebugEntry 230  }
   
   
   serverDebugDebugJMSMessagePath OBJECT-TYPE
      SYNTAX      OCTET STRING
      MAX-ACCESS  read-only
      STATUS      current
      DESCRIPTION "Debug JMS MessagePath processing"
      ::= { serverDebugEntry 231  }
   
   
   serverDebugDebugJTAMigration OBJECT-TYPE
      SYNTAX      OCTET STRING
      MAX-ACCESS  read-only
      STATUS      current
      DESCRIPTION "Debug JTA TLOG Migration"
      ::= { serverDebugEntry 232  }
   
   
   serverDebugDebugSecurityRealm OBJECT-TYPE
      SYNTAX      OCTET STRING
      MAX-ACCESS  read-only
      STATUS      current
      DESCRIPTION "Debug Security Realm processing"
      ::= { serverDebugEntry 233  }
   
   
   serverDebugDebugIIOPStartup OBJECT-TYPE
      SYNTAX      OCTET STRING
      MAX-ACCESS  read-only
      STATUS      current
      DESCRIPTION "Debug IIOP startup processing"
      ::= { serverDebugEntry 234  }
   
   
   serverDebugDebugJDBCDriverLogging OBJECT-TYPE
      SYNTAX      OCTET STRING
      MAX-ACCESS  read-only
      STATUS      current
      DESCRIPTION "Debug JDBC DriverLogging processing"
      ::= { serverDebugEntry 235  }
   
   
   serverDebugDebugJMSModule OBJECT-TYPE
      SYNTAX      OCTET STRING
      MAX-ACCESS  read-only
      STATUS      current
      DESCRIPTION "Debug JMSModule deployment processing"
      ::= { serverDebugEntry 236  }
   
   
   serverDebugDebugEjbCmpRuntime OBJECT-TYPE
      SYNTAX      OCTET STRING
      MAX-ACCESS  read-only
      STATUS      current
      DESCRIPTION "Debug EJB CMP runtime processing"
      ::= { serverDebugEntry 237  }
   
   
   serverDebugDebugWANReplicationDetails OBJECT-TYPE
      SYNTAX      OCTET STRING
      MAX-ACCESS  read-only
      STATUS      current
      DESCRIPTION "Debug low-level wan replication processing"
      ::= { serverDebugEntry 238  }
   
   
   serverDebugDebugJMST3Server OBJECT-TYPE
      SYNTAX      OCTET STRING
      MAX-ACCESS  read-only
      STATUS      current
      DESCRIPTION "Debug DebugJMST3Server processing"
      ::= { serverDebugEntry 239  }
   
   
   serverDebugDebugXMLEntityCacheIncludeLocation OBJECT-TYPE
      SYNTAX      OCTET STRING
      MAX-ACCESS  read-only
      STATUS      current
      DESCRIPTION "XMLEntityCache debugging option: Debug IncludeLocation"
      ::= { serverDebugEntry 240  }
   
   
   serverDebugDebugSAFVerbose OBJECT-TYPE
      SYNTAX      OCTET STRING
      MAX-ACCESS  read-only
      STATUS      current
      DESCRIPTION "Detailed debug of Messaging SAF."
      ::= { serverDebugEntry 241  }
   
   
   serverDebugDebugDRSQueues OBJECT-TYPE
      SYNTAX      OCTET STRING
      MAX-ACCESS  read-only
      STATUS      current
      DESCRIPTION "Debug DRS Queueing traffic."
      ::= { serverDebugEntry 242  }
   
   
   serverDebugDebugDiagnosticInstrumentationActions OBJECT-TYPE
      SYNTAX      OCTET STRING
      MAX-ACCESS  read-only
      STATUS      current
      DESCRIPTION "Debug instrumentation actions/monitors"
      ::= { serverDebugEntry 243  }
   
   
   serverDebugDebugDiagnosticsHarvester OBJECT-TYPE
      SYNTAX      OCTET STRING
      MAX-ACCESS  read-only
      STATUS      current
      DESCRIPTION "Debug diagnostic harvester processing"
      ::= { serverDebugEntry 244  }
   
   
   serverDebugDebugEjbMdbConnection OBJECT-TYPE
      SYNTAX      OCTET STRING
      MAX-ACCESS  read-only
      STATUS      current
      DESCRIPTION "Debug EJB MDB Connection processing"
      ::= { serverDebugEntry 245  }
   
   
   serverDebugDebugJTANaming OBJECT-TYPE
      SYNTAX      OCTET STRING
      MAX-ACCESS  read-only
      STATUS      current
      DESCRIPTION "Debug JTA naming"
      ::= { serverDebugEntry 246  }
   
   
   serverDebugDebugSecuritySSLEaten OBJECT-TYPE
      SYNTAX      OCTET STRING
      MAX-ACCESS  read-only
      STATUS      current
      DESCRIPTION "Debug Security SSL and TLS exception processing"
      ::= { serverDebugEntry 247  }
   
   
   serverDebugDebugEjbTimers OBJECT-TYPE
      SYNTAX      OCTET STRING
      MAX-ACCESS  read-only
      STATUS      current
      DESCRIPTION "Debug EJB Timer processing"
      ::= { serverDebugEntry 248  }
   
   
   serverDebugDebugJMXCore OBJECT-TYPE
      SYNTAX      OCTET STRING
      MAX-ACCESS  read-only
      STATUS      current
      DESCRIPTION "Debug core JMX processing"
      ::= { serverDebugEntry 249  }
   
   
   serverDebugDebugJpaTool OBJECT-TYPE
      SYNTAX      OCTET STRING
      MAX-ACCESS  read-only
      STATUS      current
      DESCRIPTION "Debug JPA tools"
      ::= { serverDebugEntry 250  }
   
   
   serverDebugDebugIIOPNaming OBJECT-TYPE
      SYNTAX      OCTET STRING
      MAX-ACCESS  read-only
      STATUS      current
      DESCRIPTION "Debug IIOP CosNaming processing"
      ::= { serverDebugEntry 251  }
   
   
   serverDebugDebugJTARMI OBJECT-TYPE
      SYNTAX      OCTET STRING
      MAX-ACCESS  read-only
      STATUS      current
      DESCRIPTION "Debug JTA RMI processing"
      ::= { serverDebugEntry 252  }
   
   
   serverDebugDebugJMSFrontEnd OBJECT-TYPE
      SYNTAX      OCTET STRING
      MAX-ACCESS  read-only
      STATUS      current
      DESCRIPTION "Debug JMSFrontEnd processing"
      ::= { serverDebugEntry 253  }
   
   
   serverDebugDebugSecuritySAMLService OBJECT-TYPE
      SYNTAX      OCTET STRING
      MAX-ACCESS  read-only
      STATUS      current
      DESCRIPTION "Debug Security Framework SAML SSO profile services"
      ::= { serverDebugEntry 254  }
   
   
   serverDebugDebugRA OBJECT-TYPE
      SYNTAX      OCTET STRING
      MAX-ACCESS  read-only
      STATUS      current
      DESCRIPTION "Debug Resource Adapter XA general/top-level processing"
      ::= { serverDebugEntry 255  }
   
   
   serverDebugDebugXMLRegistryDebugName OBJECT-TYPE
      SYNTAX      OCTET STRING
      MAX-ACCESS  read-only
      STATUS      current
      DESCRIPTION "XML Registry debugging option: Debug name"
      ::= { serverDebugEntry 256  }
   
   
   serverDebugDebugSelfTuning OBJECT-TYPE
      SYNTAX      OCTET STRING
      MAX-ACCESS  read-only
      STATUS      current
      DESCRIPTION "Debug WorkManager self-tuning processing"
      ::= { serverDebugEntry 257  }
   
   
   serverDebugDebugIIOPMarshal OBJECT-TYPE
      SYNTAX      OCTET STRING
      MAX-ACCESS  read-only
      STATUS      current
      DESCRIPTION "Debug buffer-level IIOP processing"
      ::= { serverDebugEntry 258  }
   
   
   serverDebugDebugSecurityAtz OBJECT-TYPE
      SYNTAX      OCTET STRING
      MAX-ACCESS  read-only
      STATUS      current
      DESCRIPTION "Debug Security Framework Atz processing"
      ::= { serverDebugEntry 259  }
   
   
   serverDebugDebugIIOPOTS OBJECT-TYPE
      SYNTAX      OCTET STRING
      MAX-ACCESS  read-only
      STATUS      current
      DESCRIPTION "Debug IIOP Object Transaction Service (OTS) processing"
      ::= { serverDebugEntry 260  }
   
   
   serverDebugDebugDeployment OBJECT-TYPE
      SYNTAX      OCTET STRING
      MAX-ACCESS  read-only
      STATUS      current
      DESCRIPTION "Debug deployment processing"
      ::= { serverDebugEntry 261  }
   
   
   serverDebugDebugRAWorkEvents OBJECT-TYPE
      SYNTAX      OCTET STRING
      MAX-ACCESS  read-only
      STATUS      current
      DESCRIPTION "Debug Resource Adapter work event processing"
      ::= { serverDebugEntry 262  }
   
   
   serverDebugDebugJTAGateway OBJECT-TYPE
      SYNTAX      OCTET STRING
      MAX-ACCESS  read-only
      STATUS      current
      DESCRIPTION "Debug JTA imported transactions"
      ::= { serverDebugEntry 263  }
   
   
   serverDebugDebugWebAppIdentityAssertion OBJECT-TYPE
      SYNTAX      OCTET STRING
      MAX-ACCESS  read-only
      STATUS      current
      DESCRIPTION "Debug identity assertion flow when identity assertion occurs in the webapp container."
      ::= { serverDebugEntry 264  }
   
   
   serverDebugDebugMuxerConnection OBJECT-TYPE
      SYNTAX      OCTET STRING
      MAX-ACCESS  read-only
      STATUS      current
      DESCRIPTION "Debug Muxer connection processing"
      ::= { serverDebugEntry 265  }
   
   
   serverDebugDebugDiagnosticArchiveRetirement OBJECT-TYPE
      SYNTAX      OCTET STRING
      MAX-ACCESS  read-only
      STATUS      current
      DESCRIPTION "Debug diagnostic archive retirement processing"
      ::= { serverDebugEntry 266  }
   
   
   serverDebugDebugRAPoolVerbose OBJECT-TYPE
      SYNTAX      OCTET STRING
      MAX-ACCESS  read-only
      STATUS      current
      DESCRIPTION "Debug J2EE Resource Adapter pool management (size management) processing"
      ::= { serverDebugEntry 267  }
   
   
   serverDebugDebugStoreIOLogical OBJECT-TYPE
      SYNTAX      OCTET STRING
      MAX-ACCESS  read-only
      STATUS      current
      DESCRIPTION "Debug persistent store high-level logical operations, such as read, write, delete, and update. Multiple logical operations may occur in a single physical operation."
      ::= { serverDebugEntry 268  }
   
   
   serverDebugDebugRAConnections OBJECT-TYPE
      SYNTAX      OCTET STRING
      MAX-ACCESS  read-only
      STATUS      current
      DESCRIPTION "Debug Resource Adapter outbound connection operations (get, close, associate, disassociate, ping)"
      ::= { serverDebugEntry 269  }
   
   
   serverDebugDebugReplicationDetails OBJECT-TYPE
      SYNTAX      OCTET STRING
      MAX-ACCESS  read-only
      STATUS      current
      DESCRIPTION "Debug low-level cluster replication information."
      ::= { serverDebugEntry 270  }
   
   
   serverDebugDebugDiagnosticsHarvesterMBeanPlugin OBJECT-TYPE
      SYNTAX      OCTET STRING
      MAX-ACCESS  read-only
      STATUS      current
      DESCRIPTION "Debug MBean harvester processing. This should probably be used in conjunction with DebugDiagnosticsHarvester."
      ::= { serverDebugEntry 271  }
   
   
   serverDebugDebugRALifecycle OBJECT-TYPE
      SYNTAX      OCTET STRING
      MAX-ACCESS  read-only
      STATUS      current
      DESCRIPTION "Debug ResourceAdapter Lifecycle processing"
      ::= { serverDebugEntry 272  }
   
   
   serverDebugDebugJMSDistTopic OBJECT-TYPE
      SYNTAX      OCTET STRING
      MAX-ACCESS  read-only
      STATUS      current
      DESCRIPTION "Debug JMS Distributed Topic processing"
      ::= { serverDebugEntry 273  }
   
   
   serverDebugDebugDGCEnrollment OBJECT-TYPE
      SYNTAX      OCTET STRING
      MAX-ACCESS  read-only
      STATUS      current
      DESCRIPTION "Debug each DGC enrollment."
      ::= { serverDebugEntry 274  }
   
   
   serverDebugDebugPathSvc OBJECT-TYPE
      SYNTAX      OCTET STRING
      MAX-ACCESS  read-only
      STATUS      current
      DESCRIPTION "Debug the Path Service"
      ::= { serverDebugEntry 275  }
   
   
   serverDebugDebugDiagnosticContext OBJECT-TYPE
      SYNTAX      OCTET STRING
      MAX-ACCESS  read-only
      STATUS      current
      DESCRIPTION "Debug diagnostic context processing "
      ::= { serverDebugEntry 276  }
   
   
   serverFailureTriggerTable OBJECT-TYPE
      SYNTAX      SEQUENCE OF ServerFailureTriggerEntry
      MAX-ACCESS  not-accessible
      STATUS      current
      DESCRIPTION "Configuration to mark the server as failed when threads are stuck. A failed server in turn can be configured to shutdown or go into admin state."
      ::= { wls 1095  }
      
   
   serverFailureTriggerEntry OBJECT-TYPE
      SYNTAX      ServerFailureTriggerEntry
      MAX-ACCESS  not-accessible
      STATUS      current
      DESCRIPTION "Generated SNMP Table Entry."
      INDEX { serverFailureTriggerIndex}
      ::= { serverFailureTriggerTable 1 }
      
   ServerFailureTriggerEntry ::=
      SEQUENCE
      {
         serverFailureTriggerIndex OCTET STRING,
         serverFailureTriggerObjectName OCTET STRING,
         serverFailureTriggerType OCTET STRING,
         serverFailureTriggerMaxStuckThreadTime Integer32,
         serverFailureTriggerStuckThreadCount Integer32,
         serverFailureTriggerName OCTET STRING
      }
      
   
   serverFailureTriggerIndex OBJECT-TYPE
      SYNTAX      OCTET STRING
      MAX-ACCESS  not-accessible
      STATUS      current
      DESCRIPTION "Index column"
      ::= { serverFailureTriggerEntry 1  }
   
   
   serverFailureTriggerObjectName OBJECT-TYPE
      SYNTAX      OCTET STRING
      MAX-ACCESS  read-only
      STATUS      current
      DESCRIPTION "ObjectName column"
      ::= { serverFailureTriggerEntry 2  }
   
   
   serverFailureTriggerType OBJECT-TYPE
      SYNTAX      OCTET STRING
      MAX-ACCESS  read-only
      STATUS      current
      DESCRIPTION "Returns the type of the MBean."
      ::= { serverFailureTriggerEntry 3  }
   
   
   serverFailureTriggerMaxStuckThreadTime OBJECT-TYPE
      SYNTAX      Integer32
      MAX-ACCESS  read-only
      STATUS      current
      DESCRIPTION "The number of seconds that a thread must be continually working before this server diagnoses the thread as being stuck.  For example, if you set this to 600 seconds, WebLogic Server considers a thread to be 'stuck' after 600 seconds of continuous use."
      ::= { serverFailureTriggerEntry 4  }
   
   
   serverFailureTriggerStuckThreadCount OBJECT-TYPE
      SYNTAX      Integer32
      MAX-ACCESS  read-only
      STATUS      current
      DESCRIPTION "The number of stuck threads after which the server is transitioned into FAILED state. There are options in OverloadProtectionMBean to suspend and shutdown a FAILED server. By default, the server continues to run in FAILED state.  If the StuckThreadCount value is set to zero then the server never transitions into FAILED server irrespective of the number of stuck threads."
      ::= { serverFailureTriggerEntry 5  }
   
   
   serverFailureTriggerName OBJECT-TYPE
      SYNTAX      OCTET STRING
      MAX-ACCESS  read-only
      STATUS      current
      DESCRIPTION "The user-specified name of this MBean instance.  This name is included as one of the key properties in the MBean's javax.management.ObjectName: Name=user-specified-name"
      ::= { serverFailureTriggerEntry 6  }
   
   
   shutdownClassTable OBJECT-TYPE
      SYNTAX      SEQUENCE OF ShutdownClassEntry
      MAX-ACCESS  not-accessible
      STATUS      current
      DESCRIPTION "Provides methods for configuring a shutdown class. A shutdown class is a Java program that is automatically loaded and executed when a WebLogic Server instance is shut down gracefully.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1100  }
      
   
   shutdownClassEntry OBJECT-TYPE
      SYNTAX      ShutdownClassEntry
      MAX-ACCESS  not-accessible
      STATUS      current
      DESCRIPTION "Generated SNMP Table Entry."
      INDEX { shutdownClassIndex}
      ::= { shutdownClassTable 1 }
      
   ShutdownClassEntry ::=
      SEQUENCE
      {
         shutdownClassIndex   OCTET STRING,
         shutdownClassObjectName OCTET STRING,
         shutdownClassType    OCTET STRING,
         shutdownClassDeploymentOrder Integer32,
         shutdownClassArguments OCTET STRING,
         shutdownClassName    OCTET STRING,
         shutdownClassClassName OCTET STRING
      }
      
   
   shutdownClassIndex OBJECT-TYPE
      SYNTAX      OCTET STRING
      MAX-ACCESS  not-accessible
      STATUS      current
      DESCRIPTION "Index column"
      ::= { shutdownClassEntry 1  }
   
   
   shutdownClassObjectName OBJECT-TYPE
      SYNTAX      OCTET STRING
      MAX-ACCESS  read-only
      STATUS      current
      DESCRIPTION "ObjectName column"
      ::= { shutdownClassEntry 2  }
   
   
   shutdownClassType OBJECT-TYPE
      SYNTAX      OCTET STRING
      MAX-ACCESS  read-only
      STATUS      current
      DESCRIPTION "Returns the type of the MBean."
      ::= { shutdownClassEntry 3  }
   
   
   shutdownClassDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { shutdownClassEntry 4  }
   
   
   shutdownClassArguments OBJECT-TYPE
      SYNTAX      OCTET STRING
      MAX-ACCESS  read-only
      STATUS      current
      DESCRIPTION "Arguments that a server uses to initialize a class.  Separate multiple arguments with a comma. For example: first=MyFirstName,last=MyLastName"
      ::= { shutdownClassEntry 5  }
   
   
   shutdownClassName OBJECT-TYPE
      SYNTAX      OCTET STRING
      MAX-ACCESS  read-only
      STATUS      current
      DESCRIPTION "The user-specified name of this MBean instance.  This name is included as one of the key properties in the MBean's javax.management.ObjectName: Name=user-specified-name"
      ::= { shutdownClassEntry 6  }
   
   
   shutdownClassClassName OBJECT-TYPE
      SYNTAX      OCTET STRING
      MAX-ACCESS  read-only
      STATUS      current
      DESCRIPTION "The fully qualified name of a class to load and run. The class must be on the server's classpath.  For example, mycompany.mypackage.myclass"
      ::= { shutdownClassEntry 7  }
   
   
   singleSignOnServicesTable OBJECT-TYPE
      SYNTAX      SEQUENCE OF SingleSignOnServicesEntry
      MAX-ACCESS  not-accessible
      STATUS      current
      DESCRIPTION "This MBean represents configuration for SAML 2.0-based local site Single Sign-On Services.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1105  }
      
   
   singleSignOnServicesEntry OBJECT-TYPE
      SYNTAX      SingleSignOnServicesEntry
      MAX-ACCESS  not-accessible
      STATUS      current
      DESCRIPTION "Generated SNMP Table Entry."
      INDEX { singleSignOnServicesIndex}
      ::= { singleSignOnServicesTable 1 }
      
   SingleSignOnServicesEntry ::=
      SEQUENCE
      {
         singleSignOnServicesIndex OCTET STRING,
         singleSignOnServicesObjectName OCTET STRING,
         singleSignOnServicesArtifactMaxCacheSize Integer32,
         singleSignOnServicesIdentityProviderRedirectBindingEnabled OCTET STRING,
         singleSignOnServicesForceAuthn OCTET STRING,
         singleSignOnServicesIdentityProviderPreferredBinding OCTET STRING,
         singleSignOnServicesContactPersonGivenName OCTET STRING,
         singleSignOnServicesWantArtifactRequestsSigned OCTET STRING,
         singleSignOnServicesContactPersonTelephoneNumber OCTET STRING,
         singleSignOnServicesPassive OCTET STRING,
         singleSignOnServicesTransportLayerSecurityKeyAlias OCTET STRING,
         singleSignOnServicesSSOSigningKeyAlias OCTET STRING,
         singleSignOnServicesLoginReturnQueryParameter OCTET STRING,
         singleSignOnServicesAuthnRequestTimeout Integer32,
         singleSignOnServicesPOSTOneUseCheckEnabled OCTET STRING,
         singleSignOnServicesIdentityProviderArtifactBindingEnabled OCTET STRING,
         singleSignOnServicesWantTransportLayerSecurityClientAuthentication OCTET STRING,
         singleSignOnServicesIdentityProviderEnabled OCTET STRING,
         singleSignOnServicesLoginURL OCTET STRING,
         singleSignOnServicesArtifactTimeout Integer32,
         singleSignOnServicesContactPersonType OCTET STRING,
         singleSignOnServicesOrganizationName OCTET STRING,
         singleSignOnServicesDefaultURL OCTET STRING,
         singleSignOnServicesWantBasicAuthClientAuthentication OCTET STRING,
         singleSignOnServicesType OCTET STRING,
         singleSignOnServicesContactPersonEmailAddress OCTET STRING,
         singleSignOnServicesRecipientCheckEnabled OCTET STRING,
         singleSignOnServicesErrorPath OCTET STRING,
         singleSignOnServicesAuthnRequestMaxCacheSize Integer32,
         singleSignOnServicesReplicatedCacheEnabled OCTET STRING,
         singleSignOnServicesServiceProviderEnabled OCTET STRING,
         singleSignOnServicesName OCTET STRING,
         singleSignOnServicesSignAuthnRequests OCTET STRING,
         singleSignOnServicesContactPersonCompany OCTET STRING,
         singleSignOnServicesBasicAuthUsername OCTET STRING,
         singleSignOnServicesServiceProviderPOSTBindingEnabled OCTET STRING,
         singleSignOnServicesEntityID OCTET STRING,
         singleSignOnServicesPublishedSiteURL OCTET STRING,
         singleSignOnServicesOrganizationURL OCTET STRING,
         singleSignOnServicesServiceProviderArtifactBindingEnabled OCTET STRING,
         singleSignOnServicesWantAssertionsSigned OCTET STRING,
         singleSignOnServicesWantAuthnRequestsSigned OCTET STRING,
         singleSignOnServicesServiceProviderPreferredBinding OCTET STRING,
         singleSignOnServicesIdentityProviderPOSTBindingEnabled OCTET STRING,
         singleSignOnServicesContactPersonSurName OCTET STRING
      }
      
   
   singleSignOnServicesIndex OBJECT-TYPE
      SYNTAX      OCTET STRING
      MAX-ACCESS  not-accessible
      STATUS      current
      DESCRIPTION "Index column"
      ::= { singleSignOnServicesEntry 1  }
   
   
   singleSignOnServicesObjectName OBJECT-TYPE
      SYNTAX      OCTET STRING
      MAX-ACCESS  read-only
      STATUS      current
      DESCRIPTION "ObjectName column"
      ::= { singleSignOnServicesEntry 2  }
   
   
   singleSignOnServicesArtifactMaxCacheSize OBJECT-TYPE
      SYNTAX      Integer32
      MAX-ACCESS  read-only
      STATUS      current
      DESCRIPTION "Gets the maximum size of the artifact cache.  This cache is of artifacts issued by the local site that are awaiting referencing by a partner.  Specify '0' to indicate that the cache is unbounded."
      ::= { singleSignOnServicesEntry 3  }
   
   
   singleSignOnServicesIdentityProviderRedirectBindingEnabled OBJECT-TYPE
      SYNTAX      OCTET STRING
      MAX-ACCESS  read-only
      STATUS      current
      DESCRIPTION "Gets the identity provider redirect binding enabled flag"
      ::= { singleSignOnServicesEntry 4  }
   
   
   singleSignOnServicesForceAuthn OBJECT-TYPE
      SYNTAX      OCTET STRING
      MAX-ACCESS  read-only
      STATUS      current
      DESCRIPTION "Gets the force authentication flag"
      ::= { singleSignOnServicesEntry 5  }
   
   
   singleSignOnServicesIdentityProviderPreferredBinding OBJECT-TYPE
      SYNTAX      OCTET STRING
      MAX-ACCESS  read-only
      STATUS      current
      DESCRIPTION "Gets the preferred binding type for endpoints of identity provider services"
      ::= { singleSignOnServicesEntry 6  }
   
   
   singleSignOnServicesContactPersonGivenName OBJECT-TYPE
      SYNTAX      OCTET STRING
      MAX-ACCESS  read-only
      STATUS      current
      DESCRIPTION "Contact person given name."
      ::= { singleSignOnServicesEntry 7  }
   
   
   singleSignOnServicesWantArtifactRequestsSigned OBJECT-TYPE
      SYNTAX      OCTET STRING
      MAX-ACCESS  read-only
      STATUS      current
      DESCRIPTION "Gets the want &lt;AuthnRequest&gt; docuemnts signed flag"
      ::= { singleSignOnServicesEntry 8  }
   
   
   singleSignOnServicesContactPersonTelephoneNumber OBJECT-TYPE
      SYNTAX      OCTET STRING
      MAX-ACCESS  read-only
      STATUS      current
      DESCRIPTION "Contact person telephone number."
      ::= { singleSignOnServicesEntry 9  }
   
   
   singleSignOnServicesPassive OBJECT-TYPE
      SYNTAX      OCTET STRING
      MAX-ACCESS  read-only
      STATUS      current
      DESCRIPTION "Gets the passive flag"
      ::= { singleSignOnServicesEntry 10  }
   
   
   singleSignOnServicesTransportLayerSecurityKeyAlias OBJECT-TYPE
      SYNTAX      OCTET STRING
      MAX-ACCESS  read-only
      STATUS      current
      DESCRIPTION "Get the TLS/SSL key alias.  The key is used to establish outgoing TLS/SSL connections."
      ::= { singleSignOnServicesEntry 11  }
   
   
   singleSignOnServicesSSOSigningKeyAlias OBJECT-TYPE
      SYNTAX      OCTET STRING
      MAX-ACCESS  read-only
      STATUS      current
      DESCRIPTION "Get the SSO Signing key alias.  The key is used to generate signatures on all the outgoing documents, like &lt;AuthnRequest&gt;, &lt;Response&gt;"
      ::= { singleSignOnServicesEntry 12  }
   
   
   singleSignOnServicesLoginReturnQueryParameter OBJECT-TYPE
      SYNTAX      OCTET STRING
      MAX-ACCESS  read-only
      STATUS      current
      DESCRIPTION "Gets the name of the query string parameter to extract from the response following use of Login URL"
      ::= { singleSignOnServicesEntry 13  }
   
   
   singleSignOnServicesAuthnRequestTimeout OBJECT-TYPE
      SYNTAX      Integer32
      MAX-ACCESS  read-only
      STATUS      current
      DESCRIPTION "Gets the maximum timeout (in seconds) of &lt;AuthnRequest&gt; documents stored in the local cache. This cache is of documents issued by the local SP that are awaiting response from a partner IdP.  Documents that reach this maximum timeout age will be expired from the local cache even if no response has yet been received from the partner IdP.  If a reponse is subsequently returned by the partner IdP, the cache will behave as if the &lt;AuthnRequest&gt; had never been generated."
      ::= { singleSignOnServicesEntry 14  }
   
   
   singleSignOnServicesPOSTOneUseCheckEnabled OBJECT-TYPE
      SYNTAX      OCTET STRING
      MAX-ACCESS  read-only
      STATUS      current
      DESCRIPTION "Specifies whether the POST one-use check is enabled."
      ::= { singleSignOnServicesEntry 15  }
   
   
   singleSignOnServicesIdentityProviderArtifactBindingEnabled OBJECT-TYPE
      SYNTAX      OCTET STRING
      MAX-ACCESS  read-only
      STATUS      current
      DESCRIPTION "Gets the identity provider artifact binding enabled flag"
      ::= { singleSignOnServicesEntry 16  }
   
   
   singleSignOnServicesWantTransportLayerSecurityClientAuthentication OBJECT-TYPE
      SYNTAX      OCTET STRING
      MAX-ACCESS  read-only
      STATUS      current
      DESCRIPTION "Gets the want TLS/SSL client authentication flag.  If true, callers to TLS/SSL bindings of the local site must specify client authentication (two-way SSL) and the identity specified must validate against TLS certificate of the binding client partner."
      ::= { singleSignOnServicesEntry 17  }
   
   
   singleSignOnServicesIdentityProviderEnabled OBJECT-TYPE
      SYNTAX      OCTET STRING
      MAX-ACCESS  read-only
      STATUS      current
      DESCRIPTION "Gets the identity provider enabled flag"
      ::= { singleSignOnServicesEntry 18  }
   
   
   singleSignOnServicesLoginURL OBJECT-TYPE
      SYNTAX      OCTET STRING
      MAX-ACCESS  read-only
      STATUS      current
      DESCRIPTION "Gets the Login URL to redirect callers to when IdP receives a request from an anonymous end user."
      ::= { singleSignOnServicesEntry 19  }
   
   
   singleSignOnServicesArtifactTimeout OBJECT-TYPE
      SYNTAX      Integer32
      MAX-ACCESS  read-only
      STATUS      current
      DESCRIPTION "Gets the maximum timeout (in seconds) of artifacts stored in the local cache. This cache is of artifacts issued by the local site that are awaiting referencing by a partner.  Artifacts that reach this maximum timeout age will be expired from the local cache even if no reference request has yet been received from the partner.  If a reference request is subsequently received from the partner, the cache will behave as if the artifact had never been generated."
      ::= { singleSignOnServicesEntry 20  }
   
   
   singleSignOnServicesContactPersonType OBJECT-TYPE
      SYNTAX      OCTET STRING
      MAX-ACCESS  read-only
      STATUS      current
      DESCRIPTION "Contact person type value."
      ::= { singleSignOnServicesEntry 21  }
   
   
   singleSignOnServicesOrganizationName OBJECT-TYPE
      SYNTAX      OCTET STRING
      MAX-ACCESS  read-only
      STATUS      current
      DESCRIPTION "Organization name."
      ::= { singleSignOnServicesEntry 22  }
   
   
   singleSignOnServicesDefaultURL OBJECT-TYPE
      SYNTAX      OCTET STRING
      MAX-ACCESS  read-only
      STATUS      current
      DESCRIPTION "Gets the SP's Default URL.  When an unsolicited SSO response arrives at the SP without an accompanying target URL, the user (if authenticated) is redirected to the default URL."
      ::= { singleSignOnServicesEntry 23  }
   
   
   singleSignOnServicesWantBasicAuthClientAuthentication OBJECT-TYPE
      SYNTAX      OCTET STRING
      MAX-ACCESS  read-only
      STATUS      current
      DESCRIPTION "Gets the want Basic Authentication client authentication flag.  If true, callers to HTTPS bindings of the local site must specify a basic authentication header and the username and password must validate against the basic authetnication values of the binding client partner."
      ::= { singleSignOnServicesEntry 24  }
   
   
   singleSignOnServicesType OBJECT-TYPE
      SYNTAX      OCTET STRING
      MAX-ACCESS  read-only
      STATUS      current
      DESCRIPTION "Returns the type of the MBean."
      ::= { singleSignOnServicesEntry 25  }
   
   
   singleSignOnServicesContactPersonEmailAddress OBJECT-TYPE
      SYNTAX      OCTET STRING
      MAX-ACCESS  read-only
      STATUS      current
      DESCRIPTION "Contact person e-mail address."
      ::= { singleSignOnServicesEntry 26  }
   
   
   singleSignOnServicesRecipientCheckEnabled OBJECT-TYPE
      SYNTAX      OCTET STRING
      MAX-ACCESS  read-only
      STATUS      current
      DESCRIPTION "Specifies whether the recipient/destination check is enabled. When true, the recipient of the SAML Request/Response must match the URL in the HTTP Request."
      ::= { singleSignOnServicesEntry 27  }
   
   
   singleSignOnServicesErrorPath OBJECT-TYPE
      SYNTAX      OCTET STRING
      MAX-ACCESS  read-only
      STATUS      current
      DESCRIPTION "Gets the Error Path URL.  Partner sites may redirect users to this URL for more information if SSO fails."
      ::= { singleSignOnServicesEntry 28  }
   
   
   singleSignOnServicesAuthnRequestMaxCacheSize OBJECT-TYPE
      SYNTAX      Integer32
      MAX-ACCESS  read-only
      STATUS      current
      DESCRIPTION "Gets the maximum size of the &lt;AuthnRequest&gt; document cache.  This cache is of documents issued by the local SP that are awaiting response from a partner IdP.  Specify '0' to indicate that the cache is unbounded."
      ::= { singleSignOnServicesEntry 29  }
   
   
   singleSignOnServicesReplicatedCacheEnabled OBJECT-TYPE
      SYNTAX      OCTET STRING
      MAX-ACCESS  read-only
      STATUS      current
      DESCRIPTION "Gets the Use Replicated Cache flag. If true, persistent cache(LDAP or RDBMS) will be used to store SAML2 artifacts and authentication requests. Otherwise, artifacts and requests will be saved in memory."
      ::= { singleSignOnServicesEntry 30  }
   
   
   singleSignOnServicesServiceProviderEnabled OBJECT-TYPE
      SYNTAX      OCTET STRING
      MAX-ACCESS  read-only
      STATUS      current
      DESCRIPTION "Service provider enabled flag."
      ::= { singleSignOnServicesEntry 31  }
   
   
   singleSignOnServicesName OBJECT-TYPE
      SYNTAX      OCTET STRING
      MAX-ACCESS  read-only
      STATUS      current
      DESCRIPTION "The user-specified name of this MBean instance.  This name is included as one of the key properties in the MBean's javax.management.ObjectName: Name=user-specified-name"
      ::= { singleSignOnServicesEntry 32  }
   
   
   singleSignOnServicesSignAuthnRequests OBJECT-TYPE
      SYNTAX      OCTET STRING
      MAX-ACCESS  read-only
      STATUS      current
      DESCRIPTION "Sign &lt;AuthnRequest&gt; documents flag."
      ::= { singleSignOnServicesEntry 33  }
   
   
   singleSignOnServicesContactPersonCompany OBJECT-TYPE
      SYNTAX      OCTET STRING
      MAX-ACCESS  read-only
      STATUS      current
      DESCRIPTION "Contact person company."
      ::= { singleSignOnServicesEntry 34  }
   
   
   singleSignOnServicesBasicAuthUsername OBJECT-TYPE
      SYNTAX      OCTET STRING
      MAX-ACCESS  read-only
      STATUS      current
      DESCRIPTION "Get the Basic Authentication username.  This username is used to assign Basic Authentication credentials to outgoing HTTPS connections."
      ::= { singleSignOnServicesEntry 35  }
   
   
   singleSignOnServicesServiceProviderPOSTBindingEnabled OBJECT-TYPE
      SYNTAX      OCTET STRING
      MAX-ACCESS  read-only
      STATUS      current
      DESCRIPTION "Gets the service provider POST binding enabled flag"
      ::= { singleSignOnServicesEntry 36  }
   
   
   singleSignOnServicesEntityID OBJECT-TYPE
      SYNTAX      OCTET STRING
      MAX-ACCESS  read-only
      STATUS      current
      DESCRIPTION "Entity ID"
      ::= { singleSignOnServicesEntry 37  }
   
   
   singleSignOnServicesPublishedSiteURL OBJECT-TYPE
      SYNTAX      OCTET STRING
      MAX-ACCESS  read-only
      STATUS      current
      DESCRIPTION "Get the published site URL."
      ::= { singleSignOnServicesEntry 38  }
   
   
   singleSignOnServicesOrganizationURL OBJECT-TYPE
      SYNTAX      OCTET STRING
      MAX-ACCESS  read-only
      STATUS      current
      DESCRIPTION "The Organization URL."
      ::= { singleSignOnServicesEntry 39  }
   
   
   singleSignOnServicesServiceProviderArtifactBindingEnabled OBJECT-TYPE
      SYNTAX      OCTET STRING
      MAX-ACCESS  read-only
      STATUS      current
      DESCRIPTION "Gets the service provider artifact binding enabled flag"
      ::= { singleSignOnServicesEntry 40  }
   
   
   singleSignOnServicesWantAssertionsSigned OBJECT-TYPE
      SYNTAX      OCTET STRING
      MAX-ACCESS  read-only
      STATUS      current
      DESCRIPTION "Advertized flag indicating requirement that incoming assertions be signed"
      ::= { singleSignOnServicesEntry 41  }
   
   
   singleSignOnServicesWantAuthnRequestsSigned OBJECT-TYPE
      SYNTAX      OCTET STRING
      MAX-ACCESS  read-only
      STATUS      current
      DESCRIPTION "Gets the want &lt;AuthnRequest&gt; docuemnts signed flag"
      ::= { singleSignOnServicesEntry 42  }
   
   
   singleSignOnServicesServiceProviderPreferredBinding OBJECT-TYPE
      SYNTAX      OCTET STRING
      MAX-ACCESS  read-only
      STATUS      current
      DESCRIPTION "Gets the preferred binding type for endpoints of service provider services"
      ::= { singleSignOnServicesEntry 43  }
   
   
   singleSignOnServicesIdentityProviderPOSTBindingEnabled OBJECT-TYPE
      SYNTAX      OCTET STRING
      MAX-ACCESS  read-only
      STATUS      current
      DESCRIPTION "Gets the identity provider POST binding enabled flag"
      ::= { singleSignOnServicesEntry 44  }
   
   
   singleSignOnServicesContactPersonSurName OBJECT-TYPE
      SYNTAX      OCTET STRING
      MAX-ACCESS  read-only
      STATUS      current
      DESCRIPTION "Contact person surname."
      ::= { singleSignOnServicesEntry 45  }
   
   
   singletonServiceAppScopedTable OBJECT-TYPE
      SYNTAX      SEQUENCE OF SingletonServiceAppScopedEntry
      MAX-ACCESS  not-accessible
      STATUS      current
      DESCRIPTION "A service that will be automatically maintained as a Singleton in a cluster. There will always be exactly one instance of it active at any given time.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1110  }
      
   
   singletonServiceAppScopedEntry OBJECT-TYPE
      SYNTAX      SingletonServiceAppScopedEntry
      MAX-ACCESS  not-accessible
      STATUS      current
      DESCRIPTION "Generated SNMP Table Entry."
      INDEX { singletonServiceAppScopedIndex}
      ::= { singletonServiceAppScopedTable 1 }
      
   SingletonServiceAppScopedEntry ::=
      SEQUENCE
      {
         singletonServiceAppScopedIndex OCTET STRING,
         singletonServiceAppScopedObjectName OCTET STRING,
         singletonServiceAppScopedType OCTET STRING,
         singletonServiceAppScopedCompatibilityName OCTET STRING,
         singletonServiceAppScopedMillisToSleepBetweenAttempts Integer32,
         singletonServiceAppScopedModuleType OCTET STRING,
         singletonServiceAppScopedName OCTET STRING,
         singletonServiceAppScopedAdditionalMigrationAttempts Integer32,
         singletonServiceAppScopedClassName OCTET STRING
      }
      
   
   singletonServiceAppScopedIndex OBJECT-TYPE
      SYNTAX      OCTET STRING
      MAX-ACCESS  not-accessible
      STATUS      current
      DESCRIPTION "Index column"
      ::= { singletonServiceAppScopedEntry 1  }
   
   
   singletonServiceAppScopedObjectName OBJECT-TYPE
      SYNTAX      OCTET STRING
      MAX-ACCESS  read-only
      STATUS      current
      DESCRIPTION "ObjectName column"
      ::= { singletonServiceAppScopedEntry 2  }
   
   
   singletonServiceAppScopedType OBJECT-TYPE
      SYNTAX      OCTET STRING
      MAX-ACCESS  read-only
      STATUS      current
      DESCRIPTION "Returns the type of the MBean."
      ::= { singletonServiceAppScopedEntry 3  }
   
   
   singletonServiceAppScopedCompatibilityName OBJECT-TYPE
      SYNTAX      OCTET STRING
      MAX-ACCESS  read-only
      STATUS      current
      DESCRIPTION "This is only set for beans created as a result of conversion from an 8.1 application configured using ApplicationMBean and ComponentMBean.  Standalone modules in 8.1 have both an ApplicationMBean name and ComponentMBean name. This attribute stores the name of the latter, to be used when the server creates the transient ComponentMBean for backward compatibility."
      ::= { singletonServiceAppScopedEntry 4  }
   
   
   singletonServiceAppScopedMillisToSleepBetweenAttempts OBJECT-TYPE
      SYNTAX      Integer32
      MAX-ACCESS  read-only
      STATUS      current
      DESCRIPTION "Controls how long of a pause there should be between the migration attempts described in getAdditionalMigrationAttempts(). Note that this delay only happens when the service has failed to come up on every server. It does not cause any sort of delay between attempts to migrate otherwise."
      ::= { singletonServiceAppScopedEntry 5  }
   
   
   singletonServiceAppScopedModuleType OBJECT-TYPE
      SYNTAX      OCTET STRING
      MAX-ACCESS  read-only
      STATUS      current
      DESCRIPTION "The values match those defined by jsr88. This attribute may move to another MBean."
      ::= { singletonServiceAppScopedEntry 6  }
   
   
   singletonServiceAppScopedName OBJECT-TYPE
      SYNTAX      OCTET STRING
      MAX-ACCESS  read-only
      STATUS      current
      DESCRIPTION "Unique identifier for this bean instance. It is used by the application container to match the module in the application package to the targeting information in the configuration.  For modules within an EAR, the name should be the URI of the module as defined in the META-INF/application.xml deployment descriptor. There is an exception to this for web applications. See below. For web modules in an EAR, the name should always equal the context root of that webapp, because the URI is not always unique"
      ::= { singletonServiceAppScopedEntry 7  }
   
   
   singletonServiceAppScopedAdditionalMigrationAttempts OBJECT-TYPE
      SYNTAX      Integer32
      MAX-ACCESS  read-only
      STATUS      current
      DESCRIPTION "A migratable service could fail to come up on every possible configured server. This attribute controls how many further attempts, after the service has failed on every server at least once, should be tried. Note that each attempt specified here indicates another full circut of migrations amongst all the configured servers. So for a 3-server cluster, and a value of 2, a total of 4 additional migrations will be attempted. (the original server is never a valid destination)"
      ::= { singletonServiceAppScopedEntry 8  }
   
   
   singletonServiceAppScopedClassName OBJECT-TYPE
      SYNTAX      OCTET STRING
      MAX-ACCESS  read-only
      STATUS      current
      DESCRIPTION "The fully qualified name of a class to load and run. The class must be on the server's classpath.  For example, mycompany.mypackage.myclass"
      ::= { singletonServiceAppScopedEntry 9  }
   
   
   singletonServiceTable OBJECT-TYPE
      SYNTAX      SEQUENCE OF SingletonServiceEntry
      MAX-ACCESS  not-accessible
      STATUS      current
      DESCRIPTION "A service that will be automatically maintained as a Singleton in a cluster. There will always be exactly one instance of it active at any given time.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1115  }
      
   
   singletonServiceEntry OBJECT-TYPE
      SYNTAX      SingletonServiceEntry
      MAX-ACCESS  not-accessible
      STATUS      current
      DESCRIPTION "Generated SNMP Table Entry."
      INDEX { singletonServiceIndex}
      ::= { singletonServiceTable 1 }
      
   SingletonServiceEntry ::=
      SEQUENCE
      {
         singletonServiceIndex OCTET STRING,
         singletonServiceObjectName OCTET STRING,
         singletonServiceType OCTET STRING,
         singletonServiceMillisToSleepBetweenAttempts Integer32,
         singletonServiceName OCTET STRING,
         singletonServiceAdditionalMigrationAttempts Integer32,
         singletonServiceClassName OCTET STRING
      }
      
   
   singletonServiceIndex OBJECT-TYPE
      SYNTAX      OCTET STRING
      MAX-ACCESS  not-accessible
      STATUS      current
      DESCRIPTION "Index column"
      ::= { singletonServiceEntry 1  }
   
   
   singletonServiceObjectName OBJECT-TYPE
      SYNTAX      OCTET STRING
      MAX-ACCESS  read-only
      STATUS      current
      DESCRIPTION "ObjectName column"
      ::= { singletonServiceEntry 2  }
   
   
   singletonServiceType OBJECT-TYPE
      SYNTAX      OCTET STRING
      MAX-ACCESS  read-only
      STATUS      current
      DESCRIPTION "Returns the type of the MBean."
      ::= { singletonServiceEntry 3  }
   
   
   singletonServiceMillisToSleepBetweenAttempts OBJECT-TYPE
      SYNTAX      Integer32
      MAX-ACCESS  read-only
      STATUS      current
      DESCRIPTION "Controls how long of a pause there should be between the migration attempts described in getAdditionalMigrationAttempts(). Note that this delay only happens when the service has failed to come up on every server. It does not cause any sort of delay between attempts to migrate otherwise."
      ::= { singletonServiceEntry 4  }
   
   
   singletonServiceName OBJECT-TYPE
      SYNTAX      OCTET STRING
      MAX-ACCESS  read-only
      STATUS      current
      DESCRIPTION "The user-specified name of this MBean instance.  This name is included as one of the key properties in the MBean's javax.management.ObjectName: Name=user-specified-name"
      ::= { singletonServiceEntry 5  }
   
   
   singletonServiceAdditionalMigrationAttempts OBJECT-TYPE
      SYNTAX      Integer32
      MAX-ACCESS  read-only
      STATUS      current
      DESCRIPTION "A migratable service could fail to come up on every possible configured server. This attribute controls how many further attempts, after the service has failed on every server at least once, should be tried. Note that each attempt specified here indicates another full circut of migrations amongst all the configured servers. So for a 3-server cluster, and a value of 2, a total of 4 additional migrations will be attempted. (the original server is never a valid destination)"
      ::= { singletonServiceEntry 6  }
   
   
   singletonServiceClassName OBJECT-TYPE
      SYNTAX      OCTET STRING
      MAX-ACCESS  read-only
      STATUS      current
      DESCRIPTION "The fully qualified name of a class to load and run. The class must be on the server's classpath.  For example, mycompany.mypackage.myclass"
      ::= { singletonServiceEntry 7  }
   
   
   stuckThreadActionTable OBJECT-TYPE
      SYNTAX      SEQUENCE OF StuckThreadActionEntry
      MAX-ACCESS  not-accessible
      STATUS      current
      DESCRIPTION "Configuration that deals with handling of stuck threads. Configured actions are executed when the max stuck thread limit is reached. Actions include shutting down the work manager, putting the app in admin mode or marking the server as failed.  This MBean is not directly exposed to JMX clients. It is only used by the console.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1120  }
      
   
   stuckThreadActionEntry OBJECT-TYPE
      SYNTAX      StuckThreadActionEntry
      MAX-ACCESS  not-accessible
      STATUS      current
      DESCRIPTION "Generated SNMP Table Entry."
      INDEX { stuckThreadActionIndex}
      ::= { stuckThreadActionTable 1 }
      
   StuckThreadActionEntry ::=
      SEQUENCE
      {
         stuckThreadActionIndex OCTET STRING,
         stuckThreadActionObjectName OCTET STRING,
         stuckThreadActionType OCTET STRING,
         stuckThreadActionName OCTET STRING
      }
      
   
   stuckThreadActionIndex OBJECT-TYPE
      SYNTAX      OCTET STRING
      MAX-ACCESS  not-accessible
      STATUS      current
      DESCRIPTION "Index column"
      ::= { stuckThreadActionEntry 1  }
   
   
   stuckThreadActionObjectName OBJECT-TYPE
      SYNTAX      OCTET STRING
      MAX-ACCESS  read-only
      STATUS      current
      DESCRIPTION "ObjectName column"
      ::= { stuckThreadActionEntry 2  }
   
   
   stuckThreadActionType OBJECT-TYPE
      SYNTAX      OCTET STRING
      MAX-ACCESS  read-only
      STATUS      current
      DESCRIPTION "Returns the type of the MBean."
      ::= { stuckThreadActionEntry 3  }
   
   
   stuckThreadActionName OBJECT-TYPE
      SYNTAX      OCTET STRING
      MAX-ACCESS  read-only
      STATUS      current
      DESCRIPTION "The user-specified name of this MBean instance.  This name is included as one of the key properties in the MBean's javax.management.ObjectName: Name=user-specified-name"
      ::= { stuckThreadActionEntry 4  }
   
   
   unixMachineTable OBJECT-TYPE
      SYNTAX      SEQUENCE OF UnixMachineEntry
      MAX-ACCESS  not-accessible
      STATUS      current
      DESCRIPTION "This bean represents a machine that is running the UNIX operating system. It extends MachineMBean with properties specific to the UNIX platform."
      ::= { wls 1125  }
      
   
   unixMachineEntry OBJECT-TYPE
      SYNTAX      UnixMachineEntry
      MAX-ACCESS  not-accessible
      STATUS      current
      DESCRIPTION "Generated SNMP Table Entry."
      INDEX { unixMachineIndex}
      ::= { unixMachineTable 1 }
      
   UnixMachineEntry ::=
      SEQUENCE
      {
         unixMachineIndex     OCTET STRING,
         unixMachineObjectName OCTET STRING,
         unixMachineType      OCTET STRING,
         unixMachinePostBindUID OCTET STRING,
         unixMachinePostBindUIDEnabled OCTET STRING,
         unixMachinePostBindGID OCTET STRING,
         unixMachinePostBindGIDEnabled OCTET STRING,
         unixMachineName      OCTET STRING
      }
      
   
   unixMachineIndex OBJECT-TYPE
      SYNTAX      OCTET STRING
      MAX-ACCESS  not-accessible
      STATUS      current
      DESCRIPTION "Index column"
      ::= { unixMachineEntry 1  }
   
   
   unixMachineObjectName OBJECT-TYPE
      SYNTAX      OCTET STRING
      MAX-ACCESS  read-only
      STATUS      current
      DESCRIPTION "ObjectName column"
      ::= { unixMachineEntry 2  }
   
   
   unixMachineType OBJECT-TYPE
      SYNTAX      OCTET STRING
      MAX-ACCESS  read-only
      STATUS      current
      DESCRIPTION "Returns the type of the MBean."
      ::= { unixMachineEntry 3  }
   
   
   unixMachinePostBindUID OBJECT-TYPE
      SYNTAX      OCTET STRING
      MAX-ACCESS  read-only
      STATUS      current
      DESCRIPTION "The UNIX user ID (UID) that a server running on this machine will run under after it has carried out all privileged startup actions. Otherwise, the server will continue to run under the account under which it was started.(Requires that you enable Post-Bind UID.)"
      ::= { unixMachineEntry 4  }
   
   
   unixMachinePostBindUIDEnabled OBJECT-TYPE
      SYNTAX      OCTET STRING
      MAX-ACCESS  read-only
      STATUS      current
      DESCRIPTION "Specifies whether a server running on this machine binds to a UNIX User ID (UID) after it has carried out all privileged startup actions."
      ::= { unixMachineEntry 5  }
   
   
   unixMachinePostBindGID OBJECT-TYPE
      SYNTAX      OCTET STRING
      MAX-ACCESS  read-only
      STATUS      current
      DESCRIPTION "The UNIX group ID (GID) that a server running on this machine will run under after it has carried out all privileged startup actions. Otherwise, the server will continue to run under the group under which it was started.(Requires that you enable Post-Bind GID.)"
      ::= { unixMachineEntry 6  }
   
   
   unixMachinePostBindGIDEnabled OBJECT-TYPE
      SYNTAX      OCTET STRING
      MAX-ACCESS  read-only
      STATUS      current
      DESCRIPTION "Specifies whether a server running on this machine binds to a UNIX Group ID (GID) after it has carried out all privileged startup actions."
      ::= { unixMachineEntry 7  }
   
   
   unixMachineName OBJECT-TYPE
      SYNTAX      OCTET STRING
      MAX-ACCESS  read-only
      STATUS      current
      DESCRIPTION "The user-specified name of this MBean instance.  This name is included as one of the key properties in the MBean's javax.management.ObjectName: Name=user-specified-name"
      ::= { unixMachineEntry 8  }
   
   
   virtualDestinationTable OBJECT-TYPE
      SYNTAX      SEQUENCE OF VirtualDestinationEntry
      MAX-ACCESS  not-accessible
      STATUS      current
      DESCRIPTION "This class represents a virtual destination. In 7.0 JMS has distributed destination, which is a form of the virtual destination.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1130  }
      
   
   virtualDestinationEntry OBJECT-TYPE
      SYNTAX      VirtualDestinationEntry
      MAX-ACCESS  not-accessible
      STATUS      current
      DESCRIPTION "Generated SNMP Table Entry."
      INDEX { virtualDestinationIndex}
      ::= { virtualDestinationTable 1 }
      
   VirtualDestinationEntry ::=
      SEQUENCE
      {
         virtualDestinationIndex OCTET STRING,
         virtualDestinationObjectName OCTET STRING,
         virtualDestinationType OCTET STRING,
         virtualDestinationDeploymentOrder Integer32,
         virtualDestinationJNDIName OCTET STRING,
         virtualDestinationName OCTET STRING
      }
      
   
   virtualDestinationIndex OBJECT-TYPE
      SYNTAX      OCTET STRING
      MAX-ACCESS  not-accessible
      STATUS      current
      DESCRIPTION "Index column"
      ::= { virtualDestinationEntry 1  }
   
   
   virtualDestinationObjectName OBJECT-TYPE
      SYNTAX      OCTET STRING
      MAX-ACCESS  read-only
      STATUS      current
      DESCRIPTION "ObjectName column"
      ::= { virtualDestinationEntry 2  }
   
   
   virtualDestinationType OBJECT-TYPE
      SYNTAX      OCTET STRING
      MAX-ACCESS  read-only
      STATUS      current
      DESCRIPTION "Returns the type of the MBean."
      ::= { virtualDestinationEntry 3  }
   
   
   virtualDestinationDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { virtualDestinationEntry 4  }
   
   
   virtualDestinationJNDIName OBJECT-TYPE
      SYNTAX      OCTET STRING
      MAX-ACCESS  read-only
      STATUS      current
      DESCRIPTION "The JNDI name used to look up a virtual destination within the JNDI namespace. Applications can use the JNDI name to look up the virtual destination. If not specified, then the destination is not bound into the JNDI namespace."
      ::= { virtualDestinationEntry 5  }
   
   
   virtualDestinationName OBJECT-TYPE
      SYNTAX      OCTET STRING
      MAX-ACCESS  read-only
      STATUS      current
      DESCRIPTION "The user-specified name of this MBean instance.  This name is included as one of the key properties in the MBean's javax.management.ObjectName: Name=user-specified-name"
      ::= { virtualDestinationEntry 6  }
   
   
   wldfDataRetirementByAgeTable OBJECT-TYPE
      SYNTAX      SEQUENCE OF WldfDataRetirementByAgeEntry
      MAX-ACCESS  not-accessible
      STATUS      current
      DESCRIPTION "This MBean specifies how data retirement for a WLDF archive will be performed based on the age of records in WLDF archives."
      ::= { wls 1135  }
      
   
   wldfDataRetirementByAgeEntry OBJECT-TYPE
      SYNTAX      WldfDataRetirementByAgeEntry
      MAX-ACCESS  not-accessible
      STATUS      current
      DESCRIPTION "Generated SNMP Table Entry."
      INDEX { wldfDataRetirementByAgeIndex}
      ::= { wldfDataRetirementByAgeTable 1 }
      
   WldfDataRetirementByAgeEntry ::=
      SEQUENCE
      {
         wldfDataRetirementByAgeIndex OCTET STRING,
         wldfDataRetirementByAgeObjectName OCTET STRING,
         wldfDataRetirementByAgeType OCTET STRING,
         wldfDataRetirementByAgeRetirementTime Integer32,
         wldfDataRetirementByAgeRetirementPeriod Integer32,
         wldfDataRetirementByAgeRetirementAge Integer32,
         wldfDataRetirementByAgeEnabled OCTET STRING,
         wldfDataRetirementByAgeArchiveName OCTET STRING,
         wldfDataRetirementByAgeName OCTET STRING
      }
      
   
   wldfDataRetirementByAgeIndex OBJECT-TYPE
      SYNTAX      OCTET STRING
      MAX-ACCESS  not-accessible
      STATUS      current
      DESCRIPTION "Index column"
      ::= { wldfDataRetirementByAgeEntry 1  }
   
   
   wldfDataRetirementByAgeObjectName OBJECT-TYPE
      SYNTAX      OCTET STRING
      MAX-ACCESS  read-only
      STATUS      current
      DESCRIPTION "ObjectName column"
      ::= { wldfDataRetirementByAgeEntry 2  }
   
   
   wldfDataRetirementByAgeType OBJECT-TYPE
      SYNTAX      OCTET STRING
      MAX-ACCESS  read-only
      STATUS      current
      DESCRIPTION "Returns the type of the MBean."
      ::= { wldfDataRetirementByAgeEntry 3  }
   
   
   wldfDataRetirementByAgeRetirementTime OBJECT-TYPE
      SYNTAX      Integer32
      MAX-ACCESS  read-only
      STATUS      current
      DESCRIPTION "This attribute specifies the hour of day at which the the data retirement task will first run during the day."
      ::= { wldfDataRetirementByAgeEntry 4  }
   
   
   wldfDataRetirementByAgeRetirementPeriod OBJECT-TYPE
      SYNTAX      Integer32
      MAX-ACCESS  read-only
      STATUS      current
      DESCRIPTION "This attribute specifies the period in hours at which the data retirement task will be periodically performed for the archive during the day after it is first executed. The value of this attribute must be positive"
      ::= { wldfDataRetirementByAgeEntry 5  }
   
   
   wldfDataRetirementByAgeRetirementAge OBJECT-TYPE
      SYNTAX      Integer32
      MAX-ACCESS  read-only
      STATUS      current
      DESCRIPTION "Retirement age for records in hours. Older records will be eligible for deletion."
      ::= { wldfDataRetirementByAgeEntry 6  }
   
   
   wldfDataRetirementByAgeEnabled OBJECT-TYPE
      SYNTAX      OCTET STRING
      MAX-ACCESS  read-only
      STATUS      current
      DESCRIPTION "Enable data retirement"
      ::= { wldfDataRetirementByAgeEntry 7  }
   
   
   wldfDataRetirementByAgeArchiveName OBJECT-TYPE
      SYNTAX      OCTET STRING
      MAX-ACCESS  read-only
      STATUS      current
      DESCRIPTION "Name of the archive for which data retirement is configured"
      ::= { wldfDataRetirementByAgeEntry 8  }
   
   
   wldfDataRetirementByAgeName OBJECT-TYPE
      SYNTAX      OCTET STRING
      MAX-ACCESS  read-only
      STATUS      current
      DESCRIPTION "The user-specified name of this MBean instance.  This name is included as one of the key properties in the MBean's javax.management.ObjectName: Name=user-specified-name"
      ::= { wldfDataRetirementByAgeEntry 9  }
   
   
   wldfServerDiagnosticTable OBJECT-TYPE
      SYNTAX      SEQUENCE OF WldfServerDiagnosticEntry
      MAX-ACCESS  not-accessible
      STATUS      current
      DESCRIPTION "Use this interface to configure the WebLogic Diagnostic Framework (WLDF) components that are defined for each WebLogic Server instance."
      ::= { wls 1140  }
      
   
   wldfServerDiagnosticEntry OBJECT-TYPE
      SYNTAX      WldfServerDiagnosticEntry
      MAX-ACCESS  not-accessible
      STATUS      current
      DESCRIPTION "Generated SNMP Table Entry."
      INDEX { wldfServerDiagnosticIndex}
      ::= { wldfServerDiagnosticTable 1 }
      
   WldfServerDiagnosticEntry ::=
      SEQUENCE
      {
         wldfServerDiagnosticIndex OCTET STRING,
         wldfServerDiagnosticObjectName OCTET STRING,
         wldfServerDiagnosticType OCTET STRING,
         wldfServerDiagnosticSynchronousEventPersistenceEnabled OCTET STRING,
         wldfServerDiagnosticEventPersistenceInterval Counter64,
         wldfServerDiagnosticPreferredStoreSizeLimit Integer32,
         wldfServerDiagnosticImageTimeout Integer32,
         wldfServerDiagnosticDiagnosticStoreDir OCTET STRING,
         wldfServerDiagnosticDiagnosticDataArchiveType OCTET STRING,
         wldfServerDiagnosticDiagnosticContextEnabled OCTET STRING,
         wldfServerDiagnosticStoreSizeCheckPeriod Integer32,
         wldfServerDiagnosticEventsImageCaptureInterval Counter64,
         wldfServerDiagnosticImageDir OCTET STRING,
         wldfServerDiagnosticDataRetirementEnabled OCTET STRING,
         wldfServerDiagnosticName OCTET STRING
      }
      
   
   wldfServerDiagnosticIndex OBJECT-TYPE
      SYNTAX      OCTET STRING
      MAX-ACCESS  not-accessible
      STATUS      current
      DESCRIPTION "Index column"
      ::= { wldfServerDiagnosticEntry 1  }
   
   
   wldfServerDiagnosticObjectName OBJECT-TYPE
      SYNTAX      OCTET STRING
      MAX-ACCESS  read-only
      STATUS      current
      DESCRIPTION "ObjectName column"
      ::= { wldfServerDiagnosticEntry 2  }
   
   
   wldfServerDiagnosticType OBJECT-TYPE
      SYNTAX      OCTET STRING
      MAX-ACCESS  read-only
      STATUS      current
      DESCRIPTION "Returns the type of the MBean."
      ::= { wldfServerDiagnosticEntry 3  }
   
   
   wldfServerDiagnosticSynchronousEventPersistenceEnabled OBJECT-TYPE
      SYNTAX      OCTET STRING
      MAX-ACCESS  read-only
      STATUS      current
      DESCRIPTION "Specifies the instrumentation events persistence policy. If true, events will be persisted synchronously within the same thread. If false, events will be queued up to be persisted in a separate thread."
      ::= { wldfServerDiagnosticEntry 4  }
   
   
   wldfServerDiagnosticEventPersistenceInterval OBJECT-TYPE
      SYNTAX      Counter64
      MAX-ACCESS  read-only
      STATUS      current
      DESCRIPTION "The interval, in milliseconds, at which queued up instrumentation events will be periodically dispatched to the archive."
      ::= { wldfServerDiagnosticEntry 5  }
   
   
   wldfServerDiagnosticPreferredStoreSizeLimit OBJECT-TYPE
      SYNTAX      Integer32
      MAX-ACCESS  read-only
      STATUS      current
      DESCRIPTION "Return the preferred limit on the size of diagnostic store file in MB."
      ::= { wldfServerDiagnosticEntry 6  }
   
   
   wldfServerDiagnosticImageTimeout OBJECT-TYPE
      SYNTAX      Integer32
      MAX-ACCESS  read-only
      STATUS      current
      DESCRIPTION "The default timeout period, in minutes, that the server uses to delay future diagnostic image-capture requests."
      ::= { wldfServerDiagnosticEntry 7  }
   
   
   wldfServerDiagnosticDiagnosticStoreDir OBJECT-TYPE
      SYNTAX      OCTET STRING
      MAX-ACCESS  read-only
      STATUS      current
      DESCRIPTION "The directory in which the current server maintains its diagnostic store."
      ::= { wldfServerDiagnosticEntry 8  }
   
   
   wldfServerDiagnosticDiagnosticDataArchiveType OBJECT-TYPE
      SYNTAX      OCTET STRING
      MAX-ACCESS  read-only
      STATUS      current
      DESCRIPTION "Determines whether the current server persists its harvested metrics and event data in a diagnostic store (file-based store) or a JDBC based archive. The default store is file-based."
      ::= { wldfServerDiagnosticEntry 9  }
   
   
   wldfServerDiagnosticDiagnosticContextEnabled OBJECT-TYPE
      SYNTAX      OCTET STRING
      MAX-ACCESS  read-only
      STATUS      current
      DESCRIPTION "If true, diagnostic context creation is enabled. If false, the diagnostic context will not be created when requested. However, if the diagnostics context already exists because it was propagated from another VM or was created through the DyeInjection monitor, the context will be made available."
      ::= { wldfServerDiagnosticEntry 10  }
   
   
   wldfServerDiagnosticStoreSizeCheckPeriod OBJECT-TYPE
      SYNTAX      Integer32
      MAX-ACCESS  read-only
      STATUS      current
      DESCRIPTION "Return the period in hours at which diagnostic store file size check will be performed"
      ::= { wldfServerDiagnosticEntry 11  }
   
   
   wldfServerDiagnosticEventsImageCaptureInterval OBJECT-TYPE
      SYNTAX      Counter64
      MAX-ACCESS  read-only
      STATUS      current
      DESCRIPTION "The time span, in milliseconds, for which recently archived events will be captured in the diagnostic image. All events archived on or after ( System.currentTimeMillis() - interval ) will be captured."
      ::= { wldfServerDiagnosticEntry 12  }
   
   
   wldfServerDiagnosticImageDir OBJECT-TYPE
      SYNTAX      OCTET STRING
      MAX-ACCESS  read-only
      STATUS      current
      DESCRIPTION "The default directory where the server stores captured diagnostic images.  If you specify a relative pathname, the root of that path is the server's root directory.  If the directory does not exist, it will be created when the WebLogic Diagnostic Framework is initialized on the server. Note that each image capture request can override this default directory location."
      ::= { wldfServerDiagnosticEntry 13  }
   
   
   wldfServerDiagnosticDataRetirementEnabled OBJECT-TYPE
      SYNTAX      OCTET STRING
      MAX-ACCESS  read-only
      STATUS      current
      DESCRIPTION "This attribute controls if configuration based data retirement functionality is enabled on the server. If disabled, all retirement policies will be disabled."
      ::= { wldfServerDiagnosticEntry 14  }
   
   
   wldfServerDiagnosticName OBJECT-TYPE
      SYNTAX      OCTET STRING
      MAX-ACCESS  read-only
      STATUS      current
      DESCRIPTION "The user-specified name of this MBean instance.  This name is included as one of the key properties in the MBean's javax.management.ObjectName: Name=user-specified-name"
      ::= { wldfServerDiagnosticEntry 15  }
   
   
   wldfSystemResourceTable OBJECT-TYPE
      SYNTAX      SEQUENCE OF WldfSystemResourceEntry
      MAX-ACCESS  not-accessible
      STATUS      current
      DESCRIPTION "This bean defines a system-level WebLogic Diagnostic Framework (WLDF) resource.  It links a separate descriptor that specifies the definition."
      ::= { wls 1145  }
      
   
   wldfSystemResourceEntry OBJECT-TYPE
      SYNTAX      WldfSystemResourceEntry
      MAX-ACCESS  not-accessible
      STATUS      current
      DESCRIPTION "Generated SNMP Table Entry."
      INDEX { wldfSystemResourceIndex}
      ::= { wldfSystemResourceTable 1 }
      
   WldfSystemResourceEntry ::=
      SEQUENCE
      {
         wldfSystemResourceIndex OCTET STRING,
         wldfSystemResourceObjectName OCTET STRING,
         wldfSystemResourceType OCTET STRING,
         wldfSystemResourceCompatibilityName OCTET STRING,
         wldfSystemResourceDeploymentOrder Integer32,
         wldfSystemResourceDeploymentPrincipalName OCTET STRING,
         wldfSystemResourceDescriptorFileName OCTET STRING,
         wldfSystemResourceDescription OCTET STRING,
         wldfSystemResourceModuleType OCTET STRING,
         wldfSystemResourceName OCTET STRING,
         wldfSystemResourceSourcePath OCTET STRING
      }
      
   
   wldfSystemResourceIndex OBJECT-TYPE
      SYNTAX      OCTET STRING
      MAX-ACCESS  not-accessible
      STATUS      current
      DESCRIPTION "Index column"
      ::= { wldfSystemResourceEntry 1  }
   
   
   wldfSystemResourceObjectName OBJECT-TYPE
      SYNTAX      OCTET STRING
      MAX-ACCESS  read-only
      STATUS      current
      DESCRIPTION "ObjectName column"
      ::= { wldfSystemResourceEntry 2  }
   
   
   wldfSystemResourceType OBJECT-TYPE
      SYNTAX      OCTET STRING
      MAX-ACCESS  read-only
      STATUS      current
      DESCRIPTION "Returns the type of the MBean."
      ::= { wldfSystemResourceEntry 3  }
   
   
   wldfSystemResourceCompatibilityName OBJECT-TYPE
      SYNTAX      OCTET STRING
      MAX-ACCESS  read-only
      STATUS      current
      DESCRIPTION "This is only set for beans created as a result of conversion from an 8.1 application configured using ApplicationMBean and ComponentMBean.  Standalone modules in 8.1 have both an ApplicationMBean name and ComponentMBean name. This attribute stores the name of the latter, to be used when the server creates the transient ComponentMBean for backward compatibility."
      ::= { wldfSystemResourceEntry 4  }
   
   
   wldfSystemResourceDeploymentOrder OBJECT-TYPE
      SYNTAX      Integer32
      MAX-ACCESS  read-only
      STATUS      current
      DESCRIPTION "A numerical value that indicates when this unit is deployed, relative to other DeployableUnits on a server, during startup.  Units with lower Load Order values are deployed before those with higher values."
      ::= { wldfSystemResourceEntry 5  }
   
   
   wldfSystemResourceDeploymentPrincipalName OBJECT-TYPE
      SYNTAX      OCTET STRING
      MAX-ACCESS  read-only
      STATUS      current
      DESCRIPTION "A string value that indicates what principal should be used when deploying the file or archive during startup and shutdown. This principal will be used to set the current subject when calling out into application code for interfaces such as ApplicationLifecycleListener, If no principal name is specifed, then the anonymous principal will be used."
      ::= { wldfSystemResourceEntry 6  }
   
   
   wldfSystemResourceDescriptorFileName OBJECT-TYPE
      SYNTAX      OCTET STRING
      MAX-ACCESS  read-only
      STATUS      current
      DESCRIPTION "The name of the descriptor file that contains the XML configuration information for this system-level resource. The location of this file is a relative path rooted at DOMAIN_DIR/config.  By default the file resides in the DOMAIN_DIR/config/diagnostics directory, and derives its name from the bean name using the following pattern:  .xml  Note that the filename is a read-only property, which is set when the WLDF resource is created."
      ::= { wldfSystemResourceEntry 7  }
   
   
   wldfSystemResourceDescription OBJECT-TYPE
      SYNTAX      OCTET STRING
      MAX-ACCESS  read-only
      STATUS      current
      DESCRIPTION "Optional short description of this WLDFSystemResource. If provided, the WebLogic Server Administration Console will display the resource description."
      ::= { wldfSystemResourceEntry 8  }
   
   
   wldfSystemResourceModuleType OBJECT-TYPE
      SYNTAX      OCTET STRING
      MAX-ACCESS  read-only
      STATUS      current
      DESCRIPTION "The values match those defined by jsr88. This attribute may move to another MBean."
      ::= { wldfSystemResourceEntry 9  }
   
   
   wldfSystemResourceName OBJECT-TYPE
      SYNTAX      OCTET STRING
      MAX-ACCESS  read-only
      STATUS      current
      DESCRIPTION "Unique identifier for this bean instance."
      ::= { wldfSystemResourceEntry 10  }
   
   
   wldfSystemResourceSourcePath OBJECT-TYPE
      SYNTAX      OCTET STRING
      MAX-ACCESS  read-only
      STATUS      current
      DESCRIPTION ""
      ::= { wldfSystemResourceEntry 11  }
   
   
   wtcServerTable OBJECT-TYPE
      SYNTAX      SEQUENCE OF WtcServerEntry
      MAX-ACCESS  not-accessible
      STATUS      current
      DESCRIPTION "This MBean defines a WTC Server.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1150  }
      
   
   wtcServerEntry OBJECT-TYPE
      SYNTAX      WtcServerEntry
      MAX-ACCESS  not-accessible
      STATUS      current
      DESCRIPTION "Generated SNMP Table Entry."
      INDEX { wtcServerIndex}
      ::= { wtcServerTable 1 }
      
   WtcServerEntry ::=
      SEQUENCE
      {
         wtcServerIndex       OCTET STRING,
         wtcServerObjectName  OCTET STRING,
         wtcServerType        OCTET STRING,
         wtcServerName        OCTET STRING,
         wtcServerDeploymentOrder Integer32
      }
      
   
   wtcServerIndex OBJECT-TYPE
      SYNTAX      OCTET STRING
      MAX-ACCESS  not-accessible
      STATUS      current
      DESCRIPTION "Index column"
      ::= { wtcServerEntry 1  }
   
   
   wtcServerObjectName OBJECT-TYPE
      SYNTAX      OCTET STRING
      MAX-ACCESS  read-only
      STATUS      current
      DESCRIPTION "ObjectName column"
      ::= { wtcServerEntry 2  }
   
   
   wtcServerType OBJECT-TYPE
      SYNTAX      OCTET STRING
      MAX-ACCESS  read-only
      STATUS      current
      DESCRIPTION "Returns the type of the MBean."
      ::= { wtcServerEntry 3  }
   
   
   wtcServerName OBJECT-TYPE
      SYNTAX      OCTET STRING
      MAX-ACCESS  read-only
      STATUS      current
      DESCRIPTION "The user-specified name of this MBean instance.  This name is included as one of the key properties in the MBean's javax.management.ObjectName: Name=user-specified-name"
      ::= { wtcServerEntry 4  }
   
   
   wtcServerDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { wtcServerEntry 5  }
   
   
   webAppContainerTable OBJECT-TYPE
      SYNTAX      SEQUENCE OF WebAppContainerEntry
      MAX-ACCESS  not-accessible
      STATUS      current
      DESCRIPTION "This MBean is used to specify domain-wide defaults for the WebApp container. In general, these properties can be overridden at the cluster level (in ClusterMBean, if the same property is present there), the server level (in ServerMBean, if the same property is present there) or for a specific Web application (in weblogic.xml).  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1155  }
      
   
   webAppContainerEntry OBJECT-TYPE
      SYNTAX      WebAppContainerEntry
      MAX-ACCESS  not-accessible
      STATUS      current
      DESCRIPTION "Generated SNMP Table Entry."
      INDEX { webAppContainerIndex}
      ::= { webAppContainerTable 1 }
      
   WebAppContainerEntry ::=
      SEQUENCE
      {
         webAppContainerIndex OCTET STRING,
         webAppContainerObjectName OCTET STRING,
         webAppContainerType  OCTET STRING,
         webAppContainerMaxPostSize Integer32,
         webAppContainerXPoweredByHeaderLevel OCTET STRING,
         webAppContainerServletAuthenticationFormURL OCTET STRING,
         webAppContainerReloginEnabled OCTET STRING,
         webAppContainerWorkContextPropagationEnabled OCTET STRING,
         webAppContainerRtexprvalueJspParamName OCTET STRING,
         webAppContainerFilterDispatchedRequestsEnabled OCTET STRING,
         webAppContainerClientCertProxyEnabled OCTET STRING,
         webAppContainerOverloadProtectionEnabled OCTET STRING,
         webAppContainerOptimisticSerialization OCTET STRING,
         webAppContainerRetainOriginalURL OCTET STRING,
         webAppContainerWeblogicPluginEnabled OCTET STRING,
         webAppContainerHttpTraceSupportEnabled OCTET STRING,
         webAppContainerWAPEnabled OCTET STRING,
         webAppContainerJSPCompilerBackwardsCompatible OCTET STRING,
         webAppContainerAuthCookieEnabled OCTET STRING,
         webAppContainerName  OCTET STRING,
         webAppContainerAllowAllRoles OCTET STRING,
         webAppContainerP3PHeaderValue OCTET STRING,
         webAppContainerServletReloadCheckSecs Integer32,
         webAppContainerMaxPostTimeSecs Integer32,
         webAppContainerMimeMappingFile OCTET STRING,
         webAppContainerShowArchivedRealPathEnabled OCTET STRING,
         webAppContainerPostTimeoutSecs Integer32
      }
      
   
   webAppContainerIndex OBJECT-TYPE
      SYNTAX      OCTET STRING
      MAX-ACCESS  not-accessible
      STATUS      current
      DESCRIPTION "Index column"
      ::= { webAppContainerEntry 1  }
   
   
   webAppContainerObjectName OBJECT-TYPE
      SYNTAX      OCTET STRING
      MAX-ACCESS  read-only
      STATUS      current
      DESCRIPTION "ObjectName column"
      ::= { webAppContainerEntry 2  }
   
   
   webAppContainerType OBJECT-TYPE
      SYNTAX      OCTET STRING
      MAX-ACCESS  read-only
      STATUS      current
      DESCRIPTION "Returns the type of the MBean."
      ::= { webAppContainerEntry 3  }
   
   
   webAppContainerMaxPostSize OBJECT-TYPE
      SYNTAX      Integer32
      MAX-ACCESS  read-only
      STATUS      current
      DESCRIPTION "The maximum post size this server allows for reading HTTP POST data in a servlet request. A value less than 0 indicates an unlimited size."
      ::= { webAppContainerEntry 4  }
   
   
   webAppContainerXPoweredByHeaderLevel OBJECT-TYPE
      SYNTAX      OCTET STRING
      MAX-ACCESS  read-only
      STATUS      current
      DESCRIPTION "WebLogic Server uses the X-Powered-By HTTP header, as recommended by the Servlet 2.4 specification, to publish its implementation information.   Following are the options:   'NONE':            X-Powered-By header will not be sent  'SHORT' (default): 'Servlet/2.4 JSP/2.0'   'MEDIUM':          'Servlet/2.4 JSP/2.0 (WebLogic/9.1)'  'FULL':            'Servlet/2.4 JSP/1.2 (WebLogic/9.1 JDK/1.4.1_05)'"
      ::= { webAppContainerEntry 5  }
   
   
   webAppContainerServletAuthenticationFormURL OBJECT-TYPE
      SYNTAX      OCTET STRING
      MAX-ACCESS  read-only
      STATUS      current
      DESCRIPTION "ServletAuthenticationFormURL is used for backward compatibility with previous releases of Weblogic Server.If ServletAuthenticationFormURL is set to true (default), then ServletAuthentication.getTargetURLForFormAuthentication() and HttpSession.getAttribute(AuthFilter.TARGET_URL) will return the URL of the protected target resource. If set to false, the above API's will return the URI of the protected target resource. By default the value is set to true.(new method added in 9.0.0.1)"
      ::= { webAppContainerEntry 6  }
   
   
   webAppContainerReloginEnabled OBJECT-TYPE
      SYNTAX      OCTET STRING
      MAX-ACCESS  read-only
      STATUS      current
      DESCRIPTION "Beginning with the 9.0 release the FORM/BASIC authentication behavior has been modified to conform strictly to the J2EE Specification. If a user has logged-in but does not have privileges to access a resource, the 403 (FORBIDDEN) page will be returned. Turn this flag on to enable the old behavior, which was to return the user to the login form."
      ::= { webAppContainerEntry 7  }
   
   
   webAppContainerWorkContextPropagationEnabled OBJECT-TYPE
      SYNTAX      OCTET STRING
      MAX-ACCESS  read-only
      STATUS      current
      DESCRIPTION "Indicates whether or not WorkContextPropagation is enabled. By default it is turned on. There is a little overhead involved in propagating WorkContexts. Therefore, if you don't care about WorkContext propagation, turn this value off in production environments."
      ::= { webAppContainerEntry 8  }
   
   
   webAppContainerRtexprvalueJspParamName OBJECT-TYPE
      SYNTAX      OCTET STRING
      MAX-ACCESS  read-only
      STATUS      current
      DESCRIPTION "Global property which determines the behavior of the JSP compiler when a jsp:param attribute 'name' has a request time value. Without this property set to 'true', the JSP compiler throws an error for a JSP using a request time value for the 'name' attribute as mandated by the JSP 2.0 spec. This property exists for backward compatibility."
      ::= { webAppContainerEntry 9  }
   
   
   webAppContainerFilterDispatchedRequestsEnabled OBJECT-TYPE
      SYNTAX      OCTET STRING
      MAX-ACCESS  read-only
      STATUS      current
      DESCRIPTION "Indicates whether or not to apply filters to dispatched requests. This is a backward compatibility flag. Until version 8.1, WebLogic Server applied ServletFilters (if configured for the Web application) on request dispatches (and includes/forwards). Servlet 2.4 has introduced the 'Dispatcher' element to make this behavior explicit. The default value is Dispatcher=REQUEST. In order to be complaint with the J2EE specification, the default value for FilterDispatchedRequestsEnabled is false beginning with WebLogic Server 9.0. Note that if you are using old descriptors (meaning web.xml does not have version=2.4), then WebLogic Server automatically uses FilterDispatchedRequestsEnabled = true for the Web applications, unless filter-dispatched-requests-enabled is explicitly set to false in weblogic.xml. This means that old applications will work fine without any modification. Additionally, during migration of old domains to the 9.0 domain, the migration plugin automatically sets this flag to true."
      ::= { webAppContainerEntry 10  }
   
   
   webAppContainerClientCertProxyEnabled OBJECT-TYPE
      SYNTAX      OCTET STRING
      MAX-ACCESS  read-only
      STATUS      current
      DESCRIPTION "Specifies whether or not to honor the WL-Proxy-Client-Cert header coming with the request."
      ::= { webAppContainerEntry 11  }
   
   
   webAppContainerOverloadProtectionEnabled OBJECT-TYPE
      SYNTAX      OCTET STRING
      MAX-ACCESS  read-only
      STATUS      current
      DESCRIPTION "This parameter is used to enable overload protection in the webapp container against low memory conditions. When a low memory situation occurs, new session creation attempts will result in weblogic.servlet.SessionCreationException. The application code needs to catch this exception and take proper action. Alternatively appropriate error-pages can be configured in web.xml against weblogic.servlet.SessionCreationException. This check is performed only on memory and replicated sessions."
      ::= { webAppContainerEntry 12  }
   
   
   webAppContainerOptimisticSerialization OBJECT-TYPE
      SYNTAX      OCTET STRING
      MAX-ACCESS  read-only
      STATUS      current
      DESCRIPTION "When OptimisticSerialization is turned on, WebLogic server does not serialize-deserialize context and request attributes upon getAttribute(name) when a request gets dispatched across servlet contexts. This means you will need to make sure that the attributes common to Web applications are scoped to a common parent classloader (they are application-scoped) or placed in the system classpath if the two Web applications do not belong to the same application. When OptimisticSerialization is turned off (which is the default) WebLogic Server does serialize-deserialize context and request attributes upon getAttribute(name) to avoid the possibility of ClassCastExceptions. The value of OptimisticSerialization can also be overridden for specific Web applications by setting the optimistic-serialization value in weblogic.xml."
      ::= { webAppContainerEntry 13  }
   
   
   webAppContainerRetainOriginalURL OBJECT-TYPE
      SYNTAX      OCTET STRING
      MAX-ACCESS  read-only
      STATUS      current
      DESCRIPTION "retain-original-url is used in FORM based authentication scenarios. When this property is set to true, after a successful authentication, Weblogic Server will redirect back to the web resource (page/servlet) retaining the protocol (http/https) used to access the protected resource in the original request. If set to false (which is the default value), Weblogic Server will redirect back to the protected resource using the current protocol. retain-original-url value can also be specified at per webapp level in weblogic.xml. The value in weblogic.xml, if specified, overrides the domain level value."
      ::= { webAppContainerEntry 14  }
   
   
   webAppContainerWeblogicPluginEnabled OBJECT-TYPE
      SYNTAX      OCTET STRING
      MAX-ACCESS  read-only
      STATUS      current
      DESCRIPTION "Specifies whether or not the proprietary WL-Proxy-Client-IP header should be honored. (This is needed only when WebLogic plugins are configured.)"
      ::= { webAppContainerEntry 15  }
   
   
   webAppContainerHttpTraceSupportEnabled OBJECT-TYPE
      SYNTAX      OCTET STRING
      MAX-ACCESS  read-only
      STATUS      current
      DESCRIPTION "Returns the value of HttpTraceSupportEnabled."
      ::= { webAppContainerEntry 16  }
   
   
   webAppContainerWAPEnabled OBJECT-TYPE
      SYNTAX      OCTET STRING
      MAX-ACCESS  read-only
      STATUS      current
      DESCRIPTION "Indicates whether the session ID should include JVM information. (Checking this box may be necessary when using URL rewriting with WAP devices that limit the size of the URL to 128 characters, and may also affect the use of replicated sessions in a cluster.) When this box is selected, the default size of the URL will be set at 52 characters, and it will not contain any special characters."
      ::= { webAppContainerEntry 17  }
   
   
   webAppContainerJSPCompilerBackwardsCompatible OBJECT-TYPE
      SYNTAX      OCTET STRING
      MAX-ACCESS  read-only
      STATUS      current
      DESCRIPTION "Global property to determine the behavior of the JSP compiler. When this property set to 'true', the JSP compiler throws a translation error for JSPs that do not conform to the JSP2.0 specification. This property exists for backward compatibility."
      ::= { webAppContainerEntry 18  }
   
   
   webAppContainerAuthCookieEnabled OBJECT-TYPE
      SYNTAX      OCTET STRING
      MAX-ACCESS  read-only
      STATUS      current
      DESCRIPTION "Whether authcookie feature is enabled or not."
      ::= { webAppContainerEntry 19  }
   
   
   webAppContainerName OBJECT-TYPE
      SYNTAX      OCTET STRING
      MAX-ACCESS  read-only
      STATUS      current
      DESCRIPTION "The user-specified name of this MBean instance.  This name is included as one of the key properties in the MBean's javax.management.ObjectName: Name=user-specified-name"
      ::= { webAppContainerEntry 20  }
   
   
   webAppContainerAllowAllRoles OBJECT-TYPE
      SYNTAX      OCTET STRING
      MAX-ACCESS  read-only
      STATUS      current
      DESCRIPTION "In the security-constraints elements defined in a Web application's web.xml deployment descriptor, the auth-constraint element indicates the user roles that should be permitted access to this resource collection. Here role-name = '*' is a compact syntax for indicating all roles in the Web application. In previous releases, role-name = '*' was treated as all users/roles defined in the realm.  This parameter is a backward-compatibility switch to restore old behavior. Default behavior is one required by the spec, meaning all roles defined in the web application.  If set, the value defined in weblogic.xml (container-descriptor -> allow-all-roles) takes precedence (if set) over this value."
      ::= { webAppContainerEntry 21  }
   
   
   webAppContainerP3PHeaderValue OBJECT-TYPE
      SYNTAX      OCTET STRING
      MAX-ACCESS  read-only
      STATUS      current
      DESCRIPTION "Returns the P3PHeader value that will be sent with all responses for http requests (if non-null). The value of this header should set to the location of the policy reference file for the Web site.  For details see:  http://www.w3.org/TR/p3pdeployment#Locating_PRF   Alternatively, a servlet filter can be used to set the P3P header."
      ::= { webAppContainerEntry 22  }
   
   
   webAppContainerServletReloadCheckSecs OBJECT-TYPE
      SYNTAX      Integer32
      MAX-ACCESS  read-only
      STATUS      current
      DESCRIPTION ""
      ::= { webAppContainerEntry 23  }
   
   
   webAppContainerMaxPostTimeSecs OBJECT-TYPE
      SYNTAX      Integer32
      MAX-ACCESS  read-only
      STATUS      current
      DESCRIPTION "Max Post Time (in seconds) for reading HTTP POST data in a servlet request. MaxPostTime &lt; 0 means unlimited"
      ::= { webAppContainerEntry 24  }
   
   
   webAppContainerMimeMappingFile OBJECT-TYPE
      SYNTAX      OCTET STRING
      MAX-ACCESS  read-only
      STATUS      current
      DESCRIPTION "Returns the name of the file containing mime-mappings for the domain. Format of the file should be: extension=mime-type   Example:  htm=text/html  gif=image/gif  jpg=image/jpeg   If this file does not exist, WebLogic Server uses an implicit mime-mapping set of mappings defined in weblogic.utils.http.HttpConstants (DEFAULT_MIME_MAPPINGS). To remove a mapping defined in implicit map just set it to blank."
      ::= { webAppContainerEntry 25  }
   
   
   webAppContainerShowArchivedRealPathEnabled OBJECT-TYPE
      SYNTAX      OCTET STRING
      MAX-ACCESS  read-only
      STATUS      current
      DESCRIPTION "Global property to determine the behavior of getRealPath() for archived web applications. When this property set to 'true', getRealPath() will return the canonical path of the resource files."
      ::= { webAppContainerEntry 26  }
   
   
   webAppContainerPostTimeoutSecs OBJECT-TYPE
      SYNTAX      Integer32
      MAX-ACCESS  read-only
      STATUS      current
      DESCRIPTION "The amount of time this server waits between receiving chunks of data in an HTTP POST data before it times out. (This is used to prevent denial-of-service attacks that attempt to overload the server with POST data.)"
      ::= { webAppContainerEntry 27  }
   
   
   webServerLogTable OBJECT-TYPE
      SYNTAX      SEQUENCE OF WebServerLogEntry
      MAX-ACCESS  not-accessible
      STATUS      current
      DESCRIPTION "Aggregates the logging attributes for the WebServerMBean.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1160  }
      
   
   webServerLogEntry OBJECT-TYPE
      SYNTAX      WebServerLogEntry
      MAX-ACCESS  not-accessible
      STATUS      current
      DESCRIPTION "Generated SNMP Table Entry."
      INDEX { webServerLogIndex}
      ::= { webServerLogTable 1 }
      
   WebServerLogEntry ::=
      SEQUENCE
      {
         webServerLogIndex    OCTET STRING,
         webServerLogObjectName OCTET STRING,
         webServerLogType     OCTET STRING,
         webServerLogLogTimeInGMT OCTET STRING,
         webServerLogNumberOfFilesLimited OCTET STRING,
         webServerLogFileTimeSpan Integer32,
         webServerLogLogFileFormat OCTET STRING,
         webServerLogRotationType OCTET STRING,
         webServerLogFileCount Integer32,
         webServerLogLoggingEnabled OCTET STRING,
         webServerLogELFFields OCTET STRING,
         webServerLogFileName OCTET STRING,
         webServerLogFileMinSize Integer32,
         webServerLogBufferSizeKB Integer32,
         webServerLogDateFormatPattern OCTET STRING,
         webServerLogRotationTime OCTET STRING,
         webServerLogRotateLogOnStartup OCTET STRING,
         webServerLogName     OCTET STRING,
         webServerLogLogFileRotationDir OCTET STRING
      }
      
   
   webServerLogIndex OBJECT-TYPE
      SYNTAX      OCTET STRING
      MAX-ACCESS  not-accessible
      STATUS      current
      DESCRIPTION "Index column"
      ::= { webServerLogEntry 1  }
   
   
   webServerLogObjectName OBJECT-TYPE
      SYNTAX      OCTET STRING
      MAX-ACCESS  read-only
      STATUS      current
      DESCRIPTION "ObjectName column"
      ::= { webServerLogEntry 2  }
   
   
   webServerLogType OBJECT-TYPE
      SYNTAX      OCTET STRING
      MAX-ACCESS  read-only
      STATUS      current
      DESCRIPTION "Returns the type of the MBean."
      ::= { webServerLogEntry 3  }
   
   
   webServerLogLogTimeInGMT OBJECT-TYPE
      SYNTAX      OCTET STRING
      MAX-ACCESS  read-only
      STATUS      current
      DESCRIPTION "Specifies whether the time stamps for HTTP log messages are in Greenwich Mean Time (GMT) regardless of the local time zone that the host computer specifies.  Use this method to comply with the W3C specification for Extended Format log files. The specification states that all time stamps for Extended Format log entries be in GMT.  This method applies only if you have specified the extended message format."
      ::= { webServerLogEntry 4  }
   
   
   webServerLogNumberOfFilesLimited OBJECT-TYPE
      SYNTAX      OCTET STRING
      MAX-ACCESS  read-only
      STATUS      current
      DESCRIPTION "Indicates whether to limit the number of log files that this server instance creates to store old messages. (Requires that you specify a file rotation type of SIZE or TIME.)  After the server reaches this limit, it deletes the oldest log file and creates a new log file with the latest suffix.  If you do not enable this option, the server creates new files indefinitely and you must clean up these files as you require."
      ::= { webServerLogEntry 5  }
   
   
   webServerLogFileTimeSpan OBJECT-TYPE
      SYNTAX      Integer32
      MAX-ACCESS  read-only
      STATUS      current
      DESCRIPTION "The interval (in hours) at which the server saves old log messages to another file. (Requires that you specify a file rotation type of TIME.)"
      ::= { webServerLogEntry 6  }
   
   
   webServerLogLogFileFormat OBJECT-TYPE
      SYNTAX      OCTET STRING
      MAX-ACCESS  read-only
      STATUS      current
      DESCRIPTION "The format of the HTTP log file. Both formats are defined by the W3C. With the extended log format, you use server directives in the log file to customize the information that the server records."
      ::= { webServerLogEntry 7  }
   
   
   webServerLogRotationType OBJECT-TYPE
      SYNTAX      OCTET STRING
      MAX-ACCESS  read-only
      STATUS      current
      DESCRIPTION "Criteria for moving old log messages to a separate file.  NONE Messages accumulate in a single file. You must erase the contents of the file when the size is too large. Note that WebLogic Server sets a threshold size limit of 500 MB before it forces a hard rotation to prevent excessive log file growth.  SIZE When the log file reaches the size that you specify in FileMinSize, the server renames the file as FileName.n.  TIME At each time interval that you specify in TimeSpan, the server renames the file as FileName.n.   After the server renames a file, subsequent messages accumulate in a new file with the name that you specified in FileName."
      ::= { webServerLogEntry 8  }
   
   
   webServerLogFileCount OBJECT-TYPE
      SYNTAX      Integer32
      MAX-ACCESS  read-only
      STATUS      current
      DESCRIPTION "The maximum number of log files that the server creates when it rotates the log. This number does not include the file that the server uses to store current messages. (Requires that you enable Number of Files Limited.)"
      ::= { webServerLogEntry 9  }
   
   
   webServerLogLoggingEnabled OBJECT-TYPE
      SYNTAX      OCTET STRING
      MAX-ACCESS  read-only
      STATUS      current
      DESCRIPTION "Indicates whether this server logs HTTP requests. (The remaining fields on this page are relevant only if you select this check box.)  Gets the loggingEnabled attribute of the WebServerMBean object."
      ::= { webServerLogEntry 10  }
   
   
   webServerLogELFFields OBJECT-TYPE
      SYNTAX      OCTET STRING
      MAX-ACCESS  read-only
      STATUS      current
      DESCRIPTION "Returns the list of fields specified for the extended logging format for access.log."
      ::= { webServerLogEntry 11  }
   
   
   webServerLogFileName OBJECT-TYPE
      SYNTAX      OCTET STRING
      MAX-ACCESS  read-only
      STATUS      current
      DESCRIPTION "The name of the log file."
      ::= { webServerLogEntry 12  }
   
   
   webServerLogFileMinSize OBJECT-TYPE
      SYNTAX      Integer32
      MAX-ACCESS  read-only
      STATUS      current
      DESCRIPTION "The size (1 - 65535 kilobytes) that triggers the server to move log messages to a separate file. After the log file reaches the specified minimum size, the next time the server checks the file size, it will rename the current log file as FileName.n and create a new one to store subsequent messages. (Requires that you specify a file rotation type of Size.)"
      ::= { webServerLogEntry 13  }
   
   
   webServerLogBufferSizeKB OBJECT-TYPE
      SYNTAX      Integer32
      MAX-ACCESS  read-only
      STATUS      current
      DESCRIPTION "Gets the underlying log buffer size in kilo bytes"
      ::= { webServerLogEntry 14  }
   
   
   webServerLogDateFormatPattern OBJECT-TYPE
      SYNTAX      OCTET STRING
      MAX-ACCESS  read-only
      STATUS      current
      DESCRIPTION "The date format pattern used for rendering dates in the  log. The DateFormatPattern string conforms to the specification of the java.text.SimpleDateFormat class."
      ::= { webServerLogEntry 15  }
   
   
   webServerLogRotationTime OBJECT-TYPE
      SYNTAX      OCTET STRING
      MAX-ACCESS  read-only
      STATUS      current
      DESCRIPTION "Determines the start time (hour and minute) for a time-based rotation sequence.  At the time that this value specifies, the server renames the current log file. Thereafter, the server renames the log file at an interval that you specify in File Time Span.  If the specified time has already past, then the server starts its file rotation immediately.   Use the following format: k:mm, where k is the hour in a 24-hour format. mm is the minute"
      ::= { webServerLogEntry 16  }
   
   
   webServerLogRotateLogOnStartup OBJECT-TYPE
      SYNTAX      OCTET STRING
      MAX-ACCESS  read-only
      STATUS      current
      DESCRIPTION "Specifies whether a server rotates its log file during its startup cycle."
      ::= { webServerLogEntry 17  }
   
   
   webServerLogName OBJECT-TYPE
      SYNTAX      OCTET STRING
      MAX-ACCESS  read-only
      STATUS      current
      DESCRIPTION "The user-specified name of this MBean instance.  This name is included as one of the key properties in the MBean's javax.management.ObjectName: Name=user-specified-name"
      ::= { webServerLogEntry 18  }
   
   
   webServerLogLogFileRotationDir OBJECT-TYPE
      SYNTAX      OCTET STRING
      MAX-ACCESS  read-only
      STATUS      current
      DESCRIPTION "The directory where the rotated log files will be stored. By default the rotated files are stored in the same directory where the log file is stored."
      ::= { webServerLogEntry 19  }
   
   
   webServiceTable OBJECT-TYPE
      SYNTAX      SEQUENCE OF WebServiceEntry
      MAX-ACCESS  not-accessible
      STATUS      current
      DESCRIPTION "Encapsulates information about a Web Service configuration.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1165  }
      
   
   webServiceEntry OBJECT-TYPE
      SYNTAX      WebServiceEntry
      MAX-ACCESS  not-accessible
      STATUS      current
      DESCRIPTION "Generated SNMP Table Entry."
      INDEX { webServiceIndex}
      ::= { webServiceTable 1 }
      
   WebServiceEntry ::=
      SEQUENCE
      {
         webServiceIndex      OCTET STRING,
         webServiceObjectName OCTET STRING,
         webServiceType       OCTET STRING,
         webServiceMessagingQueueMDBRunAsPrincipalName OCTET STRING,
         webServiceMessagingQueue OCTET STRING,
         webServiceJmsConnectionFactory OCTET STRING,
         webServiceCallbackQueueMDBRunAsPrincipalName OCTET STRING,
         webServiceCallbackQueue OCTET STRING,
         webServiceName       OCTET STRING
      }
      
   
   webServiceIndex OBJECT-TYPE
      SYNTAX      OCTET STRING
      MAX-ACCESS  not-accessible
      STATUS      current
      DESCRIPTION "Index column"
      ::= { webServiceEntry 1  }
   
   
   webServiceObjectName OBJECT-TYPE
      SYNTAX      OCTET STRING
      MAX-ACCESS  read-only
      STATUS      current
      DESCRIPTION "ObjectName column"
      ::= { webServiceEntry 2  }
   
   
   webServiceType OBJECT-TYPE
      SYNTAX      OCTET STRING
      MAX-ACCESS  read-only
      STATUS      current
      DESCRIPTION "Returns the type of the MBean."
      ::= { webServiceEntry 3  }
   
   
   webServiceMessagingQueueMDBRunAsPrincipalName OBJECT-TYPE
      SYNTAX      OCTET STRING
      MAX-ACCESS  read-only
      STATUS      current
      DESCRIPTION ""
      ::= { webServiceEntry 4  }
   
   
   webServiceMessagingQueue OBJECT-TYPE
      SYNTAX      OCTET STRING
      MAX-ACCESS  read-only
      STATUS      current
      DESCRIPTION ""
      ::= { webServiceEntry 5  }
   
   
   webServiceJmsConnectionFactory OBJECT-TYPE
      SYNTAX      OCTET STRING
      MAX-ACCESS  read-only
      STATUS      current
      DESCRIPTION ""
      ::= { webServiceEntry 6  }
   
   
   webServiceCallbackQueueMDBRunAsPrincipalName OBJECT-TYPE
      SYNTAX      OCTET STRING
      MAX-ACCESS  read-only
      STATUS      current
      DESCRIPTION ""
      ::= { webServiceEntry 7  }
   
   
   webServiceCallbackQueue OBJECT-TYPE
      SYNTAX      OCTET STRING
      MAX-ACCESS  read-only
      STATUS      current
      DESCRIPTION ""
      ::= { webServiceEntry 8  }
   
   
   webServiceName OBJECT-TYPE
      SYNTAX      OCTET STRING
      MAX-ACCESS  read-only
      STATUS      current
      DESCRIPTION "The user-specified name of this MBean instance.  This name is included as one of the key properties in the MBean's javax.management.ObjectName: Name=user-specified-name"
      ::= { webServiceEntry 9  }
   
   
   webserviceCredentialProviderTable OBJECT-TYPE
      SYNTAX      SEQUENCE OF WebserviceCredentialProviderEntry
      MAX-ACCESS  not-accessible
      STATUS      current
      DESCRIPTION "Encapsulates information about a particular credential provider that has been configured for a Web Service security configuration.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1170  }
      
   
   webserviceCredentialProviderEntry OBJECT-TYPE
      SYNTAX      WebserviceCredentialProviderEntry
      MAX-ACCESS  not-accessible
      STATUS      current
      DESCRIPTION "Generated SNMP Table Entry."
      INDEX { webserviceCredentialProviderIndex}
      ::= { webserviceCredentialProviderTable 1 }
      
   WebserviceCredentialProviderEntry ::=
      SEQUENCE
      {
         webserviceCredentialProviderIndex OCTET STRING,
         webserviceCredentialProviderObjectName OCTET STRING,
         webserviceCredentialProviderType OCTET STRING,
         webserviceCredentialProviderTokenType OCTET STRING,
         webserviceCredentialProviderName OCTET STRING,
         webserviceCredentialProviderClassName OCTET STRING
      }
      
   
   webserviceCredentialProviderIndex OBJECT-TYPE
      SYNTAX      OCTET STRING
      MAX-ACCESS  not-accessible
      STATUS      current
      DESCRIPTION "Index column"
      ::= { webserviceCredentialProviderEntry 1  }
   
   
   webserviceCredentialProviderObjectName OBJECT-TYPE
      SYNTAX      OCTET STRING
      MAX-ACCESS  read-only
      STATUS      current
      DESCRIPTION "ObjectName column"
      ::= { webserviceCredentialProviderEntry 2  }
   
   
   webserviceCredentialProviderType OBJECT-TYPE
      SYNTAX      OCTET STRING
      MAX-ACCESS  read-only
      STATUS      current
      DESCRIPTION "Returns the type of the MBean."
      ::= { webserviceCredentialProviderEntry 3  }
   
   
   webserviceCredentialProviderTokenType OBJECT-TYPE
      SYNTAX      OCTET STRING
      MAX-ACCESS  read-only
      STATUS      current
      DESCRIPTION "Specifies the type of token used for the particular credential provider or token handler.  WebLogic Server supports, by default, three types of tokens: X.509, UsernameToken, and SAML, as specified by the following WS-Security specifications:  Web Services Security: Username Token Profile Web Services Security: X.509 Token Profile Web Services Security: SAML Token Profile  To specify one of these out-of-the-box types, use these values respectively: 'ut', 'x509', or 'saml'."
      ::= { webserviceCredentialProviderEntry 4  }
   
   
   webserviceCredentialProviderName OBJECT-TYPE
      SYNTAX      OCTET STRING
      MAX-ACCESS  read-only
      STATUS      current
      DESCRIPTION "The user-specified name of this MBean instance.  This name is included as one of the key properties in the MBean's javax.management.ObjectName: Name=user-specified-name"
      ::= { webserviceCredentialProviderEntry 5  }
   
   
   webserviceCredentialProviderClassName OBJECT-TYPE
      SYNTAX      OCTET STRING
      MAX-ACCESS  read-only
      STATUS      current
      DESCRIPTION "The fully qualified name of the class that implements a particular credential provider or token handler."
      ::= { webserviceCredentialProviderEntry 6  }
   
   
   webserviceSecurityTable OBJECT-TYPE
      SYNTAX      SEQUENCE OF WebserviceSecurityEntry
      MAX-ACCESS  not-accessible
      STATUS      current
      DESCRIPTION "Encapsulates information about a Web Service security configuration.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1175  }
      
   
   webserviceSecurityEntry OBJECT-TYPE
      SYNTAX      WebserviceSecurityEntry
      MAX-ACCESS  not-accessible
      STATUS      current
      DESCRIPTION "Generated SNMP Table Entry."
      INDEX { webserviceSecurityIndex}
      ::= { webserviceSecurityTable 1 }
      
   WebserviceSecurityEntry ::=
      SEQUENCE
      {
         webserviceSecurityIndex OCTET STRING,
         webserviceSecurityObjectName OCTET STRING,
         webserviceSecurityType OCTET STRING,
         webserviceSecurityDefaultCredentialProviderSTSURI OCTET STRING,
         webserviceSecurityName OCTET STRING,
         webserviceSecurityPolicySelectionPreference OCTET STRING,
         webserviceSecurityCompatibilityPreference OCTET STRING
      }
      
   
   webserviceSecurityIndex OBJECT-TYPE
      SYNTAX      OCTET STRING
      MAX-ACCESS  not-accessible
      STATUS      current
      DESCRIPTION "Index column"
      ::= { webserviceSecurityEntry 1  }
   
   
   webserviceSecurityObjectName OBJECT-TYPE
      SYNTAX      OCTET STRING
      MAX-ACCESS  read-only
      STATUS      current
      DESCRIPTION "ObjectName column"
      ::= { webserviceSecurityEntry 2  }
   
   
   webserviceSecurityType OBJECT-TYPE
      SYNTAX      OCTET STRING
      MAX-ACCESS  read-only
      STATUS      current
      DESCRIPTION "Returns the type of the MBean."
      ::= { webserviceSecurityEntry 3  }
   
   
   webserviceSecurityDefaultCredentialProviderSTSURI OBJECT-TYPE
      SYNTAX      OCTET STRING
      MAX-ACCESS  read-only
      STATUS      current
      DESCRIPTION "Gets the default STS endpoint URL for all WS-Trust enabled credential providers of this Web Service security configuration."
      ::= { webserviceSecurityEntry 4  }
   
   
   webserviceSecurityName OBJECT-TYPE
      SYNTAX      OCTET STRING
      MAX-ACCESS  read-only
      STATUS      current
      DESCRIPTION "The user-specified name of this MBean instance.  This name is included as one of the key properties in the MBean's javax.management.ObjectName: Name=user-specified-name"
      ::= { webserviceSecurityEntry 5  }
   
   
   webserviceSecurityPolicySelectionPreference OBJECT-TYPE
      SYNTAX      OCTET STRING
      MAX-ACCESS  read-only
      STATUS      current
      DESCRIPTION "Gets the value of the policySelectionPreference attribute.   The preference value can be one of the following:  SCP SPC CSP CPS PCS PSC  Where: S  Security or functionality; C  Compatibility or Interoperability; P  Performance"
      ::= { webserviceSecurityEntry 6  }
   
   
   webserviceSecurityCompatibilityPreference OBJECT-TYPE
      SYNTAX      OCTET STRING
      MAX-ACCESS  read-only
      STATUS      current
      DESCRIPTION "Gets the value of the compatiblityPreference attribute. "
      ::= { webserviceSecurityEntry 7  }
   
   
   webserviceSecurityTokenTable OBJECT-TYPE
      SYNTAX      SEQUENCE OF WebserviceSecurityTokenEntry
      MAX-ACCESS  not-accessible
      STATUS      current
      DESCRIPTION "Encapsulates information about a particular token that has been configured for a Web Service security configuration.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1180  }
      
   
   webserviceSecurityTokenEntry OBJECT-TYPE
      SYNTAX      WebserviceSecurityTokenEntry
      MAX-ACCESS  not-accessible
      STATUS      current
      DESCRIPTION "Generated SNMP Table Entry."
      INDEX { webserviceSecurityTokenIndex}
      ::= { webserviceSecurityTokenTable 1 }
      
   WebserviceSecurityTokenEntry ::=
      SEQUENCE
      {
         webserviceSecurityTokenIndex OCTET STRING,
         webserviceSecurityTokenObjectName OCTET STRING,
         webserviceSecurityTokenType OCTET STRING,
         webserviceSecurityTokenTokenType OCTET STRING,
         webserviceSecurityTokenName OCTET STRING,
         webserviceSecurityTokenClassName OCTET STRING
      }
      
   
   webserviceSecurityTokenIndex OBJECT-TYPE
      SYNTAX      OCTET STRING
      MAX-ACCESS  not-accessible
      STATUS      current
      DESCRIPTION "Index column"
      ::= { webserviceSecurityTokenEntry 1  }
   
   
   webserviceSecurityTokenObjectName OBJECT-TYPE
      SYNTAX      OCTET STRING
      MAX-ACCESS  read-only
      STATUS      current
      DESCRIPTION "ObjectName column"
      ::= { webserviceSecurityTokenEntry 2  }
   
   
   webserviceSecurityTokenType OBJECT-TYPE
      SYNTAX      OCTET STRING
      MAX-ACCESS  read-only
      STATUS      current
      DESCRIPTION "Returns the type of the MBean."
      ::= { webserviceSecurityTokenEntry 3  }
   
   
   webserviceSecurityTokenTokenType OBJECT-TYPE
      SYNTAX      OCTET STRING
      MAX-ACCESS  read-only
      STATUS      current
      DESCRIPTION "Specifies the type of token used for the particular credential provider or token handler.  WebLogic Server supports, by default, three types of tokens: X.509, UsernameToken, and SAML, as specified by the following WS-Security specifications:  Web Services Security: Username Token Profile Web Services Security: X.509 Token Profile Web Services Security: SAML Token Profile  To specify one of these out-of-the-box types, use these values respectively: 'ut', 'x509', or 'saml'."
      ::= { webserviceSecurityTokenEntry 4  }
   
   
   webserviceSecurityTokenName OBJECT-TYPE
      SYNTAX      OCTET STRING
      MAX-ACCESS  read-only
      STATUS      current
      DESCRIPTION "The user-specified name of this MBean instance.  This name is included as one of the key properties in the MBean's javax.management.ObjectName: Name=user-specified-name"
      ::= { webserviceSecurityTokenEntry 5  }
   
   
   webserviceSecurityTokenClassName OBJECT-TYPE
      SYNTAX      OCTET STRING
      MAX-ACCESS  read-only
      STATUS      current
      DESCRIPTION "The fully qualified name of the class that implements a particular credential provider or token handler."
      ::= { webserviceSecurityTokenEntry 6  }
   
   
   webserviceTimestampTable OBJECT-TYPE
      SYNTAX      SEQUENCE OF WebserviceTimestampEntry
      MAX-ACCESS  not-accessible
      STATUS      current
      DESCRIPTION "Encapsulates the timestamp information that is associated with a Web Service security configuration.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1185  }
      
   
   webserviceTimestampEntry OBJECT-TYPE
      SYNTAX      WebserviceTimestampEntry
      MAX-ACCESS  not-accessible
      STATUS      current
      DESCRIPTION "Generated SNMP Table Entry."
      INDEX { webserviceTimestampIndex}
      ::= { webserviceTimestampTable 1 }
      
   WebserviceTimestampEntry ::=
      SEQUENCE
      {
         webserviceTimestampIndex OCTET STRING,
         webserviceTimestampObjectName OCTET STRING,
         webserviceTimestampType OCTET STRING,
         webserviceTimestampMaxProcessingDelay Counter64,
         webserviceTimestampClockSkew Counter64,
         webserviceTimestampClockSynchronized OCTET STRING,
         webserviceTimestampClockPrecision Counter64,
         webserviceTimestampValidityPeriod Integer32,
         webserviceTimestampLaxPrecision OCTET STRING,
         webserviceTimestampName OCTET STRING
      }
      
   
   webserviceTimestampIndex OBJECT-TYPE
      SYNTAX      OCTET STRING
      MAX-ACCESS  not-accessible
      STATUS      current
      DESCRIPTION "Index column"
      ::= { webserviceTimestampEntry 1  }
   
   
   webserviceTimestampObjectName OBJECT-TYPE
      SYNTAX      OCTET STRING
      MAX-ACCESS  read-only
      STATUS      current
      DESCRIPTION "ObjectName column"
      ::= { webserviceTimestampEntry 2  }
   
   
   webserviceTimestampType OBJECT-TYPE
      SYNTAX      OCTET STRING
      MAX-ACCESS  read-only
      STATUS      current
      DESCRIPTION "Returns the type of the MBean."
      ::= { webserviceTimestampEntry 3  }
   
   
   webserviceTimestampMaxProcessingDelay OBJECT-TYPE
      SYNTAX      Counter64
      MAX-ACCESS  read-only
      STATUS      current
      DESCRIPTION "Specifies the freshness policy for received messages: the Web Serivce observes the processing delay by subtracting the Created time in the Timestamp from the current time.  If the observed processing delay is greater than maxProcessingDelay plus clockSkew, then the message is  rejected as stale.  This attribute is specified in milliseconds.  Setting maxProcessingDelay to NO_MAX_PROCESSING_DELAY disables to enforcement of the freshenss policy."
      ::= { webserviceTimestampEntry 4  }
   
   
   webserviceTimestampClockSkew OBJECT-TYPE
      SYNTAX      Counter64
      MAX-ACCESS  read-only
      STATUS      current
      DESCRIPTION "ClockSkew takes precedence over ClockPrecision if both are defined, as ClockPrecision has been DEPRECATED. If clocks are synchronized, this attribute describes the accuracy of the synchronization between two clocks: the client and the server.  ClockSkew is expressed in milliseconds. Clock skew is enforced by rendering all times into milliseconds since a common time 0 and using these times for comparisons. For example, if you're clocks are accurate to within 1 minute of each other, you would set your skew to 1 minute * 60 seconds * 1000 milliseconds or 60000."
      ::= { webserviceTimestampEntry 5  }
   
   
   webserviceTimestampClockSynchronized OBJECT-TYPE
      SYNTAX      OCTET STRING
      MAX-ACCESS  read-only
      STATUS      current
      DESCRIPTION "Specifies whether the Web Service assumes synchronized clocks.  If the clockSynchronized attribute is false, the Web Service rejects all inbound messages with that contain expirations, because this is the only safe way to ensure that the message hasn't already expired. In this case, the Web Service also does not enforce a freshness policy. If this attribute is set to true, then the Web Service enforces expirations on inbound messages to the best of its ability and enforces an optional freshness policy (via maxProcessingDelay).    The default value of this attribute is true."
      ::= { webserviceTimestampEntry 6  }
   
   
   webserviceTimestampClockPrecision OBJECT-TYPE
      SYNTAX      Counter64
      MAX-ACCESS  read-only
      STATUS      current
      DESCRIPTION "DEPRECATED -- Use set/getClockSkew() -- If both ClockSkew and ClockPrecision are defined, then ClockSkew takes precedence and is used. If clocks are synchronized, this attribute describes the accuracy of the synchronization."
      ::= { webserviceTimestampEntry 7  }
   
   
   webserviceTimestampValidityPeriod OBJECT-TYPE
      SYNTAX      Integer32
      MAX-ACCESS  read-only
      STATUS      current
      DESCRIPTION "Represents the length of time the sender wants the outbound message to be valid.   When the validityPeriod is positive, the TimestampHandler inserts an Expires element into the Timestamp header.   The validityPeriod is expressed in seconds:  the Expires time will be that many seconds ahead of the Timestamp's Created time."
      ::= { webserviceTimestampEntry 8  }
   
   
   webserviceTimestampLaxPrecision OBJECT-TYPE
      SYNTAX      OCTET STRING
      MAX-ACCESS  read-only
      STATUS      current
      DESCRIPTION "DEPRECATED."
      ::= { webserviceTimestampEntry 9  }
   
   
   webserviceTimestampName OBJECT-TYPE
      SYNTAX      OCTET STRING
      MAX-ACCESS  read-only
      STATUS      current
      DESCRIPTION "The user-specified name of this MBean instance.  This name is included as one of the key properties in the MBean's javax.management.ObjectName: Name=user-specified-name"
      ::= { webserviceTimestampEntry 10  }
   
   
   webserviceTokenHandlerTable OBJECT-TYPE
      SYNTAX      SEQUENCE OF WebserviceTokenHandlerEntry
      MAX-ACCESS  not-accessible
      STATUS      current
      DESCRIPTION "Encapsulates information about a particular token handler that has been configured for a Web Service security configuration.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1190  }
      
   
   webserviceTokenHandlerEntry OBJECT-TYPE
      SYNTAX      WebserviceTokenHandlerEntry
      MAX-ACCESS  not-accessible
      STATUS      current
      DESCRIPTION "Generated SNMP Table Entry."
      INDEX { webserviceTokenHandlerIndex}
      ::= { webserviceTokenHandlerTable 1 }
      
   WebserviceTokenHandlerEntry ::=
      SEQUENCE
      {
         webserviceTokenHandlerIndex OCTET STRING,
         webserviceTokenHandlerObjectName OCTET STRING,
         webserviceTokenHandlerType OCTET STRING,
         webserviceTokenHandlerHandlingOrder Integer32,
         webserviceTokenHandlerTokenType OCTET STRING,
         webserviceTokenHandlerName OCTET STRING,
         webserviceTokenHandlerClassName OCTET STRING
      }
      
   
   webserviceTokenHandlerIndex OBJECT-TYPE
      SYNTAX      OCTET STRING
      MAX-ACCESS  not-accessible
      STATUS      current
      DESCRIPTION "Index column"
      ::= { webserviceTokenHandlerEntry 1  }
   
   
   webserviceTokenHandlerObjectName OBJECT-TYPE
      SYNTAX      OCTET STRING
      MAX-ACCESS  read-only
      STATUS      current
      DESCRIPTION "ObjectName column"
      ::= { webserviceTokenHandlerEntry 2  }
   
   
   webserviceTokenHandlerType OBJECT-TYPE
      SYNTAX      OCTET STRING
      MAX-ACCESS  read-only
      STATUS      current
      DESCRIPTION "Returns the type of the MBean."
      ::= { webserviceTokenHandlerEntry 3  }
   
   
   webserviceTokenHandlerHandlingOrder OBJECT-TYPE
      SYNTAX      Integer32
      MAX-ACCESS  read-only
      STATUS      current
      DESCRIPTION "Specifies the order in which the token handlers execute on a given token.  If you do not specify an order, it is determined by the order in which you added the token handlers."
      ::= { webserviceTokenHandlerEntry 4  }
   
   
   webserviceTokenHandlerTokenType OBJECT-TYPE
      SYNTAX      OCTET STRING
      MAX-ACCESS  read-only
      STATUS      current
      DESCRIPTION "Specifies the type of token used for the particular credential provider or token handler.  WebLogic Server supports, by default, three types of tokens: X.509, UsernameToken, and SAML, as specified by the following WS-Security specifications:  Web Services Security: Username Token Profile Web Services Security: X.509 Token Profile Web Services Security: SAML Token Profile  To specify one of these out-of-the-box types, use these values respectively: 'ut', 'x509', or 'saml'."
      ::= { webserviceTokenHandlerEntry 5  }
   
   
   webserviceTokenHandlerName OBJECT-TYPE
      SYNTAX      OCTET STRING
      MAX-ACCESS  read-only
      STATUS      current
      DESCRIPTION "The user-specified name of this MBean instance.  This name is included as one of the key properties in the MBean's javax.management.ObjectName: Name=user-specified-name"
      ::= { webserviceTokenHandlerEntry 6  }
   
   
   webserviceTokenHandlerClassName OBJECT-TYPE
      SYNTAX      OCTET STRING
      MAX-ACCESS  read-only
      STATUS      current
      DESCRIPTION "The fully qualified name of the class that implements a particular credential provider or token handler."
      ::= { webserviceTokenHandlerEntry 7  }
   
   
   workManagerTable OBJECT-TYPE
      SYNTAX      SEQUENCE OF WorkManagerEntry
      MAX-ACCESS  not-accessible
      STATUS      current
      DESCRIPTION "Configuration MBean representing WorkManager parameters. A WorkManager configuration can have a RequestClass(FairShare, ResponseTime, ContextBased), MinThreadsConstraint, MaxThreadsConstraint, Capacity and ShutdownTrigger. All these are optional and need to be configured as needed. An empty WorkManager without configuration gets its own default fair share. The default fair share value is 50."
      ::= { wls 1195  }
      
   
   workManagerEntry OBJECT-TYPE
      SYNTAX      WorkManagerEntry
      MAX-ACCESS  not-accessible
      STATUS      current
      DESCRIPTION "Generated SNMP Table Entry."
      INDEX { workManagerIndex}
      ::= { workManagerTable 1 }
      
   WorkManagerEntry ::=
      SEQUENCE
      {
         workManagerIndex     OCTET STRING,
         workManagerObjectName OCTET STRING,
         workManagerType      OCTET STRING,
         workManagerDeploymentOrder Integer32,
         workManagerIgnoreStuckThreads OCTET STRING,
         workManagerName      OCTET STRING
      }
      
   
   workManagerIndex OBJECT-TYPE
      SYNTAX      OCTET STRING
      MAX-ACCESS  not-accessible
      STATUS      current
      DESCRIPTION "Index column"
      ::= { workManagerEntry 1  }
   
   
   workManagerObjectName OBJECT-TYPE
      SYNTAX      OCTET STRING
      MAX-ACCESS  read-only
      STATUS      current
      DESCRIPTION "ObjectName column"
      ::= { workManagerEntry 2  }
   
   
   workManagerType OBJECT-TYPE
      SYNTAX      OCTET STRING
      MAX-ACCESS  read-only
      STATUS      current
      DESCRIPTION "Returns the type of the MBean."
      ::= { workManagerEntry 3  }
   
   
   workManagerDeploymentOrder OBJECT-TYPE
      SYNTAX      Integer32
      MAX-ACCESS  read-only
      STATUS      current
      DESCRIPTION "A priority that the server uses to determine when it deploys an item. The priority is relative to other deployable items of the same type.  For example, the server prioritizes and deploys all EJBs before it prioritizes and deploys startup classes.  Items with the lowest Deployment Order value are deployed first. There is no guarantee on the order of deployments with equal Deployment Order values. There is no guarantee of ordering across clusters."
      ::= { workManagerEntry 4  }
   
   
   workManagerIgnoreStuckThreads OBJECT-TYPE
      SYNTAX      OCTET STRING
      MAX-ACCESS  read-only
      STATUS      current
      DESCRIPTION "Specifies whether this Work Manager ignores 'stuck' threads. Normally stuck threads will cause the associated WorkManager to take some action: either switching the application to admin mode, shutting down the server or shutting down the Work Manager. If this flag is set then no thread in this Work Manager is ever considered stuck."
      ::= { workManagerEntry 5  }
   
   
   workManagerName OBJECT-TYPE
      SYNTAX      OCTET STRING
      MAX-ACCESS  read-only
      STATUS      current
      DESCRIPTION "The user-specified name of this MBean instance.  This name is included as one of the key properties in the MBean's javax.management.ObjectName: Name=user-specified-name"
      ::= { workManagerEntry 6  }
   
   
   workManagerShutdownTriggerTable OBJECT-TYPE
      SYNTAX      SEQUENCE OF WorkManagerShutdownTriggerEntry
      MAX-ACCESS  not-accessible
      STATUS      current
      DESCRIPTION "This MBean is used to configure the trigger that shuts down the WorkManager. The trigger specifies the number of threads that need to be stuck for a certain amount of time for the trigger to shutdown the WorkManager automatically. A shutdown WorkManager refuses new work and completes pending work."
      ::= { wls 1200  }
      
   
   workManagerShutdownTriggerEntry OBJECT-TYPE
      SYNTAX      WorkManagerShutdownTriggerEntry
      MAX-ACCESS  not-accessible
      STATUS      current
      DESCRIPTION "Generated SNMP Table Entry."
      INDEX { workManagerShutdownTriggerIndex}
      ::= { workManagerShutdownTriggerTable 1 }
      
   WorkManagerShutdownTriggerEntry ::=
      SEQUENCE
      {
         workManagerShutdownTriggerIndex OCTET STRING,
         workManagerShutdownTriggerObjectName OCTET STRING,
         workManagerShutdownTriggerType OCTET STRING,
         workManagerShutdownTriggerMaxStuckThreadTime Integer32,
         workManagerShutdownTriggerStuckThreadCount Integer32,
         workManagerShutdownTriggerName OCTET STRING
      }
      
   
   workManagerShutdownTriggerIndex OBJECT-TYPE
      SYNTAX      OCTET STRING
      MAX-ACCESS  not-accessible
      STATUS      current
      DESCRIPTION "Index column"
      ::= { workManagerShutdownTriggerEntry 1  }
   
   
   workManagerShutdownTriggerObjectName OBJECT-TYPE
      SYNTAX      OCTET STRING
      MAX-ACCESS  read-only
      STATUS      current
      DESCRIPTION "ObjectName column"
      ::= { workManagerShutdownTriggerEntry 2  }
   
   
   workManagerShutdownTriggerType OBJECT-TYPE
      SYNTAX      OCTET STRING
      MAX-ACCESS  read-only
      STATUS      current
      DESCRIPTION "Returns the type of the MBean."
      ::= { workManagerShutdownTriggerEntry 3  }
   
   
   workManagerShutdownTriggerMaxStuckThreadTime OBJECT-TYPE
      SYNTAX      Integer32
      MAX-ACCESS  read-only
      STATUS      current
      DESCRIPTION "Time after which a executing thread is declared as stuck."
      ::= { workManagerShutdownTriggerEntry 4  }
   
   
   workManagerShutdownTriggerStuckThreadCount OBJECT-TYPE
      SYNTAX      Integer32
      MAX-ACCESS  read-only
      STATUS      current
      DESCRIPTION "Number of stuck threads after which the WorkManager is shutdown"
      ::= { workManagerShutdownTriggerEntry 5  }
   
   
   workManagerShutdownTriggerName OBJECT-TYPE
      SYNTAX      OCTET STRING
      MAX-ACCESS  read-only
      STATUS      current
      DESCRIPTION "The user-specified name of this MBean instance.  This name is included as one of the key properties in the MBean's javax.management.ObjectName: Name=user-specified-name"
      ::= { workManagerShutdownTriggerEntry 6  }
   
   
   appClientComponentRuntimeTable OBJECT-TYPE
      SYNTAX      SEQUENCE OF AppClientComponentRuntimeEntry
      MAX-ACCESS  not-accessible
      STATUS      current
      DESCRIPTION "This is the ComponentRuntimeMBean for J2EE Application Client Containers.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1205  }
      
   
   appClientComponentRuntimeEntry OBJECT-TYPE
      SYNTAX      AppClientComponentRuntimeEntry
      MAX-ACCESS  not-accessible
      STATUS      current
      DESCRIPTION "Generated SNMP Table Entry."
      INDEX { appClientComponentRuntimeIndex}
      ::= { appClientComponentRuntimeTable 1 }
      
   AppClientComponentRuntimeEntry ::=
      SEQUENCE
      {
         appClientComponentRuntimeIndex OCTET STRING,
         appClientComponentRuntimeObjectName OCTET STRING,
         appClientComponentRuntimeType OCTET STRING,
         appClientComponentRuntimeModuleId OCTET STRING,
         appClientComponentRuntimeDeploymentState Integer32,
         appClientComponentRuntimeName OCTET STRING
      }
      
   
   appClientComponentRuntimeIndex OBJECT-TYPE
      SYNTAX      OCTET STRING
      MAX-ACCESS  not-accessible
      STATUS      current
      DESCRIPTION "Index column"
      ::= { appClientComponentRuntimeEntry 1  }
   
   
   appClientComponentRuntimeObjectName OBJECT-TYPE
      SYNTAX      OCTET STRING
      MAX-ACCESS  read-only
      STATUS      current
      DESCRIPTION "ObjectName column"
      ::= { appClientComponentRuntimeEntry 2  }
   
   
   appClientComponentRuntimeType OBJECT-TYPE
      SYNTAX      OCTET STRING
      MAX-ACCESS  read-only
      STATUS      current
      DESCRIPTION "Returns the type of the MBean."
      ::= { appClientComponentRuntimeEntry 3  }
   
   
   appClientComponentRuntimeModuleId OBJECT-TYPE
      SYNTAX      OCTET STRING
      MAX-ACCESS  read-only
      STATUS      current
      DESCRIPTION "Returns the identifier for this Component.  The identifier is unique within the application.  Typical modules will use the URI for their id.  Web Modules will return their context-root since the web-uri may not be unique within an EAR."
      ::= { appClientComponentRuntimeEntry 4  }
   
   
   appClientComponentRuntimeDeploymentState OBJECT-TYPE
      SYNTAX      Integer32
      MAX-ACCESS  read-only
      STATUS      current
      DESCRIPTION "The current deployment state of the module."
      ::= { appClientComponentRuntimeEntry 5  }
   
   
   appClientComponentRuntimeName OBJECT-TYPE
      SYNTAX      OCTET STRING
      MAX-ACCESS  read-only
      STATUS      current
      DESCRIPTION "The name of this configuration. WebLogic Server uses an MBean to implement and persist the configuration."
      ::= { appClientComponentRuntimeEntry 6  }
   
   
   appRuntimeStateRuntimeTable OBJECT-TYPE
      SYNTAX      SEQUENCE OF AppRuntimeStateRuntimeEntry
      MAX-ACCESS  not-accessible
      STATUS      current
      DESCRIPTION "Provides access to runtime state for deployed applications."
      ::= { wls 1210  }
      
   
   appRuntimeStateRuntimeEntry OBJECT-TYPE
      SYNTAX      AppRuntimeStateRuntimeEntry
      MAX-ACCESS  not-accessible
      STATUS      current
      DESCRIPTION "Generated SNMP Table Entry."
      INDEX { appRuntimeStateRuntimeIndex}
      ::= { appRuntimeStateRuntimeTable 1 }
      
   AppRuntimeStateRuntimeEntry ::=
      SEQUENCE
      {
         appRuntimeStateRuntimeIndex OCTET STRING,
         appRuntimeStateRuntimeObjectName OCTET STRING,
         appRuntimeStateRuntimeType OCTET STRING,
         appRuntimeStateRuntimeName OCTET STRING
      }
      
   
   appRuntimeStateRuntimeIndex OBJECT-TYPE
      SYNTAX      OCTET STRING
      MAX-ACCESS  not-accessible
      STATUS      current
      DESCRIPTION "Index column"
      ::= { appRuntimeStateRuntimeEntry 1  }
   
   
   appRuntimeStateRuntimeObjectName OBJECT-TYPE
      SYNTAX      OCTET STRING
      MAX-ACCESS  read-only
      STATUS      current
      DESCRIPTION "ObjectName column"
      ::= { appRuntimeStateRuntimeEntry 2  }
   
   
   appRuntimeStateRuntimeType OBJECT-TYPE
      SYNTAX      OCTET STRING
      MAX-ACCESS  read-only
      STATUS      current
      DESCRIPTION "Returns the type of the MBean."
      ::= { appRuntimeStateRuntimeEntry 3  }
   
   
   appRuntimeStateRuntimeName OBJECT-TYPE
      SYNTAX      OCTET STRING
      MAX-ACCESS  read-only
      STATUS      current
      DESCRIPTION "The name of this configuration. WebLogic Server uses an MBean to implement and persist the configuration."
      ::= { appRuntimeStateRuntimeEntry 4  }
   
   
   deploymentRequestTaskRuntimeTable OBJECT-TYPE
      SYNTAX      SEQUENCE OF DeploymentRequestTaskRuntimeEntry
      MAX-ACCESS  not-accessible
      STATUS      current
      DESCRIPTION "A DeploymentRequestTaskRuntimeMBean provides a container for tasks that collaborate on a DeploymentService request. These are typically a task tracking the application of a configuration change and one or more tasks that involve deployment [application or system resource] actions. This interface provides an overall status of the deployment request progress. Details such as the completion of the task are however dependent on the completion of the subtasks. DeploymentService requests are handled in 2 phases. The first phase - the 'prepare' phase, involves the validation of the request on each target server. Any failure encountered in this validation results in the failure of the overall request. If all targets validate the request properly, the request is considered to be successful and the admin server triggers the 2nd phase - the 'commit . Note that the 'commit' is triggered at the point when the admin server has already determined the request to be successful even though it has not yet completed."
      ::= { wls 1215  }
      
   
   deploymentRequestTaskRuntimeEntry OBJECT-TYPE
      SYNTAX      DeploymentRequestTaskRuntimeEntry
      MAX-ACCESS  not-accessible
      STATUS      current
      DESCRIPTION "Generated SNMP Table Entry."
      INDEX { deploymentRequestTaskRuntimeIndex}
      ::= { deploymentRequestTaskRuntimeTable 1 }
      
   DeploymentRequestTaskRuntimeEntry ::=
      SEQUENCE
      {
         deploymentRequestTaskRuntimeIndex OCTET STRING,
         deploymentRequestTaskRuntimeObjectName OCTET STRING,
         deploymentRequestTaskRuntimeType OCTET STRING,
         deploymentRequestTaskRuntimeStatus OCTET STRING,
         deploymentRequestTaskRuntimeRunning OCTET STRING,
         deploymentRequestTaskRuntimeBeginTime Counter64,
         deploymentRequestTaskRuntimeEndTime Counter64,
         deploymentRequestTaskRuntimeSystemTask OCTET STRING,
         deploymentRequestTaskRuntimeDescription OCTET STRING,
         deploymentRequestTaskRuntimeName OCTET STRING
      }
      
   
   deploymentRequestTaskRuntimeIndex OBJECT-TYPE
      SYNTAX      OCTET STRING
      MAX-ACCESS  not-accessible
      STATUS      current
      DESCRIPTION "Index column"
      ::= { deploymentRequestTaskRuntimeEntry 1  }
   
   
   deploymentRequestTaskRuntimeObjectName OBJECT-TYPE
      SYNTAX      OCTET STRING
      MAX-ACCESS  read-only
      STATUS      current
      DESCRIPTION "ObjectName column"
      ::= { deploymentRequestTaskRuntimeEntry 2  }
   
   
   deploymentRequestTaskRuntimeType OBJECT-TYPE
      SYNTAX      OCTET STRING
      MAX-ACCESS  read-only
      STATUS      current
      DESCRIPTION "Returns the type of the MBean."
      ::= { deploymentRequestTaskRuntimeEntry 3  }
   
   
   deploymentRequestTaskRuntimeStatus OBJECT-TYPE
      SYNTAX      OCTET STRING
      MAX-ACCESS  read-only
      STATUS      current
      DESCRIPTION "The status of this task."
      ::= { deploymentRequestTaskRuntimeEntry 4  }
   
   
   deploymentRequestTaskRuntimeRunning OBJECT-TYPE
      SYNTAX      OCTET STRING
      MAX-ACCESS  read-only
      STATUS      current
      DESCRIPTION "Indicates whether the task is still running."
      ::= { deploymentRequestTaskRuntimeEntry 5  }
   
   
   deploymentRequestTaskRuntimeBeginTime OBJECT-TYPE
      SYNTAX      Counter64
      MAX-ACCESS  read-only
      STATUS      current
      DESCRIPTION "The time at which this task was started."
      ::= { deploymentRequestTaskRuntimeEntry 6  }
   
   
   deploymentRequestTaskRuntimeEndTime OBJECT-TYPE
      SYNTAX      Counter64
      MAX-ACCESS  read-only
      STATUS      current
      DESCRIPTION "The time at which this task was completed.  A value of -1 indicates that the task is currently running."
      ::= { deploymentRequestTaskRuntimeEntry 7  }
   
   
   deploymentRequestTaskRuntimeSystemTask OBJECT-TYPE
      SYNTAX      OCTET STRING
      MAX-ACCESS  read-only
      STATUS      current
      DESCRIPTION "Indicates whether this task was initiated by the server versus a user."
      ::= { deploymentRequestTaskRuntimeEntry 8  }
   
   
   deploymentRequestTaskRuntimeDescription OBJECT-TYPE
      SYNTAX      OCTET STRING
      MAX-ACCESS  read-only
      STATUS      current
      DESCRIPTION "A description of this task."
      ::= { deploymentRequestTaskRuntimeEntry 9  }
   
   
   deploymentRequestTaskRuntimeName OBJECT-TYPE
      SYNTAX      OCTET STRING
      MAX-ACCESS  read-only
      STATUS      current
      DESCRIPTION "The name of this configuration. WebLogic Server uses an MBean to implement and persist the configuration."
      ::= { deploymentRequestTaskRuntimeEntry 10  }
   
   
   entityEJBRuntimeTable OBJECT-TYPE
      SYNTAX      SEQUENCE OF EntityEJBRuntimeEntry
      MAX-ACCESS  not-accessible
      STATUS      current
      DESCRIPTION "This interface contains accessor methods for all EJB runtime information collected for an Entity Bean.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1220  }
      
   
   entityEJBRuntimeEntry OBJECT-TYPE
      SYNTAX      EntityEJBRuntimeEntry
      MAX-ACCESS  not-accessible
      STATUS      current
      DESCRIPTION "Generated SNMP Table Entry."
      INDEX { entityEJBRuntimeIndex}
      ::= { entityEJBRuntimeTable 1 }
      
   EntityEJBRuntimeEntry ::=
      SEQUENCE
      {
         entityEJBRuntimeIndex OCTET STRING,
         entityEJBRuntimeObjectName OCTET STRING,
         entityEJBRuntimeType OCTET STRING,
         entityEJBRuntimeEJBName OCTET STRING,
         entityEJBRuntimeName OCTET STRING
      }
      
   
   entityEJBRuntimeIndex OBJECT-TYPE
      SYNTAX      OCTET STRING
      MAX-ACCESS  not-accessible
      STATUS      current
      DESCRIPTION "Index column"
      ::= { entityEJBRuntimeEntry 1  }
   
   
   entityEJBRuntimeObjectName OBJECT-TYPE
      SYNTAX      OCTET STRING
      MAX-ACCESS  read-only
      STATUS      current
      DESCRIPTION "ObjectName column"
      ::= { entityEJBRuntimeEntry 2  }
   
   
   entityEJBRuntimeType OBJECT-TYPE
      SYNTAX      OCTET STRING
      MAX-ACCESS  read-only
      STATUS      current
      DESCRIPTION "Returns the type of the MBean."
      ::= { entityEJBRuntimeEntry 3  }
   
   
   entityEJBRuntimeEJBName OBJECT-TYPE
      SYNTAX      OCTET STRING
      MAX-ACCESS  read-only
      STATUS      current
      DESCRIPTION "Provides the ejb-name for this EJB as defined in the ejb-jar.xml deployment descriptor."
      ::= { entityEJBRuntimeEntry 4  }
   
   
   entityEJBRuntimeName OBJECT-TYPE
      SYNTAX      OCTET STRING
      MAX-ACCESS  read-only
      STATUS      current
      DESCRIPTION "The name of this configuration. WebLogic Server uses an MBean to implement and persist the configuration."
      ::= { entityEJBRuntimeEntry 5  }
   
   
   jdbcDataSourceTaskRuntimeTable OBJECT-TYPE
      SYNTAX      SEQUENCE OF JdbcDataSourceTaskRuntimeEntry
      MAX-ACCESS  not-accessible
      STATUS      current
      DESCRIPTION ""
      ::= { wls 1225  }
      
   
   jdbcDataSourceTaskRuntimeEntry OBJECT-TYPE
      SYNTAX      JdbcDataSourceTaskRuntimeEntry
      MAX-ACCESS  not-accessible
      STATUS      current
      DESCRIPTION "Generated SNMP Table Entry."
      INDEX { jdbcDataSourceTaskRuntimeIndex}
      ::= { jdbcDataSourceTaskRuntimeTable 1 }
      
   JdbcDataSourceTaskRuntimeEntry ::=
      SEQUENCE
      {
         jdbcDataSourceTaskRuntimeIndex OCTET STRING,
         jdbcDataSourceTaskRuntimeObjectName OCTET STRING,
         jdbcDataSourceTaskRuntimeType OCTET STRING,
         jdbcDataSourceTaskRuntimeStatus OCTET STRING,
         jdbcDataSourceTaskRuntimeRunning OCTET STRING,
         jdbcDataSourceTaskRuntimeBeginTime Counter64,
         jdbcDataSourceTaskRuntimeEndTime Counter64,
         jdbcDataSourceTaskRuntimeSystemTask OCTET STRING,
         jdbcDataSourceTaskRuntimeDescription OCTET STRING,
         jdbcDataSourceTaskRuntimeName OCTET STRING
      }
      
   
   jdbcDataSourceTaskRuntimeIndex OBJECT-TYPE
      SYNTAX      OCTET STRING
      MAX-ACCESS  not-accessible
      STATUS      current
      DESCRIPTION "Index column"
      ::= { jdbcDataSourceTaskRuntimeEntry 1  }
   
   
   jdbcDataSourceTaskRuntimeObjectName OBJECT-TYPE
      SYNTAX      OCTET STRING
      MAX-ACCESS  read-only
      STATUS      current
      DESCRIPTION "ObjectName column"
      ::= { jdbcDataSourceTaskRuntimeEntry 2  }
   
   
   jdbcDataSourceTaskRuntimeType OBJECT-TYPE
      SYNTAX      OCTET STRING
      MAX-ACCESS  read-only
      STATUS      current
      DESCRIPTION "Returns the type of the MBean."
      ::= { jdbcDataSourceTaskRuntimeEntry 3  }
   
   
   jdbcDataSourceTaskRuntimeStatus OBJECT-TYPE
      SYNTAX      OCTET STRING
      MAX-ACCESS  read-only
      STATUS      current
      DESCRIPTION ""
      ::= { jdbcDataSourceTaskRuntimeEntry 4  }
   
   
   jdbcDataSourceTaskRuntimeRunning OBJECT-TYPE
      SYNTAX      OCTET STRING
      MAX-ACCESS  read-only
      STATUS      current
      DESCRIPTION ""
      ::= { jdbcDataSourceTaskRuntimeEntry 5  }
   
   
   jdbcDataSourceTaskRuntimeBeginTime OBJECT-TYPE
      SYNTAX      Counter64
      MAX-ACCESS  read-only
      STATUS      current
      DESCRIPTION ""
      ::= { jdbcDataSourceTaskRuntimeEntry 6  }
   
   
   jdbcDataSourceTaskRuntimeEndTime OBJECT-TYPE
      SYNTAX      Counter64
      MAX-ACCESS  read-only
      STATUS      current
      DESCRIPTION ""
      ::= { jdbcDataSourceTaskRuntimeEntry 7  }
   
   
   jdbcDataSourceTaskRuntimeSystemTask OBJECT-TYPE
      SYNTAX      OCTET STRING
      MAX-ACCESS  read-only
      STATUS      current
      DESCRIPTION ""
      ::= { jdbcDataSourceTaskRuntimeEntry 8  }
   
   
   jdbcDataSourceTaskRuntimeDescription OBJECT-TYPE
      SYNTAX      OCTET STRING
      MAX-ACCESS  read-only
      STATUS      current
      DESCRIPTION ""
      ::= { jdbcDataSourceTaskRuntimeEntry 9  }
   
   
   jdbcDataSourceTaskRuntimeName OBJECT-TYPE
      SYNTAX      OCTET STRING
      MAX-ACCESS  read-only
      STATUS      current
      DESCRIPTION "The name of this configuration. WebLogic Server uses an MBean to implement and persist the configuration."
      ::= { jdbcDataSourceTaskRuntimeEntry 10  }
   
   
   jdbcDriverRuntimeTable OBJECT-TYPE
      SYNTAX      SEQUENCE OF JdbcDriverRuntimeEntry
      MAX-ACCESS  not-accessible
      STATUS      current
      DESCRIPTION "This class maps to a JDBCDriver JMO  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1230  }
      
   
   jdbcDriverRuntimeEntry OBJECT-TYPE
      SYNTAX      JdbcDriverRuntimeEntry
      MAX-ACCESS  not-accessible
      STATUS      current
      DESCRIPTION "Generated SNMP Table Entry."
      INDEX { jdbcDriverRuntimeIndex}
      ::= { jdbcDriverRuntimeTable 1 }
      
   JdbcDriverRuntimeEntry ::=
      SEQUENCE
      {
         jdbcDriverRuntimeIndex OCTET STRING,
         jdbcDriverRuntimeObjectName OCTET STRING,
         jdbcDriverRuntimeType OCTET STRING,
         jdbcDriverRuntimeName OCTET STRING
      }
      
   
   jdbcDriverRuntimeIndex OBJECT-TYPE
      SYNTAX      OCTET STRING
      MAX-ACCESS  not-accessible
      STATUS      current
      DESCRIPTION "Index column"
      ::= { jdbcDriverRuntimeEntry 1  }
   
   
   jdbcDriverRuntimeObjectName OBJECT-TYPE
      SYNTAX      OCTET STRING
      MAX-ACCESS  read-only
      STATUS      current
      DESCRIPTION "ObjectName column"
      ::= { jdbcDriverRuntimeEntry 2  }
   
   
   jdbcDriverRuntimeType OBJECT-TYPE
      SYNTAX      OCTET STRING
      MAX-ACCESS  read-only
      STATUS      current
      DESCRIPTION "Returns the type of the MBean."
      ::= { jdbcDriverRuntimeEntry 3  }
   
   
   jdbcDriverRuntimeName OBJECT-TYPE
      SYNTAX      OCTET STRING
      MAX-ACCESS  read-only
      STATUS      current
      DESCRIPTION "The name of this configuration. WebLogic Server uses an MBean to implement and persist the configuration."
      ::= { jdbcDriverRuntimeEntry 4  }
   
   
   jdbcMultiDataSourceRuntimeTable OBJECT-TYPE
      SYNTAX      SEQUENCE OF JdbcMultiDataSourceRuntimeEntry
      MAX-ACCESS  not-accessible
      STATUS      current
      DESCRIPTION "This class is used for monitoring a WebLogic JDBC Multi Data Source and its associated data sources."
      ::= { wls 1235  }
      
   
   jdbcMultiDataSourceRuntimeEntry OBJECT-TYPE
      SYNTAX      JdbcMultiDataSourceRuntimeEntry
      MAX-ACCESS  not-accessible
      STATUS      current
      DESCRIPTION "Generated SNMP Table Entry."
      INDEX { jdbcMultiDataSourceRuntimeIndex}
      ::= { jdbcMultiDataSourceRuntimeTable 1 }
      
   JdbcMultiDataSourceRuntimeEntry ::=
      SEQUENCE
      {
         jdbcMultiDataSourceRuntimeIndex OCTET STRING,
         jdbcMultiDataSourceRuntimeObjectName OCTET STRING,
         jdbcMultiDataSourceRuntimeType OCTET STRING,
         jdbcMultiDataSourceRuntimeName OCTET STRING
      }
      
   
   jdbcMultiDataSourceRuntimeIndex OBJECT-TYPE
      SYNTAX      OCTET STRING
      MAX-ACCESS  not-accessible
      STATUS      current
      DESCRIPTION "Index column"
      ::= { jdbcMultiDataSourceRuntimeEntry 1  }
   
   
   jdbcMultiDataSourceRuntimeObjectName OBJECT-TYPE
      SYNTAX      OCTET STRING
      MAX-ACCESS  read-only
      STATUS      current
      DESCRIPTION "ObjectName column"
      ::= { jdbcMultiDataSourceRuntimeEntry 2  }
   
   
   jdbcMultiDataSourceRuntimeType OBJECT-TYPE
      SYNTAX      OCTET STRING
      MAX-ACCESS  read-only
      STATUS      current
      DESCRIPTION "Returns the type of the MBean."
      ::= { jdbcMultiDataSourceRuntimeEntry 3  }
   
   
   jdbcMultiDataSourceRuntimeName OBJECT-TYPE
      SYNTAX      OCTET STRING
      MAX-ACCESS  read-only
      STATUS      current
      DESCRIPTION "The name of this configuration. WebLogic Server uses an MBean to implement and persist the configuration."
      ::= { jdbcMultiDataSourceRuntimeEntry 4  }
   
   
   jdbcServiceRuntimeTable OBJECT-TYPE
      SYNTAX      SEQUENCE OF JdbcServiceRuntimeEntry
      MAX-ACCESS  not-accessible
      STATUS      current
      DESCRIPTION "This class is used for monitoring a WebLogic JDBC service. It maps to a JDBCResource JMO.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1240  }
      
   
   jdbcServiceRuntimeEntry OBJECT-TYPE
      SYNTAX      JdbcServiceRuntimeEntry
      MAX-ACCESS  not-accessible
      STATUS      current
      DESCRIPTION "Generated SNMP Table Entry."
      INDEX { jdbcServiceRuntimeIndex}
      ::= { jdbcServiceRuntimeTable 1 }
      
   JdbcServiceRuntimeEntry ::=
      SEQUENCE
      {
         jdbcServiceRuntimeIndex OCTET STRING,
         jdbcServiceRuntimeObjectName OCTET STRING,
         jdbcServiceRuntimeType OCTET STRING,
         jdbcServiceRuntimeName OCTET STRING
      }
      
   
   jdbcServiceRuntimeIndex OBJECT-TYPE
      SYNTAX      OCTET STRING
      MAX-ACCESS  not-accessible
      STATUS      current
      DESCRIPTION "Index column"
      ::= { jdbcServiceRuntimeEntry 1  }
   
   
   jdbcServiceRuntimeObjectName OBJECT-TYPE
      SYNTAX      OCTET STRING
      MAX-ACCESS  read-only
      STATUS      current
      DESCRIPTION "ObjectName column"
      ::= { jdbcServiceRuntimeEntry 2  }
   
   
   jdbcServiceRuntimeType OBJECT-TYPE
      SYNTAX      OCTET STRING
      MAX-ACCESS  read-only
      STATUS      current
      DESCRIPTION "Returns the type of the MBean."
      ::= { jdbcServiceRuntimeEntry 3  }
   
   
   jdbcServiceRuntimeName OBJECT-TYPE
      SYNTAX      OCTET STRING
      MAX-ACCESS  read-only
      STATUS      current
      DESCRIPTION "The name of this configuration. WebLogic Server uses an MBean to implement and persist the configuration."
      ::= { jdbcServiceRuntimeEntry 4  }
   
   
   jmsRemoteEndpointRuntimeTable OBJECT-TYPE
      SYNTAX      SEQUENCE OF JmsRemoteEndpointRuntimeEntry
      MAX-ACCESS  not-accessible
      STATUS      current
      DESCRIPTION "This class is used for monitoring a WebLogic SAF remote endpoint for a JMS imported destination.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1245  }
      
   
   jmsRemoteEndpointRuntimeEntry OBJECT-TYPE
      SYNTAX      JmsRemoteEndpointRuntimeEntry
      MAX-ACCESS  not-accessible
      STATUS      current
      DESCRIPTION "Generated SNMP Table Entry."
      INDEX { jmsRemoteEndpointRuntimeIndex}
      ::= { jmsRemoteEndpointRuntimeTable 1 }
      
   JmsRemoteEndpointRuntimeEntry ::=
      SEQUENCE
      {
         jmsRemoteEndpointRuntimeIndex OCTET STRING,
         jmsRemoteEndpointRuntimeObjectName OCTET STRING,
         jmsRemoteEndpointRuntimeType OCTET STRING,
         jmsRemoteEndpointRuntimeUptimeTotal Counter64,
         jmsRemoteEndpointRuntimeMessagesCurrentCount Counter64,
         jmsRemoteEndpointRuntimeDowntimeTotal Counter64,
         jmsRemoteEndpointRuntimeBytesReceivedCount Counter64,
         jmsRemoteEndpointRuntimeEndpointType OCTET STRING,
         jmsRemoteEndpointRuntimeFailedMessagesTotal Counter64,
         jmsRemoteEndpointRuntimeMessagesReceivedCount Counter64,
         jmsRemoteEndpointRuntimeURL OCTET STRING,
         jmsRemoteEndpointRuntimePausedForIncoming OCTET STRING,
         jmsRemoteEndpointRuntimeName OCTET STRING,
         jmsRemoteEndpointRuntimeBytesHighCount Counter64,
         jmsRemoteEndpointRuntimeUptimeHigh Counter64,
         jmsRemoteEndpointRuntimeBytesCurrentCount Counter64,
         jmsRemoteEndpointRuntimeMessagesPendingCount Counter64,
         jmsRemoteEndpointRuntimeDowntimeHigh Counter64,
         jmsRemoteEndpointRuntimeBytesThresholdTime Counter64,
         jmsRemoteEndpointRuntimeBytesPendingCount Counter64,
         jmsRemoteEndpointRuntimePausedForForwarding OCTET STRING,
         jmsRemoteEndpointRuntimeMessagesThresholdTime Counter64,
         jmsRemoteEndpointRuntimeMessagesHighCount Counter64,
         jmsRemoteEndpointRuntimeOperationState OCTET STRING
      }
      
   
   jmsRemoteEndpointRuntimeIndex OBJECT-TYPE
      SYNTAX      OCTET STRING
      MAX-ACCESS  not-accessible
      STATUS      current
      DESCRIPTION "Index column"
      ::= { jmsRemoteEndpointRuntimeEntry 1  }
   
   
   jmsRemoteEndpointRuntimeObjectName OBJECT-TYPE
      SYNTAX      OCTET STRING
      MAX-ACCESS  read-only
      STATUS      current
      DESCRIPTION "ObjectName column"
      ::= { jmsRemoteEndpointRuntimeEntry 2  }
   
   
   jmsRemoteEndpointRuntimeType OBJECT-TYPE
      SYNTAX      OCTET STRING
      MAX-ACCESS  read-only
      STATUS      current
      DESCRIPTION "Returns the type of the MBean."
      ::= { jmsRemoteEndpointRuntimeEntry 3  }
   
   
   jmsRemoteEndpointRuntimeUptimeTotal OBJECT-TYPE
      SYNTAX      Counter64
      MAX-ACCESS  read-only
      STATUS      current
      DESCRIPTION "Specifies the total time, in seconds, that the remote endpoint has been available since the last reset."
      ::= { jmsRemoteEndpointRuntimeEntry 4  }
   
   
   jmsRemoteEndpointRuntimeMessagesCurrentCount OBJECT-TYPE
      SYNTAX      Counter64
      MAX-ACCESS  read-only
      STATUS      current
      DESCRIPTION "Returns the current number of messages. This number includes the pending messages."
      ::= { jmsRemoteEndpointRuntimeEntry 5  }
   
   
   jmsRemoteEndpointRuntimeDowntimeTotal OBJECT-TYPE
      SYNTAX      Counter64
      MAX-ACCESS  read-only
      STATUS      current
      DESCRIPTION "Specifies the total time, in seconds, that the remote endpoint has not been available since the last reset."
      ::= { jmsRemoteEndpointRuntimeEntry 6  }
   
   
   jmsRemoteEndpointRuntimeBytesReceivedCount OBJECT-TYPE
      SYNTAX      Counter64
      MAX-ACCESS  read-only
      STATUS      current
      DESCRIPTION "The number of bytes received since the last reset."
      ::= { jmsRemoteEndpointRuntimeEntry 7  }
   
   
   jmsRemoteEndpointRuntimeEndpointType OBJECT-TYPE
      SYNTAX      OCTET STRING
      MAX-ACCESS  read-only
      STATUS      current
      DESCRIPTION "Specifies if the remote endpoint is a JMS or WSRM destination."
      ::= { jmsRemoteEndpointRuntimeEntry 8  }
   
   
   jmsRemoteEndpointRuntimeFailedMessagesTotal OBJECT-TYPE
      SYNTAX      Counter64
      MAX-ACCESS  read-only
      STATUS      current
      DESCRIPTION "Returns the total number of messages that have failed to be forwarded since the last reset."
      ::= { jmsRemoteEndpointRuntimeEntry 9  }
   
   
   jmsRemoteEndpointRuntimeMessagesReceivedCount OBJECT-TYPE
      SYNTAX      Counter64
      MAX-ACCESS  read-only
      STATUS      current
      DESCRIPTION "The number of messages received since the last reset."
      ::= { jmsRemoteEndpointRuntimeEntry 10  }
   
   
   jmsRemoteEndpointRuntimeURL OBJECT-TYPE
      SYNTAX      OCTET STRING
      MAX-ACCESS  read-only
      STATUS      current
      DESCRIPTION "The URL of the remote endpoint."
      ::= { jmsRemoteEndpointRuntimeEntry 11  }
   
   
   jmsRemoteEndpointRuntimePausedForIncoming OBJECT-TYPE
      SYNTAX      OCTET STRING
      MAX-ACCESS  read-only
      STATUS      current
      DESCRIPTION "Indicates if a remote endpoint is currently not accepting new messages."
      ::= { jmsRemoteEndpointRuntimeEntry 12  }
   
   
   jmsRemoteEndpointRuntimeName OBJECT-TYPE
      SYNTAX      OCTET STRING
      MAX-ACCESS  read-only
      STATUS      current
      DESCRIPTION "The name of this configuration. WebLogic Server uses an MBean to implement and persist the configuration."
      ::= { jmsRemoteEndpointRuntimeEntry 13  }
   
   
   jmsRemoteEndpointRuntimeBytesHighCount OBJECT-TYPE
      SYNTAX      Counter64
      MAX-ACCESS  read-only
      STATUS      current
      DESCRIPTION "Returns the peak number of bytes since the last reset."
      ::= { jmsRemoteEndpointRuntimeEntry 14  }
   
   
   jmsRemoteEndpointRuntimeUptimeHigh OBJECT-TYPE
      SYNTAX      Counter64
      MAX-ACCESS  read-only
      STATUS      current
      DESCRIPTION "Specifies the longest time, in seconds, that the remote endpoint has been available since the last reset."
      ::= { jmsRemoteEndpointRuntimeEntry 15  }
   
   
   jmsRemoteEndpointRuntimeBytesCurrentCount OBJECT-TYPE
      SYNTAX      Counter64
      MAX-ACCESS  read-only
      STATUS      current
      DESCRIPTION "Returns the current number of bytes. This number does not include the pending bytes."
      ::= { jmsRemoteEndpointRuntimeEntry 16  }
   
   
   jmsRemoteEndpointRuntimeMessagesPendingCount OBJECT-TYPE
      SYNTAX      Counter64
      MAX-ACCESS  read-only
      STATUS      current
      DESCRIPTION "Returns the number of pending messages. Pending messages are over and above the current number of messages. A pending message is one that has either been sent in a transaction and not committed, or been forwarded but has not been acknowledged."
      ::= { jmsRemoteEndpointRuntimeEntry 17  }
   
   
   jmsRemoteEndpointRuntimeDowntimeHigh OBJECT-TYPE
      SYNTAX      Counter64
      MAX-ACCESS  read-only
      STATUS      current
      DESCRIPTION "Specifies the longest time, in seconds, that the remote endpoint has not been available since the last reset."
      ::= { jmsRemoteEndpointRuntimeEntry 18  }
   
   
   jmsRemoteEndpointRuntimeBytesThresholdTime OBJECT-TYPE
      SYNTAX      Counter64
      MAX-ACCESS  read-only
      STATUS      current
      DESCRIPTION "Returns the amount of time in the threshold condition since the last reset."
      ::= { jmsRemoteEndpointRuntimeEntry 19  }
   
   
   jmsRemoteEndpointRuntimeBytesPendingCount OBJECT-TYPE
      SYNTAX      Counter64
      MAX-ACCESS  read-only
      STATUS      current
      DESCRIPTION "Returns the number of pending bytes. Pending bytes are over and above the current number of bytes."
      ::= { jmsRemoteEndpointRuntimeEntry 20  }
   
   
   jmsRemoteEndpointRuntimePausedForForwarding OBJECT-TYPE
      SYNTAX      OCTET STRING
      MAX-ACCESS  read-only
      STATUS      current
      DESCRIPTION "Indicates if the remote endpoint is currently not forwarding messages."
      ::= { jmsRemoteEndpointRuntimeEntry 21  }
   
   
   jmsRemoteEndpointRuntimeMessagesThresholdTime OBJECT-TYPE
      SYNTAX      Counter64
      MAX-ACCESS  read-only
      STATUS      current
      DESCRIPTION "Returns the amount of time in the threshold condition since the last reset."
      ::= { jmsRemoteEndpointRuntimeEntry 22  }
   
   
   jmsRemoteEndpointRuntimeMessagesHighCount OBJECT-TYPE
      SYNTAX      Counter64
      MAX-ACCESS  read-only
      STATUS      current
      DESCRIPTION "Returns the peak number of messages since the last reset."
      ::= { jmsRemoteEndpointRuntimeEntry 23  }
   
   
   jmsRemoteEndpointRuntimeOperationState OBJECT-TYPE
      SYNTAX      OCTET STRING
      MAX-ACCESS  read-only
      STATUS      current
      DESCRIPTION "Specifies the state of the most recent ExireAll operation."
      ::= { jmsRemoteEndpointRuntimeEntry 24  }
   
   
   jobRuntimeTable OBJECT-TYPE
      SYNTAX      SEQUENCE OF JobRuntimeEntry
      MAX-ACCESS  not-accessible
      STATUS      current
      DESCRIPTION "RuntimeMBean that provides information about a particular job."
      ::= { wls 1250  }
      
   
   jobRuntimeEntry OBJECT-TYPE
      SYNTAX      JobRuntimeEntry
      MAX-ACCESS  not-accessible
      STATUS      current
      DESCRIPTION "Generated SNMP Table Entry."
      INDEX { jobRuntimeIndex}
      ::= { jobRuntimeTable 1 }
      
   JobRuntimeEntry ::=
      SEQUENCE
      {
         jobRuntimeIndex      OCTET STRING,
         jobRuntimeObjectName OCTET STRING,
         jobRuntimeType       OCTET STRING,
         jobRuntimeTimeout    Counter64,
         jobRuntimeLocalExecutionCount Counter64,
         jobRuntimeLastLocalExecutionTime Counter64,
         jobRuntimePeriod     Counter64,
         jobRuntimeDescription OCTET STRING,
         jobRuntimeName       OCTET STRING,
         jobRuntimeID         OCTET STRING
      }
      
   
   jobRuntimeIndex OBJECT-TYPE
      SYNTAX      OCTET STRING
      MAX-ACCESS  not-accessible
      STATUS      current
      DESCRIPTION "Index column"
      ::= { jobRuntimeEntry 1  }
   
   
   jobRuntimeObjectName OBJECT-TYPE
      SYNTAX      OCTET STRING
      MAX-ACCESS  read-only
      STATUS      current
      DESCRIPTION "ObjectName column"
      ::= { jobRuntimeEntry 2  }
   
   
   jobRuntimeType OBJECT-TYPE
      SYNTAX      OCTET STRING
      MAX-ACCESS  read-only
      STATUS      current
      DESCRIPTION "Returns the type of the MBean."
      ::= { jobRuntimeEntry 3  }
   
   
   jobRuntimeTimeout OBJECT-TYPE
      SYNTAX      Counter64
      MAX-ACCESS  read-only
      STATUS      current
      DESCRIPTION "Returns when the job will be executed next"
      ::= { jobRuntimeEntry 4  }
   
   
   jobRuntimeLocalExecutionCount OBJECT-TYPE
      SYNTAX      Counter64
      MAX-ACCESS  read-only
      STATUS      current
      DESCRIPTION "Returns the number of times this job was executed locally. Job executions are load-balanced across the cluster. This count specifies the number of executions of the job in the local server."
      ::= { jobRuntimeEntry 5  }
   
   
   jobRuntimeLastLocalExecutionTime OBJECT-TYPE
      SYNTAX      Counter64
      MAX-ACCESS  read-only
      STATUS      current
      DESCRIPTION "Returns the most recent execution time of this job in the local server. Note that multiple executions of the same job are load-balanced across the cluster and this time indicates when the job was last executed locally."
      ::= { jobRuntimeEntry 6  }
   
   
   jobRuntimePeriod OBJECT-TYPE
      SYNTAX      Counter64
      MAX-ACCESS  read-only
      STATUS      current
      DESCRIPTION "Returns the specified periodicity of this job"
      ::= { jobRuntimeEntry 7  }
   
   
   jobRuntimeDescription OBJECT-TYPE
      SYNTAX      OCTET STRING
      MAX-ACCESS  read-only
      STATUS      current
      DESCRIPTION "Get the description of the submitted {@link commonj.timers.TimerListener}. Returns {@link commonj.timers.TimerListener#toString()}"
      ::= { jobRuntimeEntry 8  }
   
   
   jobRuntimeName OBJECT-TYPE
      SYNTAX      OCTET STRING
      MAX-ACCESS  read-only
      STATUS      current
      DESCRIPTION "The name of this configuration. WebLogic Server uses an MBean to implement and persist the configuration."
      ::= { jobRuntimeEntry 9  }
   
   
   jobRuntimeID OBJECT-TYPE
      SYNTAX      OCTET STRING
      MAX-ACCESS  read-only
      STATUS      current
      DESCRIPTION "The unique ID corresponding to this job"
      ::= { jobRuntimeEntry 10  }
   
   
   jobSchedulerRuntimeTable OBJECT-TYPE
      SYNTAX      SEQUENCE OF JobSchedulerRuntimeEntry
      MAX-ACCESS  not-accessible
      STATUS      current
      DESCRIPTION "RuntimeMBean that provides information about jobs scheduled with the Job Scheduler."
      ::= { wls 1255  }
      
   
   jobSchedulerRuntimeEntry OBJECT-TYPE
      SYNTAX      JobSchedulerRuntimeEntry
      MAX-ACCESS  not-accessible
      STATUS      current
      DESCRIPTION "Generated SNMP Table Entry."
      INDEX { jobSchedulerRuntimeIndex}
      ::= { jobSchedulerRuntimeTable 1 }
      
   JobSchedulerRuntimeEntry ::=
      SEQUENCE
      {
         jobSchedulerRuntimeIndex OCTET STRING,
         jobSchedulerRuntimeObjectName OCTET STRING,
         jobSchedulerRuntimeType OCTET STRING,
         jobSchedulerRuntimeName OCTET STRING
      }
      
   
   jobSchedulerRuntimeIndex OBJECT-TYPE
      SYNTAX      OCTET STRING
      MAX-ACCESS  not-accessible
      STATUS      current
      DESCRIPTION "Index column"
      ::= { jobSchedulerRuntimeEntry 1  }
   
   
   jobSchedulerRuntimeObjectName OBJECT-TYPE
      SYNTAX      OCTET STRING
      MAX-ACCESS  read-only
      STATUS      current
      DESCRIPTION "ObjectName column"
      ::= { jobSchedulerRuntimeEntry 2  }
   
   
   jobSchedulerRuntimeType OBJECT-TYPE
      SYNTAX      OCTET STRING
      MAX-ACCESS  read-only
      STATUS      current
      DESCRIPTION "Returns the type of the MBean."
      ::= { jobSchedulerRuntimeEntry 3  }
   
   
   jobSchedulerRuntimeName OBJECT-TYPE
      SYNTAX      OCTET STRING
      MAX-ACCESS  read-only
      STATUS      current
      DESCRIPTION "The name of this configuration. WebLogic Server uses an MBean to implement and persist the configuration."
      ::= { jobSchedulerRuntimeEntry 4  }
   
   
   kodoDataCacheRuntimeTable OBJECT-TYPE
      SYNTAX      SEQUENCE OF KodoDataCacheRuntimeEntry
      MAX-ACCESS  not-accessible
      STATUS      current
      DESCRIPTION "Base class for all runtime mbeans that provide status of running modules.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1260  }
      
   
   kodoDataCacheRuntimeEntry OBJECT-TYPE
      SYNTAX      KodoDataCacheRuntimeEntry
      MAX-ACCESS  not-accessible
      STATUS      current
      DESCRIPTION "Generated SNMP Table Entry."
      INDEX { kodoDataCacheRuntimeIndex}
      ::= { kodoDataCacheRuntimeTable 1 }
      
   KodoDataCacheRuntimeEntry ::=
      SEQUENCE
      {
         kodoDataCacheRuntimeIndex OCTET STRING,
         kodoDataCacheRuntimeObjectName OCTET STRING,
         kodoDataCacheRuntimeType OCTET STRING,
         kodoDataCacheRuntimeCacheHitCount Integer32,
         kodoDataCacheRuntimeTotalCurrentEntries Integer32,
         kodoDataCacheRuntimeCacheMissCount Integer32,
         kodoDataCacheRuntimeCacheHitRatio OCTET STRING,
         kodoDataCacheRuntimeName OCTET STRING,
         kodoDataCacheRuntimeStatistics OCTET STRING
      }
      
   
   kodoDataCacheRuntimeIndex OBJECT-TYPE
      SYNTAX      OCTET STRING
      MAX-ACCESS  not-accessible
      STATUS      current
      DESCRIPTION "Index column"
      ::= { kodoDataCacheRuntimeEntry 1  }
   
   
   kodoDataCacheRuntimeObjectName OBJECT-TYPE
      SYNTAX      OCTET STRING
      MAX-ACCESS  read-only
      STATUS      current
      DESCRIPTION "ObjectName column"
      ::= { kodoDataCacheRuntimeEntry 2  }
   
   
   kodoDataCacheRuntimeType OBJECT-TYPE
      SYNTAX      OCTET STRING
      MAX-ACCESS  read-only
      STATUS      current
      DESCRIPTION "Returns the type of the MBean."
      ::= { kodoDataCacheRuntimeEntry 3  }
   
   
   kodoDataCacheRuntimeCacheHitCount OBJECT-TYPE
      SYNTAX      Integer32
      MAX-ACCESS  read-only
      STATUS      current
      DESCRIPTION ""
      ::= { kodoDataCacheRuntimeEntry 4  }
   
   
   kodoDataCacheRuntimeTotalCurrentEntries OBJECT-TYPE
      SYNTAX      Integer32
      MAX-ACCESS  read-only
      STATUS      current
      DESCRIPTION ""
      ::= { kodoDataCacheRuntimeEntry 5  }
   
   
   kodoDataCacheRuntimeCacheMissCount OBJECT-TYPE
      SYNTAX      Integer32
      MAX-ACCESS  read-only
      STATUS      current
      DESCRIPTION ""
      ::= { kodoDataCacheRuntimeEntry 6  }
   
   
   kodoDataCacheRuntimeCacheHitRatio OBJECT-TYPE
      SYNTAX      OCTET STRING
      MAX-ACCESS  read-only
      STATUS      current
      DESCRIPTION ""
      ::= { kodoDataCacheRuntimeEntry 7  }
   
   
   kodoDataCacheRuntimeName OBJECT-TYPE
      SYNTAX      OCTET STRING
      MAX-ACCESS  read-only
      STATUS      current
      DESCRIPTION "The name of this configuration. WebLogic Server uses an MBean to implement and persist the configuration."
      ::= { kodoDataCacheRuntimeEntry 8  }
   
   
   kodoDataCacheRuntimeStatistics OBJECT-TYPE
      SYNTAX      OCTET STRING
      MAX-ACCESS  read-only
      STATUS      current
      DESCRIPTION ""
      ::= { kodoDataCacheRuntimeEntry 9  }
   
   
   kodoPersistenceUnitRuntimeTable OBJECT-TYPE
      SYNTAX      SEQUENCE OF KodoPersistenceUnitRuntimeEntry
      MAX-ACCESS  not-accessible
      STATUS      current
      DESCRIPTION "Base class for all runtime mbeans that provide status of running modules.  Deprecation of MBeanHome and Type-Safe Interfaces   This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1265  }
      
   
   kodoPersistenceUnitRuntimeEntry OBJECT-TYPE
      SYNTAX      KodoPersistenceUnitRuntimeEntry
      MAX-ACCESS  not-accessible
      STATUS      current
      DESCRIPTION "Generated SNMP Table Entry."
      INDEX { kodoPersistenceUnitRuntimeIndex}
      ::= { kodoPersistenceUnitRuntimeTable 1 }
      
   KodoPersistenceUnitRuntimeEntry ::=
      SEQUENCE
      {
         kodoPersistenceUnitRuntimeIndex OCTET STRING,
         kodoPersistenceUnitRuntimeObjectName OCTET STRING,
         kodoPersistenceUnitRuntimeType OCTET STRING,
         kodoPersistenceUnitRuntimePersistenceUnitName OCTET STRING,
         kodoPersistenceUnitRuntimeName OCTET STRING
      }
      
   
   kodoPersistenceUnitRuntimeIndex OBJECT-TYPE
      SYNTAX      OCTET STRING
      MAX-ACCESS  not-accessible
      STATUS      current
      DESCRIPTION "Index column"
      ::= { kodoPersistenceUnitRuntimeEntry 1  }
   
   
   kodoPersistenceUnitRuntimeObjectName OBJECT-TYPE
      SYNTAX      OCTET STRING
      MAX-ACCESS  read-only
      STATUS      current
      DESCRIPTION "ObjectName column"
      ::= { kodoPersistenceUnitRuntimeEntry 2  }
   
   
   kodoPersistenceUnitRuntimeType OBJECT-TYPE
      SYNTAX      OCTET STRING
      MAX-ACCESS  read-only
      STATUS      current
      DESCRIPTION "Returns the type of the MBean."
      ::= { kodoPersistenceUnitRuntimeEntry 3  }
   
   
   kodoPersistenceUnitRuntimePersistenceUnitName OBJECT-TYPE
      SYNTAX      OCTET STRING
      MAX-ACCESS  read-only
      STATUS      current
      DESCRIPTION ""
      ::= { kodoPersistenceUnitRuntimeEntry 4  }
   
   
   kodoPersistenceUnitRuntimeName OBJECT-TYPE
      SYNTAX      OCTET STRING
      MAX-ACCESS  read-only
      STATUS      current
      DESCRIPTION "The name of this configuration. WebLogic Server uses an MBean to implement and persist the configuration."
      ::= { kodoPersistenceUnitRuntimeEntry 5  }
   
   
   kodoQueryCacheRuntimeTable OBJECT-TYPE
      SYNTAX      SEQUENCE OF KodoQueryCacheRuntimeEntry
      MAX-ACCESS  not-accessible
      STATUS      current
      DESCRIPTION "Base class for all runtime mbeans that provide status of running modules.  Deprecation of MBeanHome and Type-Safe Interfaces   This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1270  }
      
   
   kodoQueryCacheRuntimeEntry OBJECT-TYPE
      SYNTAX      KodoQueryCacheRuntimeEntry
      MAX-ACCESS  not-accessible
      STATUS      current
      DESCRIPTION "Generated SNMP Table Entry."
      INDEX { kodoQueryCacheRuntimeIndex}
      ::= { kodoQueryCacheRuntimeTable 1 }
      
   KodoQueryCacheRuntimeEntry ::=
      SEQUENCE
      {
         kodoQueryCacheRuntimeIndex OCTET STRING,
         kodoQueryCacheRuntimeObjectName OCTET STRING,
         kodoQueryCacheRuntimeType OCTET STRING,
         kodoQueryCacheRuntimeCacheHitCount Integer32,
         kodoQueryCacheRuntimeTotalCurrentEntries Integer32,
         kodoQueryCacheRuntimeCacheMissCount Integer32,
         kodoQueryCacheRuntimeCacheHitRatio OCTET STRING,
         kodoQueryCacheRuntimeName OCTET STRING,
         kodoQueryCacheRuntimeStatistics OCTET STRING
      }
      
   
   kodoQueryCacheRuntimeIndex OBJECT-TYPE
      SYNTAX      OCTET STRING
      MAX-ACCESS  not-accessible
      STATUS      current
      DESCRIPTION "Index column"
      ::= { kodoQueryCacheRuntimeEntry 1  }
   
   
   kodoQueryCacheRuntimeObjectName OBJECT-TYPE
      SYNTAX      OCTET STRING
      MAX-ACCESS  read-only
      STATUS      current
      DESCRIPTION "ObjectName column"
      ::= { kodoQueryCacheRuntimeEntry 2  }
   
   
   kodoQueryCacheRuntimeType OBJECT-TYPE
      SYNTAX      OCTET STRING
      MAX-ACCESS  read-only
      STATUS      current
      DESCRIPTION "Returns the type of the MBean."
      ::= { kodoQueryCacheRuntimeEntry 3  }
   
   
   kodoQueryCacheRuntimeCacheHitCount OBJECT-TYPE
      SYNTAX      Integer32
      MAX-ACCESS  read-only
      STATUS      current
      DESCRIPTION ""
      ::= { kodoQueryCacheRuntimeEntry 4  }
   
   
   kodoQueryCacheRuntimeTotalCurrentEntries OBJECT-TYPE
      SYNTAX      Integer32
      MAX-ACCESS  read-only
      STATUS      current
      DESCRIPTION ""
      ::= { kodoQueryCacheRuntimeEntry 5  }
   
   
   kodoQueryCacheRuntimeCacheMissCount OBJECT-TYPE
      SYNTAX      Integer32
      MAX-ACCESS  read-only
      STATUS      current
      DESCRIPTION ""
      ::= { kodoQueryCacheRuntimeEntry 6  }
   
   
   kodoQueryCacheRuntimeCacheHitRatio OBJECT-TYPE
      SYNTAX      OCTET STRING
      MAX-ACCESS  read-only
      STATUS      current
      DESCRIPTION ""
      ::= { kodoQueryCacheRuntimeEntry 7  }
   
   
   kodoQueryCacheRuntimeName OBJECT-TYPE
      SYNTAX      OCTET STRING
      MAX-ACCESS  read-only
      STATUS      current
      DESCRIPTION "The name of this configuration. WebLogic Server uses an MBean to implement and persist the configuration."
      ::= { kodoQueryCacheRuntimeEntry 8  }
   
   
   kodoQueryCacheRuntimeStatistics OBJECT-TYPE
      SYNTAX      OCTET STRING
      MAX-ACCESS  read-only
      STATUS      current
      DESCRIPTION ""
      ::= { kodoQueryCacheRuntimeEntry 9  }
   
   
   kodoQueryCompilationCacheRuntimeTable OBJECT-TYPE
      SYNTAX      SEQUENCE OF KodoQueryCompilationCacheRuntimeEntry
      MAX-ACCESS  not-accessible
      STATUS      current
      DESCRIPTION "Base class for all runtime mbeans that provide status of running modules.  Deprecation of MBeanHome and Type-Safe Interfaces   This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1275  }
      
   
   kodoQueryCompilationCacheRuntimeEntry OBJECT-TYPE
      SYNTAX      KodoQueryCompilationCacheRuntimeEntry
      MAX-ACCESS  not-accessible
      STATUS      current
      DESCRIPTION "Generated SNMP Table Entry."
      INDEX { kodoQueryCompilationCacheRuntimeIndex}
      ::= { kodoQueryCompilationCacheRuntimeTable 1 }
      
   KodoQueryCompilationCacheRuntimeEntry ::=
      SEQUENCE
      {
         kodoQueryCompilationCacheRuntimeIndex OCTET STRING,
         kodoQueryCompilationCacheRuntimeObjectName OCTET STRING,
         kodoQueryCompilationCacheRuntimeType OCTET STRING,
         kodoQueryCompilationCacheRuntimeTotalCurrentEntries Integer32,
         kodoQueryCompilationCacheRuntimeName OCTET STRING
      }
      
   
   kodoQueryCompilationCacheRuntimeIndex OBJECT-TYPE
      SYNTAX      OCTET STRING
      MAX-ACCESS  not-accessible
      STATUS      current
      DESCRIPTION "Index column"
      ::= { kodoQueryCompilationCacheRuntimeEntry 1  }
   
   
   kodoQueryCompilationCacheRuntimeObjectName OBJECT-TYPE
      SYNTAX      OCTET STRING
      MAX-ACCESS  read-only
      STATUS      current
      DESCRIPTION "ObjectName column"
      ::= { kodoQueryCompilationCacheRuntimeEntry 2  }
   
   
   kodoQueryCompilationCacheRuntimeType OBJECT-TYPE
      SYNTAX      OCTET STRING
      MAX-ACCESS  read-only
      STATUS      current
      DESCRIPTION "Returns the type of the MBean."
      ::= { kodoQueryCompilationCacheRuntimeEntry 3  }
   
   
   kodoQueryCompilationCacheRuntimeTotalCurrentEntries OBJECT-TYPE
      SYNTAX      Integer32
      MAX-ACCESS  read-only
      STATUS      current
      DESCRIPTION ""
      ::= { kodoQueryCompilationCacheRuntimeEntry 4  }
   
   
   kodoQueryCompilationCacheRuntimeName OBJECT-TYPE
      SYNTAX      OCTET STRING
      MAX-ACCESS  read-only
      STATUS      current
      DESCRIPTION "The name of this configuration. WebLogic Server uses an MBean to implement and persist the configuration."
      ::= { kodoQueryCompilationCacheRuntimeEntry 5  }
   
   
   mailSessionRuntimeTable OBJECT-TYPE
      SYNTAX      SEQUENCE OF MailSessionRuntimeEntry
      MAX-ACCESS  not-accessible
      STATUS      current
      DESCRIPTION "RuntimeMBean for JavaMail Sessions  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1280  }
      
   
   mailSessionRuntimeEntry OBJECT-TYPE
      SYNTAX      MailSessionRuntimeEntry
      MAX-ACCESS  not-accessible
      STATUS      current
      DESCRIPTION "Generated SNMP Table Entry."
      INDEX { mailSessionRuntimeIndex}
      ::= { mailSessionRuntimeTable 1 }
      
   MailSessionRuntimeEntry ::=
      SEQUENCE
      {
         mailSessionRuntimeIndex OCTET STRING,
         mailSessionRuntimeObjectName OCTET STRING,
         mailSessionRuntimeType OCTET STRING,
         mailSessionRuntimeName OCTET STRING
      }
      
   
   mailSessionRuntimeIndex OBJECT-TYPE
      SYNTAX      OCTET STRING
      MAX-ACCESS  not-accessible
      STATUS      current
      DESCRIPTION "Index column"
      ::= { mailSessionRuntimeEntry 1  }
   
   
   mailSessionRuntimeObjectName OBJECT-TYPE
      SYNTAX      OCTET STRING
      MAX-ACCESS  read-only
      STATUS      current
      DESCRIPTION "ObjectName column"
      ::= { mailSessionRuntimeEntry 2  }
   
   
   mailSessionRuntimeType OBJECT-TYPE
      SYNTAX      OCTET STRING
      MAX-ACCESS  read-only
      STATUS      current
      DESCRIPTION "Returns the type of the MBean."
      ::= { mailSessionRuntimeEntry 3  }
   
   
   mailSessionRuntimeName OBJECT-TYPE
      SYNTAX      OCTET STRING
      MAX-ACCESS  read-only
      STATUS      current
      DESCRIPTION "The name of this configuration. WebLogic Server uses an MBean to implement and persist the configuration."
      ::= { mailSessionRuntimeEntry 4  }
   
   
   messageDrivenControlEJBRuntimeTable OBJECT-TYPE
      SYNTAX      SEQUENCE OF MessageDrivenControlEJBRuntimeEntry
      MAX-ACCESS  not-accessible
      STATUS      current
      DESCRIPTION "This interface contains controls to suspend & resume the MDBs. This RuntimeMBean deployed only on the AdminServer.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1285  }
      
   
   messageDrivenControlEJBRuntimeEntry OBJECT-TYPE
      SYNTAX      MessageDrivenControlEJBRuntimeEntry
      MAX-ACCESS  not-accessible
      STATUS      current
      DESCRIPTION "Generated SNMP Table Entry."
      INDEX { messageDrivenControlEJBRuntimeIndex}
      ::= { messageDrivenControlEJBRuntimeTable 1 }
      
   MessageDrivenControlEJBRuntimeEntry ::=
      SEQUENCE
      {
         messageDrivenControlEJBRuntimeIndex OCTET STRING,
         messageDrivenControlEJBRuntimeObjectName OCTET STRING,
         messageDrivenControlEJBRuntimeType OCTET STRING,
         messageDrivenControlEJBRuntimeName OCTET STRING
      }
      
   
   messageDrivenControlEJBRuntimeIndex OBJECT-TYPE
      SYNTAX      OCTET STRING
      MAX-ACCESS  not-accessible
      STATUS      current
      DESCRIPTION "Index column"
      ::= { messageDrivenControlEJBRuntimeEntry 1  }
   
   
   messageDrivenControlEJBRuntimeObjectName OBJECT-TYPE
      SYNTAX      OCTET STRING
      MAX-ACCESS  read-only
      STATUS      current
      DESCRIPTION "ObjectName column"
      ::= { messageDrivenControlEJBRuntimeEntry 2  }
   
   
   messageDrivenControlEJBRuntimeType OBJECT-TYPE
      SYNTAX      OCTET STRING
      MAX-ACCESS  read-only
      STATUS      current
      DESCRIPTION "Returns the type of the MBean."
      ::= { messageDrivenControlEJBRuntimeEntry 3  }
   
   
   messageDrivenControlEJBRuntimeName OBJECT-TYPE
      SYNTAX      OCTET STRING
      MAX-ACCESS  read-only
      STATUS      current
      DESCRIPTION "The name of this configuration. WebLogic Server uses an MBean to implement and persist the configuration."
      ::= { messageDrivenControlEJBRuntimeEntry 4  }
   
   
   migratableServiceCoordinatorRuntimeTable OBJECT-TYPE
      SYNTAX      SEQUENCE OF MigratableServiceCoordinatorRuntimeEntry
      MAX-ACCESS  not-accessible
      STATUS      current
      DESCRIPTION "Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1290  }
      
   
   migratableServiceCoordinatorRuntimeEntry OBJECT-TYPE
      SYNTAX      MigratableServiceCoordinatorRuntimeEntry
      MAX-ACCESS  not-accessible
      STATUS      current
      DESCRIPTION "Generated SNMP Table Entry."
      INDEX { migratableServiceCoordinatorRuntimeIndex}
      ::= { migratableServiceCoordinatorRuntimeTable 1 }
      
   MigratableServiceCoordinatorRuntimeEntry ::=
      SEQUENCE
      {
         migratableServiceCoordinatorRuntimeIndex OCTET STRING,
         migratableServiceCoordinatorRuntimeObjectName OCTET STRING,
         migratableServiceCoordinatorRuntimeType OCTET STRING,
         migratableServiceCoordinatorRuntimeName OCTET STRING
      }
      
   
   migratableServiceCoordinatorRuntimeIndex OBJECT-TYPE
      SYNTAX      OCTET STRING
      MAX-ACCESS  not-accessible
      STATUS      current
      DESCRIPTION "Index column"
      ::= { migratableServiceCoordinatorRuntimeEntry 1  }
   
   
   migratableServiceCoordinatorRuntimeObjectName OBJECT-TYPE
      SYNTAX      OCTET STRING
      MAX-ACCESS  read-only
      STATUS      current
      DESCRIPTION "ObjectName column"
      ::= { migratableServiceCoordinatorRuntimeEntry 2  }
   
   
   migratableServiceCoordinatorRuntimeType OBJECT-TYPE
      SYNTAX      OCTET STRING
      MAX-ACCESS  read-only
      STATUS      current
      DESCRIPTION "Returns the type of the MBean."
      ::= { migratableServiceCoordinatorRuntimeEntry 3  }
   
   
   migratableServiceCoordinatorRuntimeName OBJECT-TYPE
      SYNTAX      OCTET STRING
      MAX-ACCESS  read-only
      STATUS      current
      DESCRIPTION "The name of this configuration. WebLogic Server uses an MBean to implement and persist the configuration."
      ::= { migratableServiceCoordinatorRuntimeEntry 4  }
   
   
   migrationDataRuntimeTable OBJECT-TYPE
      SYNTAX      SEQUENCE OF MigrationDataRuntimeEntry
      MAX-ACCESS  not-accessible
      STATUS      current
      DESCRIPTION "Runtime information about one past or ongoing migration."
      ::= { wls 1295  }
      
   
   migrationDataRuntimeEntry OBJECT-TYPE
      SYNTAX      MigrationDataRuntimeEntry
      MAX-ACCESS  not-accessible
      STATUS      current
      DESCRIPTION "Generated SNMP Table Entry."
      INDEX { migrationDataRuntimeIndex}
      ::= { migrationDataRuntimeTable 1 }
      
   MigrationDataRuntimeEntry ::=
      SEQUENCE
      {
         migrationDataRuntimeIndex OCTET STRING,
         migrationDataRuntimeObjectName OCTET STRING,
         migrationDataRuntimeType OCTET STRING,
         migrationDataRuntimeStatus Integer32,
         migrationDataRuntimeMigrationStartTime Counter64,
         migrationDataRuntimeClusterMasterName OCTET STRING,
         migrationDataRuntimeServerName OCTET STRING,
         migrationDataRuntimeMachineMigratedFrom OCTET STRING,
         migrationDataRuntimeMigrationEndTime Counter64,
         migrationDataRuntimeClusterName OCTET STRING,
         migrationDataRuntimeName OCTET STRING,
         migrationDataRuntimeMachineMigratedTo OCTET STRING
      }
      
   
   migrationDataRuntimeIndex OBJECT-TYPE
      SYNTAX      OCTET STRING
      MAX-ACCESS  not-accessible
      STATUS      current
      DESCRIPTION "Index column"
      ::= { migrationDataRuntimeEntry 1  }
   
   
   migrationDataRuntimeObjectName OBJECT-TYPE
      SYNTAX      OCTET STRING
      MAX-ACCESS  read-only
      STATUS      current
      DESCRIPTION "ObjectName column"
      ::= { migrationDataRuntimeEntry 2  }
   
   
   migrationDataRuntimeType OBJECT-TYPE
      SYNTAX      OCTET STRING
      MAX-ACCESS  read-only
      STATUS      current
      DESCRIPTION "Returns the type of the MBean."
      ::= { migrationDataRuntimeEntry 3  }
   
   
   migrationDataRuntimeStatus OBJECT-TYPE
      SYNTAX      Integer32
      MAX-ACCESS  read-only
      STATUS      current
      DESCRIPTION "Name of the server migrated"
      ::= { migrationDataRuntimeEntry 4  }
   
   
   migrationDataRuntimeMigrationStartTime OBJECT-TYPE
      SYNTAX      Counter64
      MAX-ACCESS  read-only
      STATUS      current
      DESCRIPTION "Start time of migration"
      ::= { migrationDataRuntimeEntry 5  }
   
   
   migrationDataRuntimeClusterMasterName OBJECT-TYPE
      SYNTAX      OCTET STRING
      MAX-ACCESS  read-only
      STATUS      current
      DESCRIPTION "Name of the server that acted as the cluster master for this migration."
      ::= { migrationDataRuntimeEntry 6  }
   
   
   migrationDataRuntimeServerName OBJECT-TYPE
      SYNTAX      OCTET STRING
      MAX-ACCESS  read-only
      STATUS      current
      DESCRIPTION "Name of the server migrated"
      ::= { migrationDataRuntimeEntry 7  }
   
   
   migrationDataRuntimeMachineMigratedFrom OBJECT-TYPE
      SYNTAX      OCTET STRING
      MAX-ACCESS  read-only
      STATUS      current
      DESCRIPTION "Machine from which the server was migrated from"
      ::= { migrationDataRuntimeEntry 8  }
   
   
   migrationDataRuntimeMigrationEndTime OBJECT-TYPE
      SYNTAX      Counter64
      MAX-ACCESS  read-only
      STATUS      current
      DESCRIPTION "End time of migration"
      ::= { migrationDataRuntimeEntry 9  }
   
   
   migrationDataRuntimeClusterName OBJECT-TYPE
      SYNTAX      OCTET STRING
      MAX-ACCESS  read-only
      STATUS      current
      DESCRIPTION "Name of the server that acted as the cluster master for this migration."
      ::= { migrationDataRuntimeEntry 10  }
   
   
   migrationDataRuntimeName OBJECT-TYPE
      SYNTAX      OCTET STRING
      MAX-ACCESS  read-only
      STATUS      current
      DESCRIPTION "The name of this configuration. WebLogic Server uses an MBean to implement and persist the configuration."
      ::= { migrationDataRuntimeEntry 11  }
   
   
   migrationDataRuntimeMachineMigratedTo OBJECT-TYPE
      SYNTAX      OCTET STRING
      MAX-ACCESS  read-only
      STATUS      current
      DESCRIPTION "Machine to which the server was migrated to or is in the process of being migrated to."
      ::= { migrationDataRuntimeEntry 12  }
   
   
   migrationTaskRuntimeTable OBJECT-TYPE
      SYNTAX      SEQUENCE OF MigrationTaskRuntimeEntry
      MAX-ACCESS  not-accessible
      STATUS      current
      DESCRIPTION "Exposes monitoring information about an ongoing and potentially long-running administrative process.  This should be taken to mean, at minimum, any OAM operation involving IO.  Examples include starting and stopping servers, deploying and undeploying applications, or migrating services.  An MBean operation method of this sort should place the actual work on an ExecuteQueue and immediately return an instance of TaskRuntimeMBean to the caller.  The caller can then use this to track the task's progress as desired, and if appropriate, provide facilities for user interaction with the task, e.g. 'cancel' or 'continue anyway.'  OA&M clients can also query for all instances of TaskRuntimeMBean to get a summary of both currently-running and recently-completed tasks. Instance of TaskRuntimeMBean continue to exist in the MBeanServer after the completion of the work they describe.  They will eventually either be explicitly deregistered by an OA&M client, or removed by a scavenger process which periodically purges TaskRuntimeMBeans that have been completed for some time."
      ::= { wls 1300  }
      
   
   migrationTaskRuntimeEntry OBJECT-TYPE
      SYNTAX      MigrationTaskRuntimeEntry
      MAX-ACCESS  not-accessible
      STATUS      current
      DESCRIPTION "Generated SNMP Table Entry."
      INDEX { migrationTaskRuntimeIndex}
      ::= { migrationTaskRuntimeTable 1 }
      
   MigrationTaskRuntimeEntry ::=
      SEQUENCE
      {
         migrationTaskRuntimeIndex OCTET STRING,
         migrationTaskRuntimeObjectName OCTET STRING,
         migrationTaskRuntimeType OCTET STRING,
         migrationTaskRuntimeName OCTET STRING
      }
      
   
   migrationTaskRuntimeIndex OBJECT-TYPE
      SYNTAX      OCTET STRING
      MAX-ACCESS  not-accessible
      STATUS      current
      DESCRIPTION "Index column"
      ::= { migrationTaskRuntimeEntry 1  }
   
   
   migrationTaskRuntimeObjectName OBJECT-TYPE
      SYNTAX      OCTET STRING
      MAX-ACCESS  read-only
      STATUS      current
      DESCRIPTION "ObjectName column"
      ::= { migrationTaskRuntimeEntry 2  }
   
   
   migrationTaskRuntimeType OBJECT-TYPE
      SYNTAX      OCTET STRING
      MAX-ACCESS  read-only
      STATUS      current
      DESCRIPTION "Returns the type of the MBean."
      ::= { migrationTaskRuntimeEntry 3  }
   
   
   migrationTaskRuntimeName OBJECT-TYPE
      SYNTAX      OCTET STRING
      MAX-ACCESS  read-only
      STATUS      current
      DESCRIPTION "The name of this configuration. WebLogic Server uses an MBean to implement and persist the configuration."
      ::= { migrationTaskRuntimeEntry 4  }
   
   
   psAssemblyRuntimeTable OBJECT-TYPE
      SYNTAX      SEQUENCE OF PsAssemblyRuntimeEntry
      MAX-ACCESS  not-accessible
      STATUS      current
      DESCRIPTION "This interface is used for accessing a WebLogic path service entity  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1305  }
      
   
   psAssemblyRuntimeEntry OBJECT-TYPE
      SYNTAX      PsAssemblyRuntimeEntry
      MAX-ACCESS  not-accessible
      STATUS      current
      DESCRIPTION "Generated SNMP Table Entry."
      INDEX { psAssemblyRuntimeIndex}
      ::= { psAssemblyRuntimeTable 1 }
      
   PsAssemblyRuntimeEntry ::=
      SEQUENCE
      {
         psAssemblyRuntimeIndex OCTET STRING,
         psAssemblyRuntimeObjectName OCTET STRING,
         psAssemblyRuntimeType OCTET STRING,
         psAssemblyRuntimeMapEntries OCTET STRING,
         psAssemblyRuntimeName OCTET STRING
      }
      
   
   psAssemblyRuntimeIndex OBJECT-TYPE
      SYNTAX      OCTET STRING
      MAX-ACCESS  not-accessible
      STATUS      current
      DESCRIPTION "Index column"
      ::= { psAssemblyRuntimeEntry 1  }
   
   
   psAssemblyRuntimeObjectName OBJECT-TYPE
      SYNTAX      OCTET STRING
      MAX-ACCESS  read-only
      STATUS      current
      DESCRIPTION "ObjectName column"
      ::= { psAssemblyRuntimeEntry 2  }
   
   
   psAssemblyRuntimeType OBJECT-TYPE
      SYNTAX      OCTET STRING
      MAX-ACCESS  read-only
      STATUS      current
      DESCRIPTION "Returns the type of the MBean."
      ::= { psAssemblyRuntimeEntry 3  }
   
   
   psAssemblyRuntimeMapEntries OBJECT-TYPE
      SYNTAX      OCTET STRING
      MAX-ACCESS  read-only
      STATUS      current
      DESCRIPTION "Returns all entries in a persistent map's assembly."
      ::= { psAssemblyRuntimeEntry 4  }
   
   
   psAssemblyRuntimeName OBJECT-TYPE
      SYNTAX      OCTET STRING
      MAX-ACCESS  read-only
      STATUS      current
      DESCRIPTION "The name of this configuration. WebLogic Server uses an MBean to implement and persist the configuration."
      ::= { psAssemblyRuntimeEntry 5  }
   
   
   pageFlowActionRuntimeTable OBJECT-TYPE
      SYNTAX      SEQUENCE OF PageFlowActionRuntimeEntry
      MAX-ACCESS  not-accessible
      STATUS      current
      DESCRIPTION "This MBean represents the statistics for a single action of a PageFlow  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1310  }
      
   
   pageFlowActionRuntimeEntry OBJECT-TYPE
      SYNTAX      PageFlowActionRuntimeEntry
      MAX-ACCESS  not-accessible
      STATUS      current
      DESCRIPTION "Generated SNMP Table Entry."
      INDEX { pageFlowActionRuntimeIndex}
      ::= { pageFlowActionRuntimeTable 1 }
      
   PageFlowActionRuntimeEntry ::=
      SEQUENCE
      {
         pageFlowActionRuntimeIndex OCTET STRING,
         pageFlowActionRuntimeObjectName OCTET STRING,
         pageFlowActionRuntimeType OCTET STRING,
         pageFlowActionRuntimeName OCTET STRING
      }
      
   
   pageFlowActionRuntimeIndex OBJECT-TYPE
      SYNTAX      OCTET STRING
      MAX-ACCESS  not-accessible
      STATUS      current
      DESCRIPTION "Index column"
      ::= { pageFlowActionRuntimeEntry 1  }
   
   
   pageFlowActionRuntimeObjectName OBJECT-TYPE
      SYNTAX      OCTET STRING
      MAX-ACCESS  read-only
      STATUS      current
      DESCRIPTION "ObjectName column"
      ::= { pageFlowActionRuntimeEntry 2  }
   
   
   pageFlowActionRuntimeType OBJECT-TYPE
      SYNTAX      OCTET STRING
      MAX-ACCESS  read-only
      STATUS      current
      DESCRIPTION "Returns the type of the MBean."
      ::= { pageFlowActionRuntimeEntry 3  }
   
   
   pageFlowActionRuntimeName OBJECT-TYPE
      SYNTAX      OCTET STRING
      MAX-ACCESS  read-only
      STATUS      current
      DESCRIPTION "The name of this configuration. WebLogic Server uses an MBean to implement and persist the configuration."
      ::= { pageFlowActionRuntimeEntry 4  }
   
   
   pageFlowRuntimeTable OBJECT-TYPE
      SYNTAX      SEQUENCE OF PageFlowRuntimeEntry
      MAX-ACCESS  not-accessible
      STATUS      current
      DESCRIPTION "This MBean represents a PageFlow type.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1315  }
      
   
   pageFlowRuntimeEntry OBJECT-TYPE
      SYNTAX      PageFlowRuntimeEntry
      MAX-ACCESS  not-accessible
      STATUS      current
      DESCRIPTION "Generated SNMP Table Entry."
      INDEX { pageFlowRuntimeIndex}
      ::= { pageFlowRuntimeTable 1 }
      
   PageFlowRuntimeEntry ::=
      SEQUENCE
      {
         pageFlowRuntimeIndex OCTET STRING,
         pageFlowRuntimeObjectName OCTET STRING,
         pageFlowRuntimeType  OCTET STRING,
         pageFlowRuntimeName  OCTET STRING
      }
      
   
   pageFlowRuntimeIndex OBJECT-TYPE
      SYNTAX      OCTET STRING
      MAX-ACCESS  not-accessible
      STATUS      current
      DESCRIPTION "Index column"
      ::= { pageFlowRuntimeEntry 1  }
   
   
   pageFlowRuntimeObjectName OBJECT-TYPE
      SYNTAX      OCTET STRING
      MAX-ACCESS  read-only
      STATUS      current
      DESCRIPTION "ObjectName column"
      ::= { pageFlowRuntimeEntry 2  }
   
   
   pageFlowRuntimeType OBJECT-TYPE
      SYNTAX      OCTET STRING
      MAX-ACCESS  read-only
      STATUS      current
      DESCRIPTION "Returns the type of the MBean."
      ::= { pageFlowRuntimeEntry 3  }
   
   
   pageFlowRuntimeName OBJECT-TYPE
      SYNTAX      OCTET STRING
      MAX-ACCESS  read-only
      STATUS      current
      DESCRIPTION "The name of this configuration. WebLogic Server uses an MBean to implement and persist the configuration."
      ::= { pageFlowRuntimeEntry 4  }
   
   
   pageFlowsRuntimeTable OBJECT-TYPE
      SYNTAX      SEQUENCE OF PageFlowsRuntimeEntry
      MAX-ACCESS  not-accessible
      STATUS      current
      DESCRIPTION "This MBean just hides the lazy construction of PageFlowRuntimeMBeans and provides a top-level reset() operation for all PageFlows in the webapp. It also minimizes the impact on the WebAppRuntimeMBean.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1320  }
      
   
   pageFlowsRuntimeEntry OBJECT-TYPE
      SYNTAX      PageFlowsRuntimeEntry
      MAX-ACCESS  not-accessible
      STATUS      current
      DESCRIPTION "Generated SNMP Table Entry."
      INDEX { pageFlowsRuntimeIndex}
      ::= { pageFlowsRuntimeTable 1 }
      
   PageFlowsRuntimeEntry ::=
      SEQUENCE
      {
         pageFlowsRuntimeIndex OCTET STRING,
         pageFlowsRuntimeObjectName OCTET STRING,
         pageFlowsRuntimeType OCTET STRING,
         pageFlowsRuntimeName OCTET STRING
      }
      
   
   pageFlowsRuntimeIndex OBJECT-TYPE
      SYNTAX      OCTET STRING
      MAX-ACCESS  not-accessible
      STATUS      current
      DESCRIPTION "Index column"
      ::= { pageFlowsRuntimeEntry 1  }
   
   
   pageFlowsRuntimeObjectName OBJECT-TYPE
      SYNTAX      OCTET STRING
      MAX-ACCESS  read-only
      STATUS      current
      DESCRIPTION "ObjectName column"
      ::= { pageFlowsRuntimeEntry 2  }
   
   
   pageFlowsRuntimeType OBJECT-TYPE
      SYNTAX      OCTET STRING
      MAX-ACCESS  read-only
      STATUS      current
      DESCRIPTION "Returns the type of the MBean."
      ::= { pageFlowsRuntimeEntry 3  }
   
   
   pageFlowsRuntimeName OBJECT-TYPE
      SYNTAX      OCTET STRING
      MAX-ACCESS  read-only
      STATUS      current
      DESCRIPTION "The name of this configuration. WebLogic Server uses an MBean to implement and persist the configuration."
      ::= { pageFlowsRuntimeEntry 4  }
   
   
   pathServiceRuntimeTable OBJECT-TYPE
      SYNTAX      SEQUENCE OF PathServiceRuntimeEntry
      MAX-ACCESS  not-accessible
      STATUS      current
      DESCRIPTION "This interface is used for accessing a WebLogic path service entity  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1325  }
      
   
   pathServiceRuntimeEntry OBJECT-TYPE
      SYNTAX      PathServiceRuntimeEntry
      MAX-ACCESS  not-accessible
      STATUS      current
      DESCRIPTION "Generated SNMP Table Entry."
      INDEX { pathServiceRuntimeIndex}
      ::= { pathServiceRuntimeTable 1 }
      
   PathServiceRuntimeEntry ::=
      SEQUENCE
      {
         pathServiceRuntimeIndex OCTET STRING,
         pathServiceRuntimeObjectName OCTET STRING,
         pathServiceRuntimeType OCTET STRING,
         pathServiceRuntimeName OCTET STRING
      }
      
   
   pathServiceRuntimeIndex OBJECT-TYPE
      SYNTAX      OCTET STRING
      MAX-ACCESS  not-accessible
      STATUS      current
      DESCRIPTION "Index column"
      ::= { pathServiceRuntimeEntry 1  }
   
   
   pathServiceRuntimeObjectName OBJECT-TYPE
      SYNTAX      OCTET STRING
      MAX-ACCESS  read-only
      STATUS      current
      DESCRIPTION "ObjectName column"
      ::= { pathServiceRuntimeEntry 2  }
   
   
   pathServiceRuntimeType OBJECT-TYPE
      SYNTAX      OCTET STRING
      MAX-ACCESS  read-only
      STATUS      current
      DESCRIPTION "Returns the type of the MBean."
      ::= { pathServiceRuntimeEntry 3  }
   
   
   pathServiceRuntimeName OBJECT-TYPE
      SYNTAX      OCTET STRING
      MAX-ACCESS  read-only
      STATUS      current
      DESCRIPTION "The name of this configuration. WebLogic Server uses an MBean to implement and persist the configuration."
      ::= { pathServiceRuntimeEntry 4  }
   
   
   realmRuntimeTable OBJECT-TYPE
      SYNTAX      SEQUENCE OF RealmRuntimeEntry
      MAX-ACCESS  not-accessible
      STATUS      current
      DESCRIPTION "This class is used to monitor and manage per security realm runtime information."
      ::= { wls 1330  }
      
   
   realmRuntimeEntry OBJECT-TYPE
      SYNTAX      RealmRuntimeEntry
      MAX-ACCESS  not-accessible
      STATUS      current
      DESCRIPTION "Generated SNMP Table Entry."
      INDEX { realmRuntimeIndex}
      ::= { realmRuntimeTable 1 }
      
   RealmRuntimeEntry ::=
      SEQUENCE
      {
         realmRuntimeIndex    OCTET STRING,
         realmRuntimeObjectName OCTET STRING,
         realmRuntimeType     OCTET STRING,
         realmRuntimeName     OCTET STRING
      }
      
   
   realmRuntimeIndex OBJECT-TYPE
      SYNTAX      OCTET STRING
      MAX-ACCESS  not-accessible
      STATUS      current
      DESCRIPTION "Index column"
      ::= { realmRuntimeEntry 1  }
   
   
   realmRuntimeObjectName OBJECT-TYPE
      SYNTAX      OCTET STRING
      MAX-ACCESS  read-only
      STATUS      current
      DESCRIPTION "ObjectName column"
      ::= { realmRuntimeEntry 2  }
   
   
   realmRuntimeType OBJECT-TYPE
      SYNTAX      OCTET STRING
      MAX-ACCESS  read-only
      STATUS      current
      DESCRIPTION "Returns the type of the MBean."
      ::= { realmRuntimeEntry 3  }
   
   
   realmRuntimeName OBJECT-TYPE
      SYNTAX      OCTET STRING
      MAX-ACCESS  read-only
      STATUS      current
      DESCRIPTION "The name of this configuration. WebLogic Server uses an MBean to implement and persist the configuration."
      ::= { realmRuntimeEntry 4  }
   
   
   safRuntimeTable OBJECT-TYPE
      SYNTAX      SEQUENCE OF SafRuntimeEntry
      MAX-ACCESS  not-accessible
      STATUS      current
      DESCRIPTION "This class is used for monitoring a WebLogic SAF service.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1335  }
      
   
   safRuntimeEntry OBJECT-TYPE
      SYNTAX      SafRuntimeEntry
      MAX-ACCESS  not-accessible
      STATUS      current
      DESCRIPTION "Generated SNMP Table Entry."
      INDEX { safRuntimeIndex}
      ::= { safRuntimeTable 1 }
      
   SafRuntimeEntry ::=
      SEQUENCE
      {
         safRuntimeIndex      OCTET STRING,
         safRuntimeObjectName OCTET STRING,
         safRuntimeType       OCTET STRING,
         safRuntimeName       OCTET STRING
      }
      
   
   safRuntimeIndex OBJECT-TYPE
      SYNTAX      OCTET STRING
      MAX-ACCESS  not-accessible
      STATUS      current
      DESCRIPTION "Index column"
      ::= { safRuntimeEntry 1  }
   
   
   safRuntimeObjectName OBJECT-TYPE
      SYNTAX      OCTET STRING
      MAX-ACCESS  read-only
      STATUS      current
      DESCRIPTION "ObjectName column"
      ::= { safRuntimeEntry 2  }
   
   
   safRuntimeType OBJECT-TYPE
      SYNTAX      OCTET STRING
      MAX-ACCESS  read-only
      STATUS      current
      DESCRIPTION "Returns the type of the MBean."
      ::= { safRuntimeEntry 3  }
   
   
   safRuntimeName OBJECT-TYPE
      SYNTAX      OCTET STRING
      MAX-ACCESS  read-only
      STATUS      current
      DESCRIPTION "The name of this configuration. WebLogic Server uses an MBean to implement and persist the configuration."
      ::= { safRuntimeEntry 4  }
   
   
   wlssnmpAgentRuntimeTable OBJECT-TYPE
      SYNTAX      SEQUENCE OF WlssnmpAgentRuntimeEntry
      MAX-ACCESS  not-accessible
      STATUS      current
      DESCRIPTION "Runtime information for an SNMP agent that is running in the current WebLogic Server domain."
      ::= { wls 1340  }
      
   
   wlssnmpAgentRuntimeEntry OBJECT-TYPE
      SYNTAX      WlssnmpAgentRuntimeEntry
      MAX-ACCESS  not-accessible
      STATUS      current
      DESCRIPTION "Generated SNMP Table Entry."
      INDEX { wlssnmpAgentRuntimeIndex}
      ::= { wlssnmpAgentRuntimeTable 1 }
      
   WlssnmpAgentRuntimeEntry ::=
      SEQUENCE
      {
         wlssnmpAgentRuntimeIndex OCTET STRING,
         wlssnmpAgentRuntimeObjectName OCTET STRING,
         wlssnmpAgentRuntimeType OCTET STRING,
         wlssnmpAgentRuntimeUDPListenPort Integer32,
         wlssnmpAgentRuntimeLogMessageTrapCount Counter64,
         wlssnmpAgentRuntimeFailedAuthorizationCount Integer32,
         wlssnmpAgentRuntimeRunning OCTET STRING,
         wlssnmpAgentRuntimeStringMonitorTrapCount Counter64,
         wlssnmpAgentRuntimeMonitorTrapCount Counter64,
         wlssnmpAgentRuntimeMasterAgentXPort Integer32,
         wlssnmpAgentRuntimeGaugeMonitorTrapCount Counter64,
         wlssnmpAgentRuntimeServerStopTrapCount Counter64,
         wlssnmpAgentRuntimeAttributeChangeTrapCount Counter64,
         wlssnmpAgentRuntimeServerStartTrapCount Counter64,
         wlssnmpAgentRuntimeFailedAuthenticationCount Integer32,
         wlssnmpAgentRuntimeCounterMonitorTrapCount Counter64,
         wlssnmpAgentRuntimeName OCTET STRING,
         wlssnmpAgentRuntimeFailedEncryptionCount Integer32,
         wlssnmpAgentRuntimeSNMPAgentName OCTET STRING
      }
      
   
   wlssnmpAgentRuntimeIndex OBJECT-TYPE
      SYNTAX      OCTET STRING
      MAX-ACCESS  not-accessible
      STATUS      current
      DESCRIPTION "Index column"
      ::= { wlssnmpAgentRuntimeEntry 1  }
   
   
   wlssnmpAgentRuntimeObjectName OBJECT-TYPE
      SYNTAX      OCTET STRING
      MAX-ACCESS  read-only
      STATUS      current
      DESCRIPTION "ObjectName column"
      ::= { wlssnmpAgentRuntimeEntry 2  }
   
   
   wlssnmpAgentRuntimeType OBJECT-TYPE
      SYNTAX      OCTET STRING
      MAX-ACCESS  read-only
      STATUS      current
      DESCRIPTION "Returns the type of the MBean."
      ::= { wlssnmpAgentRuntimeEntry 3  }
   
   
   wlssnmpAgentRuntimeUDPListenPort OBJECT-TYPE
      SYNTAX      Integer32
      MAX-ACCESS  read-only
      STATUS      current
      DESCRIPTION "The UDP port on which this SNMP agent is listening for incoming requests from SNMP managers. SNMP agents can also communicate through the host server's TCP listen port (7001 by default) or through a TCP port that is configured by a custom network channel."
      ::= { wlssnmpAgentRuntimeEntry 4  }
   
   
   wlssnmpAgentRuntimeLogMessageTrapCount OBJECT-TYPE
      SYNTAX      Counter64
      MAX-ACCESS  read-only
      STATUS      current
      DESCRIPTION "The number of log message notifications that this SNMP agent has sent to all trap destinations since the agent's host server was started."
      ::= { wlssnmpAgentRuntimeEntry 5  }
   
   
   wlssnmpAgentRuntimeFailedAuthorizationCount OBJECT-TYPE
      SYNTAX      Integer32
      MAX-ACCESS  read-only
      STATUS      current
      DESCRIPTION "The number of requests that this agent has rejected because an authenticated user does not have sufficient privileges to view the requested information. You use the WebLogic Server security realm to assign privileges to users."
      ::= { wlssnmpAgentRuntimeEntry 6  }
   
   
   wlssnmpAgentRuntimeRunning OBJECT-TYPE
      SYNTAX      OCTET STRING
      MAX-ACCESS  read-only
      STATUS      current
      DESCRIPTION "Indicates whether this SNMP agent is running."
      ::= { wlssnmpAgentRuntimeEntry 7  }
   
   
   wlssnmpAgentRuntimeStringMonitorTrapCount OBJECT-TYPE
      SYNTAX      Counter64
      MAX-ACCESS  read-only
      STATUS      current
      DESCRIPTION "The number of string monitor notifications that this SNMP agent has sent to all trap destinations since the agent's host server was started."
      ::= { wlssnmpAgentRuntimeEntry 8  }
   
   
   wlssnmpAgentRuntimeMonitorTrapCount OBJECT-TYPE
      SYNTAX      Counter64
      MAX-ACCESS  read-only
      STATUS      current
      DESCRIPTION "The total number of all notifications that this SNMP agent has sent to all trap destinations since the agent's host server was started."
      ::= { wlssnmpAgentRuntimeEntry 9  }
   
   
   wlssnmpAgentRuntimeMasterAgentXPort OBJECT-TYPE
      SYNTAX      Integer32
      MAX-ACCESS  read-only
      STATUS      current
      DESCRIPTION "The port that this SNMP agent uses to communicate with subagents. The agent uses subagents to provide access to custom MBeans (MBeans that you create and register) and to other BEA software components. WebLogic Server SNMP agents do not enable users to register their own subagents."
      ::= { wlssnmpAgentRuntimeEntry 10  }
   
   
   wlssnmpAgentRuntimeGaugeMonitorTrapCount OBJECT-TYPE
      SYNTAX      Counter64
      MAX-ACCESS  read-only
      STATUS      current
      DESCRIPTION "The number of gauge monitor notifications that this SNMP agent has sent to all trap destinations since the agent's host server was started."
      ::= { wlssnmpAgentRuntimeEntry 11  }
   
   
   wlssnmpAgentRuntimeServerStopTrapCount OBJECT-TYPE
      SYNTAX      Counter64
      MAX-ACCESS  read-only
      STATUS      current
      DESCRIPTION "The number of serverShutdown notifications that this SNMP agent has sent to all trap destinations since the agent's host server was started."
      ::= { wlssnmpAgentRuntimeEntry 12  }
   
   
   wlssnmpAgentRuntimeAttributeChangeTrapCount OBJECT-TYPE
      SYNTAX      Counter64
      MAX-ACCESS  read-only
      STATUS      current
      DESCRIPTION "The number of attribute change notifications that this SNMP agent has sent to all trap destinations since the agent's host server was started."
      ::= { wlssnmpAgentRuntimeEntry 13  }
   
   
   wlssnmpAgentRuntimeServerStartTrapCount OBJECT-TYPE
      SYNTAX      Counter64
      MAX-ACCESS  read-only
      STATUS      current
      DESCRIPTION "The number of serverStart notifications that this SNMP agent has sent to all trap destinations since the agent's host server was started."
      ::= { wlssnmpAgentRuntimeEntry 14  }
   
   
   wlssnmpAgentRuntimeFailedAuthenticationCount OBJECT-TYPE
      SYNTAX      Integer32
      MAX-ACCESS  read-only
      STATUS      current
      DESCRIPTION "The number of requests that this agent has rejected because of incorrect user credentials."
      ::= { wlssnmpAgentRuntimeEntry 15  }
   
   
   wlssnmpAgentRuntimeCounterMonitorTrapCount OBJECT-TYPE
      SYNTAX      Counter64
      MAX-ACCESS  read-only
      STATUS      current
      DESCRIPTION "The number of counter monitor notifications that this SNMP agent has sent to all trap destinations since the agent's host server was started."
      ::= { wlssnmpAgentRuntimeEntry 16  }
   
   
   wlssnmpAgentRuntimeName OBJECT-TYPE
      SYNTAX      OCTET STRING
      MAX-ACCESS  read-only
      STATUS      current
      DESCRIPTION "The name of this configuration. WebLogic Server uses an MBean to implement and persist the configuration."
      ::= { wlssnmpAgentRuntimeEntry 17  }
   
   
   wlssnmpAgentRuntimeFailedEncryptionCount OBJECT-TYPE
      SYNTAX      Integer32
      MAX-ACCESS  read-only
      STATUS      current
      DESCRIPTION "The number of requests that this agent has rejected because of incorrect privacy (encryption) credentials"
      ::= { wlssnmpAgentRuntimeEntry 18  }
   
   
   wlssnmpAgentRuntimeSNMPAgentName OBJECT-TYPE
      SYNTAX      OCTET STRING
      MAX-ACCESS  read-only
      STATUS      current
      DESCRIPTION ""
      ::= { wlssnmpAgentRuntimeEntry 19  }
   
   
   serverLifeCycleTaskRuntimeTable OBJECT-TYPE
      SYNTAX      SEQUENCE OF ServerLifeCycleTaskRuntimeEntry
      MAX-ACCESS  not-accessible
      STATUS      current
      DESCRIPTION "Exposes monitoring information about a server's lifecycle. Remote clients as well as clients running within a server can access this information.  An operation (task) to change a server's state will fork a separate thread to perform the actual work and immediately return an instance of this MBean to the caller. The caller can then use this MBean to track the task's progress as desired.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1345  }
      
   
   serverLifeCycleTaskRuntimeEntry OBJECT-TYPE
      SYNTAX      ServerLifeCycleTaskRuntimeEntry
      MAX-ACCESS  not-accessible
      STATUS      current
      DESCRIPTION "Generated SNMP Table Entry."
      INDEX { serverLifeCycleTaskRuntimeIndex}
      ::= { serverLifeCycleTaskRuntimeTable 1 }
      
   ServerLifeCycleTaskRuntimeEntry ::=
      SEQUENCE
      {
         serverLifeCycleTaskRuntimeIndex OCTET STRING,
         serverLifeCycleTaskRuntimeObjectName OCTET STRING,
         serverLifeCycleTaskRuntimeType OCTET STRING,
         serverLifeCycleTaskRuntimeStatus OCTET STRING,
         serverLifeCycleTaskRuntimeRunning OCTET STRING,
         serverLifeCycleTaskRuntimeBeginTime Counter64,
         serverLifeCycleTaskRuntimeOperation OCTET STRING,
         serverLifeCycleTaskRuntimeEndTime Counter64,
         serverLifeCycleTaskRuntimeServerName OCTET STRING,
         serverLifeCycleTaskRuntimeSystemTask OCTET STRING,
         serverLifeCycleTaskRuntimeDescription OCTET STRING,
         serverLifeCycleTaskRuntimeName OCTET STRING
      }
      
   
   serverLifeCycleTaskRuntimeIndex OBJECT-TYPE
      SYNTAX      OCTET STRING
      MAX-ACCESS  not-accessible
      STATUS      current
      DESCRIPTION "Index column"
      ::= { serverLifeCycleTaskRuntimeEntry 1  }
   
   
   serverLifeCycleTaskRuntimeObjectName OBJECT-TYPE
      SYNTAX      OCTET STRING
      MAX-ACCESS  read-only
      STATUS      current
      DESCRIPTION "ObjectName column"
      ::= { serverLifeCycleTaskRuntimeEntry 2  }
   
   
   serverLifeCycleTaskRuntimeType OBJECT-TYPE
      SYNTAX      OCTET STRING
      MAX-ACCESS  read-only
      STATUS      current
      DESCRIPTION "Returns the type of the MBean."
      ::= { serverLifeCycleTaskRuntimeEntry 3  }
   
   
   serverLifeCycleTaskRuntimeStatus OBJECT-TYPE
      SYNTAX      OCTET STRING
      MAX-ACCESS  read-only
      STATUS      current
      DESCRIPTION ""
      ::= { serverLifeCycleTaskRuntimeEntry 4  }
   
   
   serverLifeCycleTaskRuntimeRunning OBJECT-TYPE
      SYNTAX      OCTET STRING
      MAX-ACCESS  read-only
      STATUS      current
      DESCRIPTION ""
      ::= { serverLifeCycleTaskRuntimeEntry 5  }
   
   
   serverLifeCycleTaskRuntimeBeginTime OBJECT-TYPE
      SYNTAX      Counter64
      MAX-ACCESS  read-only
      STATUS      current
      DESCRIPTION ""
      ::= { serverLifeCycleTaskRuntimeEntry 6  }
   
   
   serverLifeCycleTaskRuntimeOperation OBJECT-TYPE
      SYNTAX      OCTET STRING
      MAX-ACCESS  read-only
      STATUS      current
      DESCRIPTION "Gets the name of the method that was invoked on the ServerLifeCycleRuntime to initiate this task."
      ::= { serverLifeCycleTaskRuntimeEntry 7  }
   
   
   serverLifeCycleTaskRuntimeEndTime OBJECT-TYPE
      SYNTAX      Counter64
      MAX-ACCESS  read-only
      STATUS      current
      DESCRIPTION ""
      ::= { serverLifeCycleTaskRuntimeEntry 8  }
   
   
   serverLifeCycleTaskRuntimeServerName OBJECT-TYPE
      SYNTAX      OCTET STRING
      MAX-ACCESS  read-only
      STATUS      current
      DESCRIPTION "The name of the server."
      ::= { serverLifeCycleTaskRuntimeEntry 9  }
   
   
   serverLifeCycleTaskRuntimeSystemTask OBJECT-TYPE
      SYNTAX      OCTET STRING
      MAX-ACCESS  read-only
      STATUS      current
      DESCRIPTION ""
      ::= { serverLifeCycleTaskRuntimeEntry 10  }
   
   
   serverLifeCycleTaskRuntimeDescription OBJECT-TYPE
      SYNTAX      OCTET STRING
      MAX-ACCESS  read-only
      STATUS      current
      DESCRIPTION ""
      ::= { serverLifeCycleTaskRuntimeEntry 11  }
   
   
   serverLifeCycleTaskRuntimeName OBJECT-TYPE
      SYNTAX      OCTET STRING
      MAX-ACCESS  read-only
      STATUS      current
      DESCRIPTION "The name of this configuration. WebLogic Server uses an MBean to implement and persist the configuration."
      ::= { serverLifeCycleTaskRuntimeEntry 12  }
   
   
   serverMigrationRuntimeTable OBJECT-TYPE
      SYNTAX      SEQUENCE OF ServerMigrationRuntimeEntry
      MAX-ACCESS  not-accessible
      STATUS      current
      DESCRIPTION "ServerMigrationRuntimeMBean provides runtime monitoring information about the past migrations performed by this server as the cluster master. If this server was never the cluster master then no information would be available. This RuntimeMBean would be hosted on all cluster members and can be queried for the location of the cluster master which is just another peer in the cluster. JMX clients can make another call to the server hosting the cluster master functionality to get the migration history.  Please note that the migration history is not persisted and is lost when a server is shutdown."
      ::= { wls 1350  }
      
   
   serverMigrationRuntimeEntry OBJECT-TYPE
      SYNTAX      ServerMigrationRuntimeEntry
      MAX-ACCESS  not-accessible
      STATUS      current
      DESCRIPTION "Generated SNMP Table Entry."
      INDEX { serverMigrationRuntimeIndex}
      ::= { serverMigrationRuntimeTable 1 }
      
   ServerMigrationRuntimeEntry ::=
      SEQUENCE
      {
         serverMigrationRuntimeIndex OCTET STRING,
         serverMigrationRuntimeObjectName OCTET STRING,
         serverMigrationRuntimeType OCTET STRING,
         serverMigrationRuntimeClusterMaster OCTET STRING,
         serverMigrationRuntimeClusterMasterName OCTET STRING,
         serverMigrationRuntimeName OCTET STRING
      }
      
   
   serverMigrationRuntimeIndex OBJECT-TYPE
      SYNTAX      OCTET STRING
      MAX-ACCESS  not-accessible
      STATUS      current
      DESCRIPTION "Index column"
      ::= { serverMigrationRuntimeEntry 1  }
   
   
   serverMigrationRuntimeObjectName OBJECT-TYPE
      SYNTAX      OCTET STRING
      MAX-ACCESS  read-only
      STATUS      current
      DESCRIPTION "ObjectName column"
      ::= { serverMigrationRuntimeEntry 2  }
   
   
   serverMigrationRuntimeType OBJECT-TYPE
      SYNTAX      OCTET STRING
      MAX-ACCESS  read-only
      STATUS      current
      DESCRIPTION "Returns the type of the MBean."
      ::= { serverMigrationRuntimeEntry 3  }
   
   
   serverMigrationRuntimeClusterMaster OBJECT-TYPE
      SYNTAX      OCTET STRING
      MAX-ACCESS  read-only
      STATUS      current
      DESCRIPTION "Is the current server the cluster master?"
      ::= { serverMigrationRuntimeEntry 4  }
   
   
   serverMigrationRuntimeClusterMasterName OBJECT-TYPE
      SYNTAX      OCTET STRING
      MAX-ACCESS  read-only
      STATUS      current
      DESCRIPTION "Returns the server name who is the cluster master. Migration history is only available from the cluster master."
      ::= { serverMigrationRuntimeEntry 5  }
   
   
   serverMigrationRuntimeName OBJECT-TYPE
      SYNTAX      OCTET STRING
      MAX-ACCESS  read-only
      STATUS      current
      DESCRIPTION "The name of this configuration. WebLogic Server uses an MBean to implement and persist the configuration."
      ::= { serverMigrationRuntimeEntry 6  }
   
   
   serviceMigrationDataRuntimeTable OBJECT-TYPE
      SYNTAX      SEQUENCE OF ServiceMigrationDataRuntimeEntry
      MAX-ACCESS  not-accessible
      STATUS      current
      DESCRIPTION "Runtime information about one past or ongoing migration."
      ::= { wls 1355  }
      
   
   serviceMigrationDataRuntimeEntry OBJECT-TYPE
      SYNTAX      ServiceMigrationDataRuntimeEntry
      MAX-ACCESS  not-accessible
      STATUS      current
      DESCRIPTION "Generated SNMP Table Entry."
      INDEX { serviceMigrationDataRuntimeIndex}
      ::= { serviceMigrationDataRuntimeTable 1 }
      
   ServiceMigrationDataRuntimeEntry ::=
      SEQUENCE
      {
         serviceMigrationDataRuntimeIndex OCTET STRING,
         serviceMigrationDataRuntimeObjectName OCTET STRING,
         serviceMigrationDataRuntimeType OCTET STRING,
         serviceMigrationDataRuntimeStatus Integer32,
         serviceMigrationDataRuntimeMigrationStartTime Counter64,
         serviceMigrationDataRuntimeMigratedFrom OCTET STRING,
         serviceMigrationDataRuntimeServerName OCTET STRING,
         serviceMigrationDataRuntimeMigratedTo OCTET STRING,
         serviceMigrationDataRuntimeMigrationEndTime Counter64,
         serviceMigrationDataRuntimeClusterName OCTET STRING,
         serviceMigrationDataRuntimeName OCTET STRING,
         serviceMigrationDataRuntimeCoordinatorName OCTET STRING
      }
      
   
   serviceMigrationDataRuntimeIndex OBJECT-TYPE
      SYNTAX      OCTET STRING
      MAX-ACCESS  not-accessible
      STATUS      current
      DESCRIPTION "Index column"
      ::= { serviceMigrationDataRuntimeEntry 1  }
   
   
   serviceMigrationDataRuntimeObjectName OBJECT-TYPE
      SYNTAX      OCTET STRING
      MAX-ACCESS  read-only
      STATUS      current
      DESCRIPTION "ObjectName column"
      ::= { serviceMigrationDataRuntimeEntry 2  }
   
   
   serviceMigrationDataRuntimeType OBJECT-TYPE
      SYNTAX      OCTET STRING
      MAX-ACCESS  read-only
      STATUS      current
      DESCRIPTION "Returns the type of the MBean."
      ::= { serviceMigrationDataRuntimeEntry 3  }
   
   
   serviceMigrationDataRuntimeStatus OBJECT-TYPE
      SYNTAX      Integer32
      MAX-ACCESS  read-only
      STATUS      current
      DESCRIPTION "Status of the migration (SUCCESSFUL, IN_PROGRESS, or FAILED)"
      ::= { serviceMigrationDataRuntimeEntry 4  }
   
   
   serviceMigrationDataRuntimeMigrationStartTime OBJECT-TYPE
      SYNTAX      Counter64
      MAX-ACCESS  read-only
      STATUS      current
      DESCRIPTION "Start time of migration"
      ::= { serviceMigrationDataRuntimeEntry 5  }
   
   
   serviceMigrationDataRuntimeMigratedFrom OBJECT-TYPE
      SYNTAX      OCTET STRING
      MAX-ACCESS  read-only
      STATUS      current
      DESCRIPTION "Where this object was migrated from"
      ::= { serviceMigrationDataRuntimeEntry 6  }
   
   
   serviceMigrationDataRuntimeServerName OBJECT-TYPE
      SYNTAX      OCTET STRING
      MAX-ACCESS  read-only
      STATUS      current
      DESCRIPTION "Name of the object migrated"
      ::= { serviceMigrationDataRuntimeEntry 7  }
   
   
   serviceMigrationDataRuntimeMigratedTo OBJECT-TYPE
      SYNTAX      OCTET STRING
      MAX-ACCESS  read-only
      STATUS      current
      DESCRIPTION "Where this object was migrated to"
      ::= { serviceMigrationDataRuntimeEntry 8  }
   
   
   serviceMigrationDataRuntimeMigrationEndTime OBJECT-TYPE
      SYNTAX      Counter64
      MAX-ACCESS  read-only
      STATUS      current
      DESCRIPTION "End time of migration"
      ::= { serviceMigrationDataRuntimeEntry 9  }
   
   
   serviceMigrationDataRuntimeClusterName OBJECT-TYPE
      SYNTAX      OCTET STRING
      MAX-ACCESS  read-only
      STATUS      current
      DESCRIPTION "Name of the cluster"
      ::= { serviceMigrationDataRuntimeEntry 10  }
   
   
   serviceMigrationDataRuntimeName OBJECT-TYPE
      SYNTAX      OCTET STRING
      MAX-ACCESS  read-only
      STATUS      current
      DESCRIPTION "The name of this configuration. WebLogic Server uses an MBean to implement and persist the configuration."
      ::= { serviceMigrationDataRuntimeEntry 11  }
   
   
   serviceMigrationDataRuntimeCoordinatorName OBJECT-TYPE
      SYNTAX      OCTET STRING
      MAX-ACCESS  read-only
      STATUS      current
      DESCRIPTION "Name of the server that acted as the coordinator for this migration."
      ::= { serviceMigrationDataRuntimeEntry 12  }
   
   
   serviceMigrationRuntimeTable OBJECT-TYPE
      SYNTAX      SEQUENCE OF ServiceMigrationRuntimeEntry
      MAX-ACCESS  not-accessible
      STATUS      current
      DESCRIPTION "ServiceMigrationRuntimeMBean provides runtime monitoring information about the past migrations performed by this server as the cluster master. If this server was never the cluster master then no information would be available. This RuntimeMBean would be hosted on all cluster members and can be queried for the location of the cluster master which is just another peer in the cluster. JMX clients can make another call to the server hosting the cluster master functionality to get the migration history.  Please note that the migration history is not persisted and is lost when a server is shutdown."
      ::= { wls 1360  }
      
   
   serviceMigrationRuntimeEntry OBJECT-TYPE
      SYNTAX      ServiceMigrationRuntimeEntry
      MAX-ACCESS  not-accessible
      STATUS      current
      DESCRIPTION "Generated SNMP Table Entry."
      INDEX { serviceMigrationRuntimeIndex}
      ::= { serviceMigrationRuntimeTable 1 }
      
   ServiceMigrationRuntimeEntry ::=
      SEQUENCE
      {
         serviceMigrationRuntimeIndex OCTET STRING,
         serviceMigrationRuntimeObjectName OCTET STRING,
         serviceMigrationRuntimeType OCTET STRING,
         serviceMigrationRuntimeClusterMaster OCTET STRING,
         serviceMigrationRuntimeClusterMasterName OCTET STRING,
         serviceMigrationRuntimeName OCTET STRING
      }
      
   
   serviceMigrationRuntimeIndex OBJECT-TYPE
      SYNTAX      OCTET STRING
      MAX-ACCESS  not-accessible
      STATUS      current
      DESCRIPTION "Index column"
      ::= { serviceMigrationRuntimeEntry 1  }
   
   
   serviceMigrationRuntimeObjectName OBJECT-TYPE
      SYNTAX      OCTET STRING
      MAX-ACCESS  read-only
      STATUS      current
      DESCRIPTION "ObjectName column"
      ::= { serviceMigrationRuntimeEntry 2  }
   
   
   serviceMigrationRuntimeType OBJECT-TYPE
      SYNTAX      OCTET STRING
      MAX-ACCESS  read-only
      STATUS      current
      DESCRIPTION "Returns the type of the MBean."
      ::= { serviceMigrationRuntimeEntry 3  }
   
   
   serviceMigrationRuntimeClusterMaster OBJECT-TYPE
      SYNTAX      OCTET STRING
      MAX-ACCESS  read-only
      STATUS      current
      DESCRIPTION "Is the current server the cluster master?"
      ::= { serviceMigrationRuntimeEntry 4  }
   
   
   serviceMigrationRuntimeClusterMasterName OBJECT-TYPE
      SYNTAX      OCTET STRING
      MAX-ACCESS  read-only
      STATUS      current
      DESCRIPTION "Returns the server name who is the cluster master. Migration history is only available from the cluster master."
      ::= { serviceMigrationRuntimeEntry 5  }
   
   
   serviceMigrationRuntimeName OBJECT-TYPE
      SYNTAX      OCTET STRING
      MAX-ACCESS  read-only
      STATUS      current
      DESCRIPTION "The name of this configuration. WebLogic Server uses an MBean to implement and persist the configuration."
      ::= { serviceMigrationRuntimeEntry 6  }
   
   
   singleSignOnServicesRuntimeTable OBJECT-TYPE
      SYNTAX      SEQUENCE OF SingleSignOnServicesRuntimeEntry
      MAX-ACCESS  not-accessible
      STATUS      current
      DESCRIPTION "This interface is used to publish SAML 2.0 local site meta-data for single sign-on services."
      ::= { wls 1365  }
      
   
   singleSignOnServicesRuntimeEntry OBJECT-TYPE
      SYNTAX      SingleSignOnServicesRuntimeEntry
      MAX-ACCESS  not-accessible
      STATUS      current
      DESCRIPTION "Generated SNMP Table Entry."
      INDEX { singleSignOnServicesRuntimeIndex}
      ::= { singleSignOnServicesRuntimeTable 1 }
      
   SingleSignOnServicesRuntimeEntry ::=
      SEQUENCE
      {
         singleSignOnServicesRuntimeIndex OCTET STRING,
         singleSignOnServicesRuntimeObjectName OCTET STRING,
         singleSignOnServicesRuntimeType OCTET STRING,
         singleSignOnServicesRuntimeName OCTET STRING
      }
      
   
   singleSignOnServicesRuntimeIndex OBJECT-TYPE
      SYNTAX      OCTET STRING
      MAX-ACCESS  not-accessible
      STATUS      current
      DESCRIPTION "Index column"
      ::= { singleSignOnServicesRuntimeEntry 1  }
   
   
   singleSignOnServicesRuntimeObjectName OBJECT-TYPE
      SYNTAX      OCTET STRING
      MAX-ACCESS  read-only
      STATUS      current
      DESCRIPTION "ObjectName column"
      ::= { singleSignOnServicesRuntimeEntry 2  }
   
   
   singleSignOnServicesRuntimeType OBJECT-TYPE
      SYNTAX      OCTET STRING
      MAX-ACCESS  read-only
      STATUS      current
      DESCRIPTION "Returns the type of the MBean."
      ::= { singleSignOnServicesRuntimeEntry 3  }
   
   
   singleSignOnServicesRuntimeName OBJECT-TYPE
      SYNTAX      OCTET STRING
      MAX-ACCESS  read-only
      STATUS      current
      DESCRIPTION "The name of this configuration. WebLogic Server uses an MBean to implement and persist the configuration."
      ::= { singleSignOnServicesRuntimeEntry 4  }
   
   
   springAdviceRuntimeTable OBJECT-TYPE
      SYNTAX      SEQUENCE OF SpringAdviceRuntimeEntry
      MAX-ACCESS  not-accessible
      STATUS      current
      DESCRIPTION ""
      ::= { wls 1370  }
      
   
   springAdviceRuntimeEntry OBJECT-TYPE
      SYNTAX      SpringAdviceRuntimeEntry
      MAX-ACCESS  not-accessible
      STATUS      current
      DESCRIPTION "Generated SNMP Table Entry."
      INDEX { springAdviceRuntimeIndex}
      ::= { springAdviceRuntimeTable 1 }
      
   SpringAdviceRuntimeEntry ::=
      SEQUENCE
      {
         springAdviceRuntimeIndex OCTET STRING,
         springAdviceRuntimeObjectName OCTET STRING,
         springAdviceRuntimeType OCTET STRING,
         springAdviceRuntimeLazyInit OCTET STRING,
         springAdviceRuntimeResourceDescription OCTET STRING,
         springAdviceRuntimeAbstract OCTET STRING,
         springAdviceRuntimeBeanId OCTET STRING,
         springAdviceRuntimeBeanClassname OCTET STRING,
         springAdviceRuntimeTransactional OCTET STRING,
         springAdviceRuntimeSingleton OCTET STRING,
         springAdviceRuntimeTransactionManager OCTET STRING,
         springAdviceRuntimeName OCTET STRING
      }
      
   
   springAdviceRuntimeIndex OBJECT-TYPE
      SYNTAX      OCTET STRING
      MAX-ACCESS  not-accessible
      STATUS      current
      DESCRIPTION "Index column"
      ::= { springAdviceRuntimeEntry 1  }
   
   
   springAdviceRuntimeObjectName OBJECT-TYPE
      SYNTAX      OCTET STRING
      MAX-ACCESS  read-only
      STATUS      current
      DESCRIPTION "ObjectName column"
      ::= { springAdviceRuntimeEntry 2  }
   
   
   springAdviceRuntimeType OBJECT-TYPE
      SYNTAX      OCTET STRING
      MAX-ACCESS  read-only
      STATUS      current
      DESCRIPTION "Returns the type of the MBean."
      ::= { springAdviceRuntimeEntry 3  }
   
   
   springAdviceRuntimeLazyInit OBJECT-TYPE
      SYNTAX      OCTET STRING
      MAX-ACCESS  read-only
      STATUS      current
      DESCRIPTION ""
      ::= { springAdviceRuntimeEntry 4  }
   
   
   springAdviceRuntimeResourceDescription OBJECT-TYPE
      SYNTAX      OCTET STRING
      MAX-ACCESS  read-only
      STATUS      current
      DESCRIPTION ""
      ::= { springAdviceRuntimeEntry 5  }
   
   
   springAdviceRuntimeAbstract OBJECT-TYPE
      SYNTAX      OCTET STRING
      MAX-ACCESS  read-only
      STATUS      current
      DESCRIPTION ""
      ::= { springAdviceRuntimeEntry 6  }
   
   
   springAdviceRuntimeBeanId OBJECT-TYPE
      SYNTAX      OCTET STRING
      MAX-ACCESS  read-only
      STATUS      current
      DESCRIPTION ""
      ::= { springAdviceRuntimeEntry 7  }
   
   
   springAdviceRuntimeBeanClassname OBJECT-TYPE
      SYNTAX      OCTET STRING
      MAX-ACCESS  read-only
      STATUS      current
      DESCRIPTION ""
      ::= { springAdviceRuntimeEntry 8  }
   
   
   springAdviceRuntimeTransactional OBJECT-TYPE
      SYNTAX      OCTET STRING
      MAX-ACCESS  read-only
      STATUS      current
      DESCRIPTION ""
      ::= { springAdviceRuntimeEntry 9  }
   
   
   springAdviceRuntimeSingleton OBJECT-TYPE
      SYNTAX      OCTET STRING
      MAX-ACCESS  read-only
      STATUS      current
      DESCRIPTION ""
      ::= { springAdviceRuntimeEntry 10  }
   
   
   springAdviceRuntimeTransactionManager OBJECT-TYPE
      SYNTAX      OCTET STRING
      MAX-ACCESS  read-only
      STATUS      current
      DESCRIPTION ""
      ::= { springAdviceRuntimeEntry 11  }
   
   
   springAdviceRuntimeName OBJECT-TYPE
      SYNTAX      OCTET STRING
      MAX-ACCESS  read-only
      STATUS      current
      DESCRIPTION "The name of this configuration. WebLogic Server uses an MBean to implement and persist the configuration."
      ::= { springAdviceRuntimeEntry 12  }
   
   
   springAdvisorRuntimeTable OBJECT-TYPE
      SYNTAX      SEQUENCE OF SpringAdvisorRuntimeEntry
      MAX-ACCESS  not-accessible
      STATUS      current
      DESCRIPTION ""
      ::= { wls 1375  }
      
   
   springAdvisorRuntimeEntry OBJECT-TYPE
      SYNTAX      SpringAdvisorRuntimeEntry
      MAX-ACCESS  not-accessible
      STATUS      current
      DESCRIPTION "Generated SNMP Table Entry."
      INDEX { springAdvisorRuntimeIndex}
      ::= { springAdvisorRuntimeTable 1 }
      
   SpringAdvisorRuntimeEntry ::=
      SEQUENCE
      {
         springAdvisorRuntimeIndex OCTET STRING,
         springAdvisorRuntimeObjectName OCTET STRING,
         springAdvisorRuntimeType OCTET STRING,
         springAdvisorRuntimeLazyInit OCTET STRING,
         springAdvisorRuntimeResourceDescription OCTET STRING,
         springAdvisorRuntimeAbstract OCTET STRING,
         springAdvisorRuntimeBeanId OCTET STRING,
         springAdvisorRuntimeBeanClassname OCTET STRING,
         springAdvisorRuntimeTransactional OCTET STRING,
         springAdvisorRuntimeSingleton OCTET STRING,
         springAdvisorRuntimeName OCTET STRING
      }
      
   
   springAdvisorRuntimeIndex OBJECT-TYPE
      SYNTAX      OCTET STRING
      MAX-ACCESS  not-accessible
      STATUS      current
      DESCRIPTION "Index column"
      ::= { springAdvisorRuntimeEntry 1  }
   
   
   springAdvisorRuntimeObjectName OBJECT-TYPE
      SYNTAX      OCTET STRING
      MAX-ACCESS  read-only
      STATUS      current
      DESCRIPTION "ObjectName column"
      ::= { springAdvisorRuntimeEntry 2  }
   
   
   springAdvisorRuntimeType OBJECT-TYPE
      SYNTAX      OCTET STRING
      MAX-ACCESS  read-only
      STATUS      current
      DESCRIPTION "Returns the type of the MBean."
      ::= { springAdvisorRuntimeEntry 3  }
   
   
   springAdvisorRuntimeLazyInit OBJECT-TYPE
      SYNTAX      OCTET STRING
      MAX-ACCESS  read-only
      STATUS      current
      DESCRIPTION ""
      ::= { springAdvisorRuntimeEntry 4  }
   
   
   springAdvisorRuntimeResourceDescription OBJECT-TYPE
      SYNTAX      OCTET STRING
      MAX-ACCESS  read-only
      STATUS      current
      DESCRIPTION ""
      ::= { springAdvisorRuntimeEntry 5  }
   
   
   springAdvisorRuntimeAbstract OBJECT-TYPE
      SYNTAX      OCTET STRING
      MAX-ACCESS  read-only
      STATUS      current
      DESCRIPTION ""
      ::= { springAdvisorRuntimeEntry 6  }
   
   
   springAdvisorRuntimeBeanId OBJECT-TYPE
      SYNTAX      OCTET STRING
      MAX-ACCESS  read-only
      STATUS      current
      DESCRIPTION ""
      ::= { springAdvisorRuntimeEntry 7  }
   
   
   springAdvisorRuntimeBeanClassname OBJECT-TYPE
      SYNTAX      OCTET STRING
      MAX-ACCESS  read-only
      STATUS      current
      DESCRIPTION ""
      ::= { springAdvisorRuntimeEntry 8  }
   
   
   springAdvisorRuntimeTransactional OBJECT-TYPE
      SYNTAX      OCTET STRING
      MAX-ACCESS  read-only
      STATUS      current
      DESCRIPTION ""
      ::= { springAdvisorRuntimeEntry 9  }
   
   
   springAdvisorRuntimeSingleton OBJECT-TYPE
      SYNTAX      OCTET STRING
      MAX-ACCESS  read-only
      STATUS      current
      DESCRIPTION ""
      ::= { springAdvisorRuntimeEntry 10  }
   
   
   springAdvisorRuntimeName OBJECT-TYPE
      SYNTAX      OCTET STRING
      MAX-ACCESS  read-only
      STATUS      current
      DESCRIPTION "The name of this configuration. WebLogic Server uses an MBean to implement and persist the configuration."
      ::= { springAdvisorRuntimeEntry 11  }
   
   
   springPointcutRuntimeTable OBJECT-TYPE
      SYNTAX      SEQUENCE OF SpringPointcutRuntimeEntry
      MAX-ACCESS  not-accessible
      STATUS      current
      DESCRIPTION ""
      ::= { wls 1380  }
      
   
   springPointcutRuntimeEntry OBJECT-TYPE
      SYNTAX      SpringPointcutRuntimeEntry
      MAX-ACCESS  not-accessible
      STATUS      current
      DESCRIPTION "Generated SNMP Table Entry."
      INDEX { springPointcutRuntimeIndex}
      ::= { springPointcutRuntimeTable 1 }
      
   SpringPointcutRuntimeEntry ::=
      SEQUENCE
      {
         springPointcutRuntimeIndex OCTET STRING,
         springPointcutRuntimeObjectName OCTET STRING,
         springPointcutRuntimeType OCTET STRING,
         springPointcutRuntimeLazyInit OCTET STRING,
         springPointcutRuntimeResourceDescription OCTET STRING,
         springPointcutRuntimeAbstract OCTET STRING,
         springPointcutRuntimeBeanId OCTET STRING,
         springPointcutRuntimeBeanClassname OCTET STRING,
         springPointcutRuntimeExpression OCTET STRING,
         springPointcutRuntimeTransactional OCTET STRING,
         springPointcutRuntimeSingleton OCTET STRING,
         springPointcutRuntimeName OCTET STRING
      }
      
   
   springPointcutRuntimeIndex OBJECT-TYPE
      SYNTAX      OCTET STRING
      MAX-ACCESS  not-accessible
      STATUS      current
      DESCRIPTION "Index column"
      ::= { springPointcutRuntimeEntry 1  }
   
   
   springPointcutRuntimeObjectName OBJECT-TYPE
      SYNTAX      OCTET STRING
      MAX-ACCESS  read-only
      STATUS      current
      DESCRIPTION "ObjectName column"
      ::= { springPointcutRuntimeEntry 2  }
   
   
   springPointcutRuntimeType OBJECT-TYPE
      SYNTAX      OCTET STRING
      MAX-ACCESS  read-only
      STATUS      current
      DESCRIPTION "Returns the type of the MBean."
      ::= { springPointcutRuntimeEntry 3  }
   
   
   springPointcutRuntimeLazyInit OBJECT-TYPE
      SYNTAX      OCTET STRING
      MAX-ACCESS  read-only
      STATUS      current
      DESCRIPTION ""
      ::= { springPointcutRuntimeEntry 4  }
   
   
   springPointcutRuntimeResourceDescription OBJECT-TYPE
      SYNTAX      OCTET STRING
      MAX-ACCESS  read-only
      STATUS      current
      DESCRIPTION ""
      ::= { springPointcutRuntimeEntry 5  }
   
   
   springPointcutRuntimeAbstract OBJECT-TYPE
      SYNTAX      OCTET STRING
      MAX-ACCESS  read-only
      STATUS      current
      DESCRIPTION ""
      ::= { springPointcutRuntimeEntry 6  }
   
   
   springPointcutRuntimeBeanId OBJECT-TYPE
      SYNTAX      OCTET STRING
      MAX-ACCESS  read-only
      STATUS      current
      DESCRIPTION ""
      ::= { springPointcutRuntimeEntry 7  }
   
   
   springPointcutRuntimeBeanClassname OBJECT-TYPE
      SYNTAX      OCTET STRING
      MAX-ACCESS  read-only
      STATUS      current
      DESCRIPTION ""
      ::= { springPointcutRuntimeEntry 8  }
   
   
   springPointcutRuntimeExpression OBJECT-TYPE
      SYNTAX      OCTET STRING
      MAX-ACCESS  read-only
      STATUS      current
      DESCRIPTION ""
      ::= { springPointcutRuntimeEntry 9  }
   
   
   springPointcutRuntimeTransactional OBJECT-TYPE
      SYNTAX      OCTET STRING
      MAX-ACCESS  read-only
      STATUS      current
      DESCRIPTION ""
      ::= { springPointcutRuntimeEntry 10  }
   
   
   springPointcutRuntimeSingleton OBJECT-TYPE
      SYNTAX      OCTET STRING
      MAX-ACCESS  read-only
      STATUS      current
      DESCRIPTION ""
      ::= { springPointcutRuntimeEntry 11  }
   
   
   springPointcutRuntimeName OBJECT-TYPE
      SYNTAX      OCTET STRING
      MAX-ACCESS  read-only
      STATUS      current
      DESCRIPTION "The name of this configuration. WebLogic Server uses an MBean to implement and persist the configuration."
      ::= { springPointcutRuntimeEntry 12  }
   
   
   springRuntimeTable OBJECT-TYPE
      SYNTAX      SEQUENCE OF SpringRuntimeEntry
      MAX-ACCESS  not-accessible
      STATUS      current
      DESCRIPTION ""
      ::= { wls 1385  }
      
   
   springRuntimeEntry OBJECT-TYPE
      SYNTAX      SpringRuntimeEntry
      MAX-ACCESS  not-accessible
      STATUS      current
      DESCRIPTION "Generated SNMP Table Entry."
      INDEX { springRuntimeIndex}
      ::= { springRuntimeTable 1 }
      
   SpringRuntimeEntry ::=
      SEQUENCE
      {
         springRuntimeIndex   OCTET STRING,
         springRuntimeObjectName OCTET STRING,
         springRuntimeType    OCTET STRING,
         springRuntimeName    OCTET STRING
      }
      
   
   springRuntimeIndex OBJECT-TYPE
      SYNTAX      OCTET STRING
      MAX-ACCESS  not-accessible
      STATUS      current
      DESCRIPTION "Index column"
      ::= { springRuntimeEntry 1  }
   
   
   springRuntimeObjectName OBJECT-TYPE
      SYNTAX      OCTET STRING
      MAX-ACCESS  read-only
      STATUS      current
      DESCRIPTION "ObjectName column"
      ::= { springRuntimeEntry 2  }
   
   
   springRuntimeType OBJECT-TYPE
      SYNTAX      OCTET STRING
      MAX-ACCESS  read-only
      STATUS      current
      DESCRIPTION "Returns the type of the MBean."
      ::= { springRuntimeEntry 3  }
   
   
   springRuntimeName OBJECT-TYPE
      SYNTAX      OCTET STRING
      MAX-ACCESS  read-only
      STATUS      current
      DESCRIPTION "The name of this configuration. WebLogic Server uses an MBean to implement and persist the configuration."
      ::= { springRuntimeEntry 4  }
   
   
   springTransactionManagerRuntimeTable OBJECT-TYPE
      SYNTAX      SEQUENCE OF SpringTransactionManagerRuntimeEntry
      MAX-ACCESS  not-accessible
      STATUS      current
      DESCRIPTION ""
      ::= { wls 1390  }
      
   
   springTransactionManagerRuntimeEntry OBJECT-TYPE
      SYNTAX      SpringTransactionManagerRuntimeEntry
      MAX-ACCESS  not-accessible
      STATUS      current
      DESCRIPTION "Generated SNMP Table Entry."
      INDEX { springTransactionManagerRuntimeIndex}
      ::= { springTransactionManagerRuntimeTable 1 }
      
   SpringTransactionManagerRuntimeEntry ::=
      SEQUENCE
      {
         springTransactionManagerRuntimeIndex OCTET STRING,
         springTransactionManagerRuntimeObjectName OCTET STRING,
         springTransactionManagerRuntimeType OCTET STRING,
         springTransactionManagerRuntimeDataSource OCTET STRING,
         springTransactionManagerRuntimeEntityManagerFactory OCTET STRING,
         springTransactionManagerRuntimeLazyInit OCTET STRING,
         springTransactionManagerRuntimeResourceDescription OCTET STRING,
         springTransactionManagerRuntimeRollbackOnCommitFailure OCTET STRING,
         springTransactionManagerRuntimeDefaultTimeout Integer32,
         springTransactionManagerRuntimeFailEarlyOnGlobalRollbackOnly OCTET STRING,
         springTransactionManagerRuntimeAbstract OCTET STRING,
         springTransactionManagerRuntimeGlobalRollbackOnParticipationFailure OCTET STRING,
         springTransactionManagerRuntimeBeanId OCTET STRING,
         springTransactionManagerRuntimeNestedTransactionAllowed OCTET STRING,
         springTransactionManagerRuntimeBeanClassname OCTET STRING,
         springTransactionManagerRuntimeSingleton OCTET STRING,
         springTransactionManagerRuntimeName OCTET STRING,
         springTransactionManagerRuntimeTransactionSynchronization OCTET STRING
      }
      
   
   springTransactionManagerRuntimeIndex OBJECT-TYPE
      SYNTAX      OCTET STRING
      MAX-ACCESS  not-accessible
      STATUS      current
      DESCRIPTION "Index column"
      ::= { springTransactionManagerRuntimeEntry 1  }
   
   
   springTransactionManagerRuntimeObjectName OBJECT-TYPE
      SYNTAX      OCTET STRING
      MAX-ACCESS  read-only
      STATUS      current
      DESCRIPTION "ObjectName column"
      ::= { springTransactionManagerRuntimeEntry 2  }
   
   
   springTransactionManagerRuntimeType OBJECT-TYPE
      SYNTAX      OCTET STRING
      MAX-ACCESS  read-only
      STATUS      current
      DESCRIPTION "Returns the type of the MBean."
      ::= { springTransactionManagerRuntimeEntry 3  }
   
   
   springTransactionManagerRuntimeDataSource OBJECT-TYPE
      SYNTAX      OCTET STRING
      MAX-ACCESS  read-only
      STATUS      current
      DESCRIPTION ""
      ::= { springTransactionManagerRuntimeEntry 4  }
   
   
   springTransactionManagerRuntimeEntityManagerFactory OBJECT-TYPE
      SYNTAX      OCTET STRING
      MAX-ACCESS  read-only
      STATUS      current
      DESCRIPTION ""
      ::= { springTransactionManagerRuntimeEntry 5  }
   
   
   springTransactionManagerRuntimeLazyInit OBJECT-TYPE
      SYNTAX      OCTET STRING
      MAX-ACCESS  read-only
      STATUS      current
      DESCRIPTION ""
      ::= { springTransactionManagerRuntimeEntry 6  }
   
   
   springTransactionManagerRuntimeResourceDescription OBJECT-TYPE
      SYNTAX      OCTET STRING
      MAX-ACCESS  read-only
      STATUS      current
      DESCRIPTION ""
      ::= { springTransactionManagerRuntimeEntry 7  }
   
   
   springTransactionManagerRuntimeRollbackOnCommitFailure OBJECT-TYPE
      SYNTAX      OCTET STRING
      MAX-ACCESS  read-only
      STATUS      current
      DESCRIPTION ""
      ::= { springTransactionManagerRuntimeEntry 8  }
   
   
   springTransactionManagerRuntimeDefaultTimeout OBJECT-TYPE
      SYNTAX      Integer32
      MAX-ACCESS  read-only
      STATUS      current
      DESCRIPTION ""
      ::= { springTransactionManagerRuntimeEntry 9  }
   
   
   springTransactionManagerRuntimeFailEarlyOnGlobalRollbackOnly OBJECT-TYPE
      SYNTAX      OCTET STRING
      MAX-ACCESS  read-only
      STATUS      current
      DESCRIPTION ""
      ::= { springTransactionManagerRuntimeEntry 10  }
   
   
   springTransactionManagerRuntimeAbstract OBJECT-TYPE
      SYNTAX      OCTET STRING
      MAX-ACCESS  read-only
      STATUS      current
      DESCRIPTION ""
      ::= { springTransactionManagerRuntimeEntry 11  }
   
   
   springTransactionManagerRuntimeGlobalRollbackOnParticipationFailure OBJECT-TYPE
      SYNTAX      OCTET STRING
      MAX-ACCESS  read-only
      STATUS      current
      DESCRIPTION ""
      ::= { springTransactionManagerRuntimeEntry 12  }
   
   
   springTransactionManagerRuntimeBeanId OBJECT-TYPE
      SYNTAX      OCTET STRING
      MAX-ACCESS  read-only
      STATUS      current
      DESCRIPTION ""
      ::= { springTransactionManagerRuntimeEntry 13  }
   
   
   springTransactionManagerRuntimeNestedTransactionAllowed OBJECT-TYPE
      SYNTAX      OCTET STRING
      MAX-ACCESS  read-only
      STATUS      current
      DESCRIPTION ""
      ::= { springTransactionManagerRuntimeEntry 14  }
   
   
   springTransactionManagerRuntimeBeanClassname OBJECT-TYPE
      SYNTAX      OCTET STRING
      MAX-ACCESS  read-only
      STATUS      current
      DESCRIPTION ""
      ::= { springTransactionManagerRuntimeEntry 15  }
   
   
   springTransactionManagerRuntimeSingleton OBJECT-TYPE
      SYNTAX      OCTET STRING
      MAX-ACCESS  read-only
      STATUS      current
      DESCRIPTION ""
      ::= { springTransactionManagerRuntimeEntry 16  }
   
   
   springTransactionManagerRuntimeName OBJECT-TYPE
      SYNTAX      OCTET STRING
      MAX-ACCESS  read-only
      STATUS      current
      DESCRIPTION "The name of this configuration. WebLogic Server uses an MBean to implement and persist the configuration."
      ::= { springTransactionManagerRuntimeEntry 17  }
   
   
   springTransactionManagerRuntimeTransactionSynchronization OBJECT-TYPE
      SYNTAX      OCTET STRING
      MAX-ACCESS  read-only
      STATUS      current
      DESCRIPTION ""
      ::= { springTransactionManagerRuntimeEntry 18  }
   
   
   statefulEJBRuntimeTable OBJECT-TYPE
      SYNTAX      SEQUENCE OF StatefulEJBRuntimeEntry
      MAX-ACCESS  not-accessible
      STATUS      current
      DESCRIPTION "This interface contains accessor methods for all EJB runtime information collected for a Stateful Session Bean.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1395  }
      
   
   statefulEJBRuntimeEntry OBJECT-TYPE
      SYNTAX      StatefulEJBRuntimeEntry
      MAX-ACCESS  not-accessible
      STATUS      current
      DESCRIPTION "Generated SNMP Table Entry."
      INDEX { statefulEJBRuntimeIndex}
      ::= { statefulEJBRuntimeTable 1 }
      
   StatefulEJBRuntimeEntry ::=
      SEQUENCE
      {
         statefulEJBRuntimeIndex OCTET STRING,
         statefulEJBRuntimeObjectName OCTET STRING,
         statefulEJBRuntimeType OCTET STRING,
         statefulEJBRuntimeEJBName OCTET STRING,
         statefulEJBRuntimeName OCTET STRING
      }
      
   
   statefulEJBRuntimeIndex OBJECT-TYPE
      SYNTAX      OCTET STRING
      MAX-ACCESS  not-accessible
      STATUS      current
      DESCRIPTION "Index column"
      ::= { statefulEJBRuntimeEntry 1  }
   
   
   statefulEJBRuntimeObjectName OBJECT-TYPE
      SYNTAX      OCTET STRING
      MAX-ACCESS  read-only
      STATUS      current
      DESCRIPTION "ObjectName column"
      ::= { statefulEJBRuntimeEntry 2  }
   
   
   statefulEJBRuntimeType OBJECT-TYPE
      SYNTAX      OCTET STRING
      MAX-ACCESS  read-only
      STATUS      current
      DESCRIPTION "Returns the type of the MBean."
      ::= { statefulEJBRuntimeEntry 3  }
   
   
   statefulEJBRuntimeEJBName OBJECT-TYPE
      SYNTAX      OCTET STRING
      MAX-ACCESS  read-only
      STATUS      current
      DESCRIPTION "Provides the ejb-name for this EJB as defined in the ejb-jar.xml deployment descriptor."
      ::= { statefulEJBRuntimeEntry 4  }
   
   
   statefulEJBRuntimeName OBJECT-TYPE
      SYNTAX      OCTET STRING
      MAX-ACCESS  read-only
      STATUS      current
      DESCRIPTION "The name of this configuration. WebLogic Server uses an MBean to implement and persist the configuration."
      ::= { statefulEJBRuntimeEntry 5  }
   
   
   statelessEJBRuntimeTable OBJECT-TYPE
      SYNTAX      SEQUENCE OF StatelessEJBRuntimeEntry
      MAX-ACCESS  not-accessible
      STATUS      current
      DESCRIPTION "This interface contains accessor methods for all EJB runtime information collected for a Stateless Session Bean.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1400  }
      
   
   statelessEJBRuntimeEntry OBJECT-TYPE
      SYNTAX      StatelessEJBRuntimeEntry
      MAX-ACCESS  not-accessible
      STATUS      current
      DESCRIPTION "Generated SNMP Table Entry."
      INDEX { statelessEJBRuntimeIndex}
      ::= { statelessEJBRuntimeTable 1 }
      
   StatelessEJBRuntimeEntry ::=
      SEQUENCE
      {
         statelessEJBRuntimeIndex OCTET STRING,
         statelessEJBRuntimeObjectName OCTET STRING,
         statelessEJBRuntimeType OCTET STRING,
         statelessEJBRuntimeEJBName OCTET STRING,
         statelessEJBRuntimeName OCTET STRING
      }
      
   
   statelessEJBRuntimeIndex OBJECT-TYPE
      SYNTAX      OCTET STRING
      MAX-ACCESS  not-accessible
      STATUS      current
      DESCRIPTION "Index column"
      ::= { statelessEJBRuntimeEntry 1  }
   
   
   statelessEJBRuntimeObjectName OBJECT-TYPE
      SYNTAX      OCTET STRING
      MAX-ACCESS  read-only
      STATUS      current
      DESCRIPTION "ObjectName column"
      ::= { statelessEJBRuntimeEntry 2  }
   
   
   statelessEJBRuntimeType OBJECT-TYPE
      SYNTAX      OCTET STRING
      MAX-ACCESS  read-only
      STATUS      current
      DESCRIPTION "Returns the type of the MBean."
      ::= { statelessEJBRuntimeEntry 3  }
   
   
   statelessEJBRuntimeEJBName OBJECT-TYPE
      SYNTAX      OCTET STRING
      MAX-ACCESS  read-only
      STATUS      current
      DESCRIPTION "Provides the ejb-name for this EJB as defined in the ejb-jar.xml deployment descriptor."
      ::= { statelessEJBRuntimeEntry 4  }
   
   
   statelessEJBRuntimeName OBJECT-TYPE
      SYNTAX      OCTET STRING
      MAX-ACCESS  read-only
      STATUS      current
      DESCRIPTION "The name of this configuration. WebLogic Server uses an MBean to implement and persist the configuration."
      ::= { statelessEJBRuntimeEntry 5  }
   
   
   timeServiceRuntimeTable OBJECT-TYPE
      SYNTAX      SEQUENCE OF TimeServiceRuntimeEntry
      MAX-ACCESS  not-accessible
      STATUS      current
      DESCRIPTION "This class is used for monitoring the WebLogic Time Service."
      ::= { wls 1405  }
      
   
   timeServiceRuntimeEntry OBJECT-TYPE
      SYNTAX      TimeServiceRuntimeEntry
      MAX-ACCESS  not-accessible
      STATUS      current
      DESCRIPTION "Generated SNMP Table Entry."
      INDEX { timeServiceRuntimeIndex}
      ::= { timeServiceRuntimeTable 1 }
      
   TimeServiceRuntimeEntry ::=
      SEQUENCE
      {
         timeServiceRuntimeIndex OCTET STRING,
         timeServiceRuntimeObjectName OCTET STRING,
         timeServiceRuntimeType OCTET STRING,
         timeServiceRuntimeName OCTET STRING
      }
      
   
   timeServiceRuntimeIndex OBJECT-TYPE
      SYNTAX      OCTET STRING
      MAX-ACCESS  not-accessible
      STATUS      current
      DESCRIPTION "Index column"
      ::= { timeServiceRuntimeEntry 1  }
   
   
   timeServiceRuntimeObjectName OBJECT-TYPE
      SYNTAX      OCTET STRING
      MAX-ACCESS  read-only
      STATUS      current
      DESCRIPTION "ObjectName column"
      ::= { timeServiceRuntimeEntry 2  }
   
   
   timeServiceRuntimeType OBJECT-TYPE
      SYNTAX      OCTET STRING
      MAX-ACCESS  read-only
      STATUS      current
      DESCRIPTION "Returns the type of the MBean."
      ::= { timeServiceRuntimeEntry 3  }
   
   
   timeServiceRuntimeName OBJECT-TYPE
      SYNTAX      OCTET STRING
      MAX-ACCESS  read-only
      STATUS      current
      DESCRIPTION "The name of this configuration. WebLogic Server uses an MBean to implement and persist the configuration."
      ::= { timeServiceRuntimeEntry 4  }
   
   
   timerRuntimeTable OBJECT-TYPE
      SYNTAX      SEQUENCE OF TimerRuntimeEntry
      MAX-ACCESS  not-accessible
      STATUS      current
      DESCRIPTION "This RuntimeMBean exposes information about all active timers present in the WebLogic timer implementation."
      ::= { wls 1410  }
      
   
   timerRuntimeEntry OBJECT-TYPE
      SYNTAX      TimerRuntimeEntry
      MAX-ACCESS  not-accessible
      STATUS      current
      DESCRIPTION "Generated SNMP Table Entry."
      INDEX { timerRuntimeIndex}
      ::= { timerRuntimeTable 1 }
      
   TimerRuntimeEntry ::=
      SEQUENCE
      {
         timerRuntimeIndex    OCTET STRING,
         timerRuntimeObjectName OCTET STRING,
         timerRuntimeType     OCTET STRING,
         timerRuntimeName     OCTET STRING
      }
      
   
   timerRuntimeIndex OBJECT-TYPE
      SYNTAX      OCTET STRING
      MAX-ACCESS  not-accessible
      STATUS      current
      DESCRIPTION "Index column"
      ::= { timerRuntimeEntry 1  }
   
   
   timerRuntimeObjectName OBJECT-TYPE
      SYNTAX      OCTET STRING
      MAX-ACCESS  read-only
      STATUS      current
      DESCRIPTION "ObjectName column"
      ::= { timerRuntimeEntry 2  }
   
   
   timerRuntimeType OBJECT-TYPE
      SYNTAX      OCTET STRING
      MAX-ACCESS  read-only
      STATUS      current
      DESCRIPTION "Returns the type of the MBean."
      ::= { timerRuntimeEntry 3  }
   
   
   timerRuntimeName OBJECT-TYPE
      SYNTAX      OCTET STRING
      MAX-ACCESS  read-only
      STATUS      current
      DESCRIPTION "The name of this configuration. WebLogic Server uses an MBean to implement and persist the configuration."
      ::= { timerRuntimeEntry 4  }
   
   
   urlResourceRuntimeTable OBJECT-TYPE
      SYNTAX      SEQUENCE OF UrlResourceRuntimeEntry
      MAX-ACCESS  not-accessible
      STATUS      current
      DESCRIPTION "RuntimeMBean for URLResources  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1415  }
      
   
   urlResourceRuntimeEntry OBJECT-TYPE
      SYNTAX      UrlResourceRuntimeEntry
      MAX-ACCESS  not-accessible
      STATUS      current
      DESCRIPTION "Generated SNMP Table Entry."
      INDEX { urlResourceRuntimeIndex}
      ::= { urlResourceRuntimeTable 1 }
      
   UrlResourceRuntimeEntry ::=
      SEQUENCE
      {
         urlResourceRuntimeIndex OCTET STRING,
         urlResourceRuntimeObjectName OCTET STRING,
         urlResourceRuntimeType OCTET STRING,
         urlResourceRuntimeName OCTET STRING
      }
      
   
   urlResourceRuntimeIndex OBJECT-TYPE
      SYNTAX      OCTET STRING
      MAX-ACCESS  not-accessible
      STATUS      current
      DESCRIPTION "Index column"
      ::= { urlResourceRuntimeEntry 1  }
   
   
   urlResourceRuntimeObjectName OBJECT-TYPE
      SYNTAX      OCTET STRING
      MAX-ACCESS  read-only
      STATUS      current
      DESCRIPTION "ObjectName column"
      ::= { urlResourceRuntimeEntry 2  }
   
   
   urlResourceRuntimeType OBJECT-TYPE
      SYNTAX      OCTET STRING
      MAX-ACCESS  read-only
      STATUS      current
      DESCRIPTION "Returns the type of the MBean."
      ::= { urlResourceRuntimeEntry 3  }
   
   
   urlResourceRuntimeName OBJECT-TYPE
      SYNTAX      OCTET STRING
      MAX-ACCESS  read-only
      STATUS      current
      DESCRIPTION "The name of this configuration. WebLogic Server uses an MBean to implement and persist the configuration."
      ::= { urlResourceRuntimeEntry 4  }
   
   
   unicastMessagingRuntimeTable OBJECT-TYPE
      SYNTAX      SEQUENCE OF UnicastMessagingRuntimeEntry
      MAX-ACCESS  not-accessible
      STATUS      current
      DESCRIPTION "Monitoring information when unicast messaging is turned on"
      ::= { wls 1420  }
      
   
   unicastMessagingRuntimeEntry OBJECT-TYPE
      SYNTAX      UnicastMessagingRuntimeEntry
      MAX-ACCESS  not-accessible
      STATUS      current
      DESCRIPTION "Generated SNMP Table Entry."
      INDEX { unicastMessagingRuntimeIndex}
      ::= { unicastMessagingRuntimeTable 1 }
      
   UnicastMessagingRuntimeEntry ::=
      SEQUENCE
      {
         unicastMessagingRuntimeIndex OCTET STRING,
         unicastMessagingRuntimeObjectName OCTET STRING,
         unicastMessagingRuntimeType OCTET STRING,
         unicastMessagingRuntimeRemoteGroupsDiscoveredCount Integer32,
         unicastMessagingRuntimeTotalGroupsCount Integer32,
         unicastMessagingRuntimeLocalGroupLeaderName OCTET STRING,
         unicastMessagingRuntimeGroups OCTET STRING,
         unicastMessagingRuntimeName OCTET STRING
      }
      
   
   unicastMessagingRuntimeIndex OBJECT-TYPE
      SYNTAX      OCTET STRING
      MAX-ACCESS  not-accessible
      STATUS      current
      DESCRIPTION "Index column"
      ::= { unicastMessagingRuntimeEntry 1  }
   
   
   unicastMessagingRuntimeObjectName OBJECT-TYPE
      SYNTAX      OCTET STRING
      MAX-ACCESS  read-only
      STATUS      current
      DESCRIPTION "ObjectName column"
      ::= { unicastMessagingRuntimeEntry 2  }
   
   
   unicastMessagingRuntimeType OBJECT-TYPE
      SYNTAX      OCTET STRING
      MAX-ACCESS  read-only
      STATUS      current
      DESCRIPTION "Returns the type of the MBean."
      ::= { unicastMessagingRuntimeEntry 3  }
   
   
   unicastMessagingRuntimeRemoteGroupsDiscoveredCount OBJECT-TYPE
      SYNTAX      Integer32
      MAX-ACCESS  read-only
      STATUS      current
      DESCRIPTION "Returns the total groups discovered by this server"
      ::= { unicastMessagingRuntimeEntry 4  }
   
   
   unicastMessagingRuntimeTotalGroupsCount OBJECT-TYPE
      SYNTAX      Integer32
      MAX-ACCESS  read-only
      STATUS      current
      DESCRIPTION "Total configured groups - running and not running"
      ::= { unicastMessagingRuntimeEntry 5  }
   
   
   unicastMessagingRuntimeLocalGroupLeaderName OBJECT-TYPE
      SYNTAX      OCTET STRING
      MAX-ACCESS  read-only
      STATUS      current
      DESCRIPTION "Name of the local group leader"
      ::= { unicastMessagingRuntimeEntry 6  }
   
   
   unicastMessagingRuntimeGroups OBJECT-TYPE
      SYNTAX      OCTET STRING
      MAX-ACCESS  read-only
      STATUS      current
      DESCRIPTION "Formatted group list"
      ::= { unicastMessagingRuntimeEntry 7  }
   
   
   unicastMessagingRuntimeName OBJECT-TYPE
      SYNTAX      OCTET STRING
      MAX-ACCESS  read-only
      STATUS      current
      DESCRIPTION "The name of this configuration. WebLogic Server uses an MBean to implement and persist the configuration."
      ::= { unicastMessagingRuntimeEntry 8  }
   
   
   wldfAccessRuntimeTable OBJECT-TYPE
      SYNTAX      SEQUENCE OF WldfAccessRuntimeEntry
      MAX-ACCESS  not-accessible
      STATUS      current
      DESCRIPTION "Use this interface to access the different types of diagnostic data generated by a server."
      ::= { wls 1425  }
      
   
   wldfAccessRuntimeEntry OBJECT-TYPE
      SYNTAX      WldfAccessRuntimeEntry
      MAX-ACCESS  not-accessible
      STATUS      current
      DESCRIPTION "Generated SNMP Table Entry."
      INDEX { wldfAccessRuntimeIndex}
      ::= { wldfAccessRuntimeTable 1 }
      
   WldfAccessRuntimeEntry ::=
      SEQUENCE
      {
         wldfAccessRuntimeIndex OCTET STRING,
         wldfAccessRuntimeObjectName OCTET STRING,
         wldfAccessRuntimeType OCTET STRING,
         wldfAccessRuntimeName OCTET STRING
      }
      
   
   wldfAccessRuntimeIndex OBJECT-TYPE
      SYNTAX      OCTET STRING
      MAX-ACCESS  not-accessible
      STATUS      current
      DESCRIPTION "Index column"
      ::= { wldfAccessRuntimeEntry 1  }
   
   
   wldfAccessRuntimeObjectName OBJECT-TYPE
      SYNTAX      OCTET STRING
      MAX-ACCESS  read-only
      STATUS      current
      DESCRIPTION "ObjectName column"
      ::= { wldfAccessRuntimeEntry 2  }
   
   
   wldfAccessRuntimeType OBJECT-TYPE
      SYNTAX      OCTET STRING
      MAX-ACCESS  read-only
      STATUS      current
      DESCRIPTION "Returns the type of the MBean."
      ::= { wldfAccessRuntimeEntry 3  }
   
   
   wldfAccessRuntimeName OBJECT-TYPE
      SYNTAX      OCTET STRING
      MAX-ACCESS  read-only
      STATUS      current
      DESCRIPTION "The name of this configuration. WebLogic Server uses an MBean to implement and persist the configuration."
      ::= { wldfAccessRuntimeEntry 4  }
   
   
   wldfDataAccessRuntimeTable OBJECT-TYPE
      SYNTAX      SEQUENCE OF WldfDataAccessRuntimeEntry
      MAX-ACCESS  not-accessible
      STATUS      current
      DESCRIPTION "Use this interface to access the specific type of diagnostic data from an underlying log for which this instance is created."
      ::= { wls 1430  }
      
   
   wldfDataAccessRuntimeEntry OBJECT-TYPE
      SYNTAX      WldfDataAccessRuntimeEntry
      MAX-ACCESS  not-accessible
      STATUS      current
      DESCRIPTION "Generated SNMP Table Entry."
      INDEX { wldfDataAccessRuntimeIndex}
      ::= { wldfDataAccessRuntimeTable 1 }
      
   WldfDataAccessRuntimeEntry ::=
      SEQUENCE
      {
         wldfDataAccessRuntimeIndex OCTET STRING,
         wldfDataAccessRuntimeObjectName OCTET STRING,
         wldfDataAccessRuntimeType OCTET STRING,
         wldfDataAccessRuntimeEarliestAvailableTimestamp Counter64,
         wldfDataAccessRuntimeLatestAvailableTimestamp Counter64,
         wldfDataAccessRuntimeTimestampAvailable OCTET STRING,
         wldfDataAccessRuntimeName OCTET STRING,
         wldfDataAccessRuntimeLatestRecordId Counter64
      }
      
   
   wldfDataAccessRuntimeIndex OBJECT-TYPE
      SYNTAX      OCTET STRING
      MAX-ACCESS  not-accessible
      STATUS      current
      DESCRIPTION "Index column"
      ::= { wldfDataAccessRuntimeEntry 1  }
   
   
   wldfDataAccessRuntimeObjectName OBJECT-TYPE
      SYNTAX      OCTET STRING
      MAX-ACCESS  read-only
      STATUS      current
      DESCRIPTION "ObjectName column"
      ::= { wldfDataAccessRuntimeEntry 2  }
   
   
   wldfDataAccessRuntimeType OBJECT-TYPE
      SYNTAX      OCTET STRING
      MAX-ACCESS  read-only
      STATUS      current
      DESCRIPTION "Returns the type of the MBean."
      ::= { wldfDataAccessRuntimeEntry 3  }
   
   
   wldfDataAccessRuntimeEarliestAvailableTimestamp OBJECT-TYPE
      SYNTAX      Counter64
      MAX-ACCESS  read-only
      STATUS      current
      DESCRIPTION "The timestamp, in milliseconds, since Jan 1, 1970 AD, 00:00:00 GMT for the earliest record in the diagnostic data log."
      ::= { wldfDataAccessRuntimeEntry 4  }
   
   
   wldfDataAccessRuntimeLatestAvailableTimestamp OBJECT-TYPE
      SYNTAX      Counter64
      MAX-ACCESS  read-only
      STATUS      current
      DESCRIPTION "The timestamp, in milliseconds, since Jan 1, 1970 AD, 00:00:00 GMT for the newest record in the diagnostic data log."
      ::= { wldfDataAccessRuntimeEntry 5  }
   
   
   wldfDataAccessRuntimeTimestampAvailable OBJECT-TYPE
      SYNTAX      OCTET STRING
      MAX-ACCESS  read-only
      STATUS      current
      DESCRIPTION "Return if timestamp information is available with the underlying archive."
      ::= { wldfDataAccessRuntimeEntry 6  }
   
   
   wldfDataAccessRuntimeName OBJECT-TYPE
      SYNTAX      OCTET STRING
      MAX-ACCESS  read-only
      STATUS      current
      DESCRIPTION "The name of this configuration. WebLogic Server uses an MBean to implement and persist the configuration."
      ::= { wldfDataAccessRuntimeEntry 7  }
   
   
   wldfDataAccessRuntimeLatestRecordId OBJECT-TYPE
      SYNTAX      Counter64
      MAX-ACCESS  read-only
      STATUS      current
      DESCRIPTION "The latest known record ID for the underlying archive."
      ::= { wldfDataAccessRuntimeEntry 8  }
   
   
   wldfDataRetirementTaskRuntimeTable OBJECT-TYPE
      SYNTAX      SEQUENCE OF WldfDataRetirementTaskRuntimeEntry
      MAX-ACCESS  not-accessible
      STATUS      current
      DESCRIPTION "Exposes monitoring information about a potentially long-running request for the data retirement task. Remote clients, as well as clients running within a server, can access this information."
      ::= { wls 1435  }
      
   
   wldfDataRetirementTaskRuntimeEntry OBJECT-TYPE
      SYNTAX      WldfDataRetirementTaskRuntimeEntry
      MAX-ACCESS  not-accessible
      STATUS      current
      DESCRIPTION "Generated SNMP Table Entry."
      INDEX { wldfDataRetirementTaskRuntimeIndex}
      ::= { wldfDataRetirementTaskRuntimeTable 1 }
      
   WldfDataRetirementTaskRuntimeEntry ::=
      SEQUENCE
      {
         wldfDataRetirementTaskRuntimeIndex OCTET STRING,
         wldfDataRetirementTaskRuntimeObjectName OCTET STRING,
         wldfDataRetirementTaskRuntimeType OCTET STRING,
         wldfDataRetirementTaskRuntimeStatus OCTET STRING,
         wldfDataRetirementTaskRuntimeRetiredRecordsCount Counter64,
         wldfDataRetirementTaskRuntimeRunning OCTET STRING,
         wldfDataRetirementTaskRuntimeBeginTime Counter64,
         wldfDataRetirementTaskRuntimeEndTime Counter64,
         wldfDataRetirementTaskRuntimeSystemTask OCTET STRING,
         wldfDataRetirementTaskRuntimeDescription OCTET STRING,
         wldfDataRetirementTaskRuntimeName OCTET STRING
      }
      
   
   wldfDataRetirementTaskRuntimeIndex OBJECT-TYPE
      SYNTAX      OCTET STRING
      MAX-ACCESS  not-accessible
      STATUS      current
      DESCRIPTION "Index column"
      ::= { wldfDataRetirementTaskRuntimeEntry 1  }
   
   
   wldfDataRetirementTaskRuntimeObjectName OBJECT-TYPE
      SYNTAX      OCTET STRING
      MAX-ACCESS  read-only
      STATUS      current
      DESCRIPTION "ObjectName column"
      ::= { wldfDataRetirementTaskRuntimeEntry 2  }
   
   
   wldfDataRetirementTaskRuntimeType OBJECT-TYPE
      SYNTAX      OCTET STRING
      MAX-ACCESS  read-only
      STATUS      current
      DESCRIPTION "Returns the type of the MBean."
      ::= { wldfDataRetirementTaskRuntimeEntry 3  }
   
   
   wldfDataRetirementTaskRuntimeStatus OBJECT-TYPE
      SYNTAX      OCTET STRING
      MAX-ACCESS  read-only
      STATUS      current
      DESCRIPTION ""
      ::= { wldfDataRetirementTaskRuntimeEntry 4  }
   
   
   wldfDataRetirementTaskRuntimeRetiredRecordsCount OBJECT-TYPE
      SYNTAX      Counter64
      MAX-ACCESS  read-only
      STATUS      current
      DESCRIPTION ""
      ::= { wldfDataRetirementTaskRuntimeEntry 5  }
   
   
   wldfDataRetirementTaskRuntimeRunning OBJECT-TYPE
      SYNTAX      OCTET STRING
      MAX-ACCESS  read-only
      STATUS      current
      DESCRIPTION ""
      ::= { wldfDataRetirementTaskRuntimeEntry 6  }
   
   
   wldfDataRetirementTaskRuntimeBeginTime OBJECT-TYPE
      SYNTAX      Counter64
      MAX-ACCESS  read-only
      STATUS      current
      DESCRIPTION ""
      ::= { wldfDataRetirementTaskRuntimeEntry 7  }
   
   
   wldfDataRetirementTaskRuntimeEndTime OBJECT-TYPE
      SYNTAX      Counter64
      MAX-ACCESS  read-only
      STATUS      current
      DESCRIPTION ""
      ::= { wldfDataRetirementTaskRuntimeEntry 8  }
   
   
   wldfDataRetirementTaskRuntimeSystemTask OBJECT-TYPE
      SYNTAX      OCTET STRING
      MAX-ACCESS  read-only
      STATUS      current
      DESCRIPTION ""
      ::= { wldfDataRetirementTaskRuntimeEntry 9  }
   
   
   wldfDataRetirementTaskRuntimeDescription OBJECT-TYPE
      SYNTAX      OCTET STRING
      MAX-ACCESS  read-only
      STATUS      current
      DESCRIPTION ""
      ::= { wldfDataRetirementTaskRuntimeEntry 10  }
   
   
   wldfDataRetirementTaskRuntimeName OBJECT-TYPE
      SYNTAX      OCTET STRING
      MAX-ACCESS  read-only
      STATUS      current
      DESCRIPTION "The name of this configuration. WebLogic Server uses an MBean to implement and persist the configuration."
      ::= { wldfDataRetirementTaskRuntimeEntry 11  }
   
   
   wldfImageCreationTaskRuntimeTable OBJECT-TYPE
      SYNTAX      SEQUENCE OF WldfImageCreationTaskRuntimeEntry
      MAX-ACCESS  not-accessible
      STATUS      current
      DESCRIPTION "Exposes monitoring information about a potentially long-running request for the generation of a diagnostic image. Remote clients, as well as clients running within a server, can access this information.  {@link weblogic.management.runtime.WLDFImageRuntimeMBean WLDFImageRuntimeMBean} supports operations to request the generation of a diagnostic image for capturing a running server's internal state information.  These operations will fork a separate thread to perform the actual work and immediately return an instance of this MBean to the caller. The caller can then use that instance to track the task's progress."
      ::= { wls 1440  }
      
   
   wldfImageCreationTaskRuntimeEntry OBJECT-TYPE
      SYNTAX      WldfImageCreationTaskRuntimeEntry
      MAX-ACCESS  not-accessible
      STATUS      current
      DESCRIPTION "Generated SNMP Table Entry."
      INDEX { wldfImageCreationTaskRuntimeIndex}
      ::= { wldfImageCreationTaskRuntimeTable 1 }
      
   WldfImageCreationTaskRuntimeEntry ::=
      SEQUENCE
      {
         wldfImageCreationTaskRuntimeIndex OCTET STRING,
         wldfImageCreationTaskRuntimeObjectName OCTET STRING,
         wldfImageCreationTaskRuntimeType OCTET STRING,
         wldfImageCreationTaskRuntimeStatus OCTET STRING,
         wldfImageCreationTaskRuntimeRunning OCTET STRING,
         wldfImageCreationTaskRuntimeBeginTime Counter64,
         wldfImageCreationTaskRuntimeEndTime Counter64,
         wldfImageCreationTaskRuntimeSystemTask OCTET STRING,
         wldfImageCreationTaskRuntimeDescription OCTET STRING,
         wldfImageCreationTaskRuntimeName OCTET STRING
      }
      
   
   wldfImageCreationTaskRuntimeIndex OBJECT-TYPE
      SYNTAX      OCTET STRING
      MAX-ACCESS  not-accessible
      STATUS      current
      DESCRIPTION "Index column"
      ::= { wldfImageCreationTaskRuntimeEntry 1  }
   
   
   wldfImageCreationTaskRuntimeObjectName OBJECT-TYPE
      SYNTAX      OCTET STRING
      MAX-ACCESS  read-only
      STATUS      current
      DESCRIPTION "ObjectName column"
      ::= { wldfImageCreationTaskRuntimeEntry 2  }
   
   
   wldfImageCreationTaskRuntimeType OBJECT-TYPE
      SYNTAX      OCTET STRING
      MAX-ACCESS  read-only
      STATUS      current
      DESCRIPTION "Returns the type of the MBean."
      ::= { wldfImageCreationTaskRuntimeEntry 3  }
   
   
   wldfImageCreationTaskRuntimeStatus OBJECT-TYPE
      SYNTAX      OCTET STRING
      MAX-ACCESS  read-only
      STATUS      current
      DESCRIPTION ""
      ::= { wldfImageCreationTaskRuntimeEntry 4  }
   
   
   wldfImageCreationTaskRuntimeRunning OBJECT-TYPE
      SYNTAX      OCTET STRING
      MAX-ACCESS  read-only
      STATUS      current
      DESCRIPTION ""
      ::= { wldfImageCreationTaskRuntimeEntry 5  }
   
   
   wldfImageCreationTaskRuntimeBeginTime OBJECT-TYPE
      SYNTAX      Counter64
      MAX-ACCESS  read-only
      STATUS      current
      DESCRIPTION ""
      ::= { wldfImageCreationTaskRuntimeEntry 6  }
   
   
   wldfImageCreationTaskRuntimeEndTime OBJECT-TYPE
      SYNTAX      Counter64
      MAX-ACCESS  read-only
      STATUS      current
      DESCRIPTION ""
      ::= { wldfImageCreationTaskRuntimeEntry 7  }
   
   
   wldfImageCreationTaskRuntimeSystemTask OBJECT-TYPE
      SYNTAX      OCTET STRING
      MAX-ACCESS  read-only
      STATUS      current
      DESCRIPTION ""
      ::= { wldfImageCreationTaskRuntimeEntry 8  }
   
   
   wldfImageCreationTaskRuntimeDescription OBJECT-TYPE
      SYNTAX      OCTET STRING
      MAX-ACCESS  read-only
      STATUS      current
      DESCRIPTION ""
      ::= { wldfImageCreationTaskRuntimeEntry 9  }
   
   
   wldfImageCreationTaskRuntimeName OBJECT-TYPE
      SYNTAX      OCTET STRING
      MAX-ACCESS  read-only
      STATUS      current
      DESCRIPTION "The name of this configuration. WebLogic Server uses an MBean to implement and persist the configuration."
      ::= { wldfImageCreationTaskRuntimeEntry 10  }
   
   
   wldfImageRuntimeTable OBJECT-TYPE
      SYNTAX      SEQUENCE OF WldfImageRuntimeEntry
      MAX-ACCESS  not-accessible
      STATUS      current
      DESCRIPTION "This interface controls diagnostic image creation, and provides access to run-time information about past and current diagnostic image capture requests."
      ::= { wls 1445  }
      
   
   wldfImageRuntimeEntry OBJECT-TYPE
      SYNTAX      WldfImageRuntimeEntry
      MAX-ACCESS  not-accessible
      STATUS      current
      DESCRIPTION "Generated SNMP Table Entry."
      INDEX { wldfImageRuntimeIndex}
      ::= { wldfImageRuntimeTable 1 }
      
   WldfImageRuntimeEntry ::=
      SEQUENCE
      {
         wldfImageRuntimeIndex OCTET STRING,
         wldfImageRuntimeObjectName OCTET STRING,
         wldfImageRuntimeType OCTET STRING,
         wldfImageRuntimeName OCTET STRING
      }
      
   
   wldfImageRuntimeIndex OBJECT-TYPE
      SYNTAX      OCTET STRING
      MAX-ACCESS  not-accessible
      STATUS      current
      DESCRIPTION "Index column"
      ::= { wldfImageRuntimeEntry 1  }
   
   
   wldfImageRuntimeObjectName OBJECT-TYPE
      SYNTAX      OCTET STRING
      MAX-ACCESS  read-only
      STATUS      current
      DESCRIPTION "ObjectName column"
      ::= { wldfImageRuntimeEntry 2  }
   
   
   wldfImageRuntimeType OBJECT-TYPE
      SYNTAX      OCTET STRING
      MAX-ACCESS  read-only
      STATUS      current
      DESCRIPTION "Returns the type of the MBean."
      ::= { wldfImageRuntimeEntry 3  }
   
   
   wldfImageRuntimeName OBJECT-TYPE
      SYNTAX      OCTET STRING
      MAX-ACCESS  read-only
      STATUS      current
      DESCRIPTION "The name of this configuration. WebLogic Server uses an MBean to implement and persist the configuration."
      ::= { wldfImageRuntimeEntry 4  }
   
   
   wldfRuntimeTable OBJECT-TYPE
      SYNTAX      SEQUENCE OF WldfRuntimeEntry
      MAX-ACCESS  not-accessible
      STATUS      current
      DESCRIPTION "This interface provides access to all the runtime MBeans for the WebLogic Diagnostic Framework (WLDF)."
      ::= { wls 1450  }
      
   
   wldfRuntimeEntry OBJECT-TYPE
      SYNTAX      WldfRuntimeEntry
      MAX-ACCESS  not-accessible
      STATUS      current
      DESCRIPTION "Generated SNMP Table Entry."
      INDEX { wldfRuntimeIndex}
      ::= { wldfRuntimeTable 1 }
      
   WldfRuntimeEntry ::=
      SEQUENCE
      {
         wldfRuntimeIndex     OCTET STRING,
         wldfRuntimeObjectName OCTET STRING,
         wldfRuntimeType      OCTET STRING,
         wldfRuntimeName      OCTET STRING
      }
      
   
   wldfRuntimeIndex OBJECT-TYPE
      SYNTAX      OCTET STRING
      MAX-ACCESS  not-accessible
      STATUS      current
      DESCRIPTION "Index column"
      ::= { wldfRuntimeEntry 1  }
   
   
   wldfRuntimeObjectName OBJECT-TYPE
      SYNTAX      OCTET STRING
      MAX-ACCESS  read-only
      STATUS      current
      DESCRIPTION "ObjectName column"
      ::= { wldfRuntimeEntry 2  }
   
   
   wldfRuntimeType OBJECT-TYPE
      SYNTAX      OCTET STRING
      MAX-ACCESS  read-only
      STATUS      current
      DESCRIPTION "Returns the type of the MBean."
      ::= { wldfRuntimeEntry 3  }
   
   
   wldfRuntimeName OBJECT-TYPE
      SYNTAX      OCTET STRING
      MAX-ACCESS  read-only
      STATUS      current
      DESCRIPTION "The name of this configuration. WebLogic Server uses an MBean to implement and persist the configuration."
      ::= { wldfRuntimeEntry 4  }
   
   
   wldfWatchJMXNotificationRuntimeTable OBJECT-TYPE
      SYNTAX      SEQUENCE OF WldfWatchJMXNotificationRuntimeEntry
      MAX-ACCESS  not-accessible
      STATUS      current
      DESCRIPTION "Attaches a notification listener in order to receive watch notification events when a watch evaluates to true. Note that the listener will receive all notifications; the caller must filter the output."
      ::= { wls 1455  }
      
   
   wldfWatchJMXNotificationRuntimeEntry OBJECT-TYPE
      SYNTAX      WldfWatchJMXNotificationRuntimeEntry
      MAX-ACCESS  not-accessible
      STATUS      current
      DESCRIPTION "Generated SNMP Table Entry."
      INDEX { wldfWatchJMXNotificationRuntimeIndex}
      ::= { wldfWatchJMXNotificationRuntimeTable 1 }
      
   WldfWatchJMXNotificationRuntimeEntry ::=
      SEQUENCE
      {
         wldfWatchJMXNotificationRuntimeIndex OCTET STRING,
         wldfWatchJMXNotificationRuntimeObjectName OCTET STRING,
         wldfWatchJMXNotificationRuntimeType OCTET STRING,
         wldfWatchJMXNotificationRuntimeName OCTET STRING
      }
      
   
   wldfWatchJMXNotificationRuntimeIndex OBJECT-TYPE
      SYNTAX      OCTET STRING
      MAX-ACCESS  not-accessible
      STATUS      current
      DESCRIPTION "Index column"
      ::= { wldfWatchJMXNotificationRuntimeEntry 1  }
   
   
   wldfWatchJMXNotificationRuntimeObjectName OBJECT-TYPE
      SYNTAX      OCTET STRING
      MAX-ACCESS  read-only
      STATUS      current
      DESCRIPTION "ObjectName column"
      ::= { wldfWatchJMXNotificationRuntimeEntry 2  }
   
   
   wldfWatchJMXNotificationRuntimeType OBJECT-TYPE
      SYNTAX      OCTET STRING
      MAX-ACCESS  read-only
      STATUS      current
      DESCRIPTION "Returns the type of the MBean."
      ::= { wldfWatchJMXNotificationRuntimeEntry 3  }
   
   
   wldfWatchJMXNotificationRuntimeName OBJECT-TYPE
      SYNTAX      OCTET STRING
      MAX-ACCESS  read-only
      STATUS      current
      DESCRIPTION "The name of this configuration. WebLogic Server uses an MBean to implement and persist the configuration."
      ::= { wldfWatchJMXNotificationRuntimeEntry 4  }
   
   
   wsrmRemoteEndpointRuntimeTable OBJECT-TYPE
      SYNTAX      SEQUENCE OF WsrmRemoteEndpointRuntimeEntry
      MAX-ACCESS  not-accessible
      STATUS      current
      DESCRIPTION "This class is used for monitoring a WebLogic SAF remote endpoint for WebServices Reliable Messaging.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1460  }
      
   
   wsrmRemoteEndpointRuntimeEntry OBJECT-TYPE
      SYNTAX      WsrmRemoteEndpointRuntimeEntry
      MAX-ACCESS  not-accessible
      STATUS      current
      DESCRIPTION "Generated SNMP Table Entry."
      INDEX { wsrmRemoteEndpointRuntimeIndex}
      ::= { wsrmRemoteEndpointRuntimeTable 1 }
      
   WsrmRemoteEndpointRuntimeEntry ::=
      SEQUENCE
      {
         wsrmRemoteEndpointRuntimeIndex OCTET STRING,
         wsrmRemoteEndpointRuntimeObjectName OCTET STRING,
         wsrmRemoteEndpointRuntimeType OCTET STRING,
         wsrmRemoteEndpointRuntimeUptimeTotal Counter64,
         wsrmRemoteEndpointRuntimeMessagesCurrentCount Counter64,
         wsrmRemoteEndpointRuntimeDowntimeTotal Counter64,
         wsrmRemoteEndpointRuntimeBytesReceivedCount Counter64,
         wsrmRemoteEndpointRuntimeEndpointType OCTET STRING,
         wsrmRemoteEndpointRuntimeFailedMessagesTotal Counter64,
         wsrmRemoteEndpointRuntimeMessagesReceivedCount Counter64,
         wsrmRemoteEndpointRuntimeURL OCTET STRING,
         wsrmRemoteEndpointRuntimePausedForIncoming OCTET STRING,
         wsrmRemoteEndpointRuntimeName OCTET STRING,
         wsrmRemoteEndpointRuntimeBytesHighCount Counter64,
         wsrmRemoteEndpointRuntimeUptimeHigh Counter64,
         wsrmRemoteEndpointRuntimeBytesCurrentCount Counter64,
         wsrmRemoteEndpointRuntimeMessagesPendingCount Counter64,
         wsrmRemoteEndpointRuntimeConversationsCurrentCount Counter64,
         wsrmRemoteEndpointRuntimeConversationsHighCount Counter64,
         wsrmRemoteEndpointRuntimeConversationsTotalCount Counter64,
         wsrmRemoteEndpointRuntimeDowntimeHigh Counter64,
         wsrmRemoteEndpointRuntimeBytesThresholdTime Counter64,
         wsrmRemoteEndpointRuntimeBytesPendingCount Counter64,
         wsrmRemoteEndpointRuntimePausedForForwarding OCTET STRING,
         wsrmRemoteEndpointRuntimeMessagesThresholdTime Counter64,
         wsrmRemoteEndpointRuntimeMessagesHighCount Counter64,
         wsrmRemoteEndpointRuntimeOperationState OCTET STRING
      }
      
   
   wsrmRemoteEndpointRuntimeIndex OBJECT-TYPE
      SYNTAX      OCTET STRING
      MAX-ACCESS  not-accessible
      STATUS      current
      DESCRIPTION "Index column"
      ::= { wsrmRemoteEndpointRuntimeEntry 1  }
   
   
   wsrmRemoteEndpointRuntimeObjectName OBJECT-TYPE
      SYNTAX      OCTET STRING
      MAX-ACCESS  read-only
      STATUS      current
      DESCRIPTION "ObjectName column"
      ::= { wsrmRemoteEndpointRuntimeEntry 2  }
   
   
   wsrmRemoteEndpointRuntimeType OBJECT-TYPE
      SYNTAX      OCTET STRING
      MAX-ACCESS  read-only
      STATUS      current
      DESCRIPTION "Returns the type of the MBean."
      ::= { wsrmRemoteEndpointRuntimeEntry 3  }
   
   
   wsrmRemoteEndpointRuntimeUptimeTotal OBJECT-TYPE
      SYNTAX      Counter64
      MAX-ACCESS  read-only
      STATUS      current
      DESCRIPTION "Specifies the total time, in seconds, that the remote endpoint has been available since the last reset."
      ::= { wsrmRemoteEndpointRuntimeEntry 4  }
   
   
   wsrmRemoteEndpointRuntimeMessagesCurrentCount OBJECT-TYPE
      SYNTAX      Counter64
      MAX-ACCESS  read-only
      STATUS      current
      DESCRIPTION "Returns the current number of messages. This number includes the pending messages."
      ::= { wsrmRemoteEndpointRuntimeEntry 5  }
   
   
   wsrmRemoteEndpointRuntimeDowntimeTotal OBJECT-TYPE
      SYNTAX      Counter64
      MAX-ACCESS  read-only
      STATUS      current
      DESCRIPTION "Specifies the total time, in seconds, that the remote endpoint has not been available since the last reset."
      ::= { wsrmRemoteEndpointRuntimeEntry 6  }
   
   
   wsrmRemoteEndpointRuntimeBytesReceivedCount OBJECT-TYPE
      SYNTAX      Counter64
      MAX-ACCESS  read-only
      STATUS      current
      DESCRIPTION "The number of bytes received since the last reset."
      ::= { wsrmRemoteEndpointRuntimeEntry 7  }
   
   
   wsrmRemoteEndpointRuntimeEndpointType OBJECT-TYPE
      SYNTAX      OCTET STRING
      MAX-ACCESS  read-only
      STATUS      current
      DESCRIPTION "Specifies if the remote endpoint is a JMS or WSRM destination."
      ::= { wsrmRemoteEndpointRuntimeEntry 8  }
   
   
   wsrmRemoteEndpointRuntimeFailedMessagesTotal OBJECT-TYPE
      SYNTAX      Counter64
      MAX-ACCESS  read-only
      STATUS      current
      DESCRIPTION "Returns the total number of messages that have failed to be forwarded since the last reset."
      ::= { wsrmRemoteEndpointRuntimeEntry 9  }
   
   
   wsrmRemoteEndpointRuntimeMessagesReceivedCount OBJECT-TYPE
      SYNTAX      Counter64
      MAX-ACCESS  read-only
      STATUS      current
      DESCRIPTION "The number of messages received since the last reset."
      ::= { wsrmRemoteEndpointRuntimeEntry 10  }
   
   
   wsrmRemoteEndpointRuntimeURL OBJECT-TYPE
      SYNTAX      OCTET STRING
      MAX-ACCESS  read-only
      STATUS      current
      DESCRIPTION "The URL of the remote endpoint."
      ::= { wsrmRemoteEndpointRuntimeEntry 11  }
   
   
   wsrmRemoteEndpointRuntimePausedForIncoming OBJECT-TYPE
      SYNTAX      OCTET STRING
      MAX-ACCESS  read-only
      STATUS      current
      DESCRIPTION "Indicates if a remote endpoint is currently not accepting new messages."
      ::= { wsrmRemoteEndpointRuntimeEntry 12  }
   
   
   wsrmRemoteEndpointRuntimeName OBJECT-TYPE
      SYNTAX      OCTET STRING
      MAX-ACCESS  read-only
      STATUS      current
      DESCRIPTION "The name of this configuration. WebLogic Server uses an MBean to implement and persist the configuration."
      ::= { wsrmRemoteEndpointRuntimeEntry 13  }
   
   
   wsrmRemoteEndpointRuntimeBytesHighCount OBJECT-TYPE
      SYNTAX      Counter64
      MAX-ACCESS  read-only
      STATUS      current
      DESCRIPTION "Returns the peak number of bytes since the last reset."
      ::= { wsrmRemoteEndpointRuntimeEntry 14  }
   
   
   wsrmRemoteEndpointRuntimeUptimeHigh OBJECT-TYPE
      SYNTAX      Counter64
      MAX-ACCESS  read-only
      STATUS      current
      DESCRIPTION "Specifies the longest time, in seconds, that the remote endpoint has been available since the last reset."
      ::= { wsrmRemoteEndpointRuntimeEntry 15  }
   
   
   wsrmRemoteEndpointRuntimeBytesCurrentCount OBJECT-TYPE
      SYNTAX      Counter64
      MAX-ACCESS  read-only
      STATUS      current
      DESCRIPTION "Returns the current number of bytes. This number does not include the pending bytes."
      ::= { wsrmRemoteEndpointRuntimeEntry 16  }
   
   
   wsrmRemoteEndpointRuntimeMessagesPendingCount OBJECT-TYPE
      SYNTAX      Counter64
      MAX-ACCESS  read-only
      STATUS      current
      DESCRIPTION "Returns the number of pending messages. Pending messages are over and above the current number of messages. A pending message is one that has either been sent in a transaction and not committed, or been forwarded but has not been acknowledged."
      ::= { wsrmRemoteEndpointRuntimeEntry 17  }
   
   
   wsrmRemoteEndpointRuntimeConversationsCurrentCount OBJECT-TYPE
      SYNTAX      Counter64
      MAX-ACCESS  read-only
      STATUS      current
      DESCRIPTION "Returns the current number of conversations"
      ::= { wsrmRemoteEndpointRuntimeEntry 18  }
   
   
   wsrmRemoteEndpointRuntimeConversationsHighCount OBJECT-TYPE
      SYNTAX      Counter64
      MAX-ACCESS  read-only
      STATUS      current
      DESCRIPTION "Returns the peak number of conversations since the last reset."
      ::= { wsrmRemoteEndpointRuntimeEntry 19  }
   
   
   wsrmRemoteEndpointRuntimeConversationsTotalCount OBJECT-TYPE
      SYNTAX      Counter64
      MAX-ACCESS  read-only
      STATUS      current
      DESCRIPTION "Returns the total number of conversations since the last reset."
      ::= { wsrmRemoteEndpointRuntimeEntry 20  }
   
   
   wsrmRemoteEndpointRuntimeDowntimeHigh OBJECT-TYPE
      SYNTAX      Counter64
      MAX-ACCESS  read-only
      STATUS      current
      DESCRIPTION "Specifies the longest time, in seconds, that the remote endpoint has not been available since the last reset."
      ::= { wsrmRemoteEndpointRuntimeEntry 21  }
   
   
   wsrmRemoteEndpointRuntimeBytesThresholdTime OBJECT-TYPE
      SYNTAX      Counter64
      MAX-ACCESS  read-only
      STATUS      current
      DESCRIPTION "Returns the amount of time in the threshold condition since the last reset."
      ::= { wsrmRemoteEndpointRuntimeEntry 22  }
   
   
   wsrmRemoteEndpointRuntimeBytesPendingCount OBJECT-TYPE
      SYNTAX      Counter64
      MAX-ACCESS  read-only
      STATUS      current
      DESCRIPTION "Returns the number of pending bytes. Pending bytes are over and above the current number of bytes."
      ::= { wsrmRemoteEndpointRuntimeEntry 23  }
   
   
   wsrmRemoteEndpointRuntimePausedForForwarding OBJECT-TYPE
      SYNTAX      OCTET STRING
      MAX-ACCESS  read-only
      STATUS      current
      DESCRIPTION "Indicates if the remote endpoint is currently not forwarding messages."
      ::= { wsrmRemoteEndpointRuntimeEntry 24  }
   
   
   wsrmRemoteEndpointRuntimeMessagesThresholdTime OBJECT-TYPE
      SYNTAX      Counter64
      MAX-ACCESS  read-only
      STATUS      current
      DESCRIPTION "Returns the amount of time in the threshold condition since the last reset."
      ::= { wsrmRemoteEndpointRuntimeEntry 25  }
   
   
   wsrmRemoteEndpointRuntimeMessagesHighCount OBJECT-TYPE
      SYNTAX      Counter64
      MAX-ACCESS  read-only
      STATUS      current
      DESCRIPTION "Returns the peak number of messages since the last reset."
      ::= { wsrmRemoteEndpointRuntimeEntry 26  }
   
   
   wsrmRemoteEndpointRuntimeOperationState OBJECT-TYPE
      SYNTAX      OCTET STRING
      MAX-ACCESS  read-only
      STATUS      current
      DESCRIPTION "Specifies the state of the most recent ExireAll operation."
      ::= { wsrmRemoteEndpointRuntimeEntry 27  }
   
   
   wtcRuntimeTable OBJECT-TYPE
      SYNTAX      SEQUENCE OF WtcRuntimeEntry
      MAX-ACCESS  not-accessible
      STATUS      current
      DESCRIPTION "This class is used to 1. query, stop, and start WTC connections. 2. query, suspend, and resume WTC imported and exported services.  Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com."
      ::= { wls 1465  }
      
   
   wtcRuntimeEntry OBJECT-TYPE
      SYNTAX      WtcRuntimeEntry
      MAX-ACCESS  not-accessible
      STATUS      current
      DESCRIPTION "Generated SNMP Table Entry."
      INDEX { wtcRuntimeIndex}
      ::= { wtcRuntimeTable 1 }
      
   WtcRuntimeEntry ::=
      SEQUENCE
      {
         wtcRuntimeIndex      OCTET STRING,
         wtcRuntimeObjectName OCTET STRING,
         wtcRuntimeType       OCTET STRING,
         wtcRuntimeName       OCTET STRING
      }
      
   
   wtcRuntimeIndex OBJECT-TYPE
      SYNTAX      OCTET STRING
      MAX-ACCESS  not-accessible
      STATUS      current
      DESCRIPTION "Index column"
      ::= { wtcRuntimeEntry 1  }
   
   
   wtcRuntimeObjectName OBJECT-TYPE
      SYNTAX      OCTET STRING
      MAX-ACCESS  read-only
      STATUS      current
      DESCRIPTION "ObjectName column"
      ::= { wtcRuntimeEntry 2  }
   
   
   wtcRuntimeType OBJECT-TYPE
      SYNTAX      OCTET STRING
      MAX-ACCESS  read-only
      STATUS      current
      DESCRIPTION "Returns the type of the MBean."
      ::= { wtcRuntimeEntry 3  }
   
   
   wtcRuntimeName OBJECT-TYPE
      SYNTAX      OCTET STRING
      MAX-ACCESS  read-only
      STATUS      current
      DESCRIPTION "The name of this configuration. WebLogic Server uses an MBean to implement and persist the configuration."
      ::= { wtcRuntimeEntry 4  }
   
   
   webServiceComponentRuntimeTable OBJECT-TYPE
      SYNTAX      SEQUENCE OF WebServiceComponentRuntimeEntry
      MAX-ACCESS  not-accessible
      STATUS      current
      DESCRIPTION "Describes the state of a webservice component, which may in turn contain multiple webservices."
      ::= { wls 1470  }
      
   
   webServiceComponentRuntimeEntry OBJECT-TYPE
      SYNTAX      WebServiceComponentRuntimeEntry
      MAX-ACCESS  not-accessible
      STATUS      current
      DESCRIPTION "Generated SNMP Table Entry."
      INDEX { webServiceComponentRuntimeIndex}
      ::= { webServiceComponentRuntimeTable 1 }
      
   WebServiceComponentRuntimeEntry ::=
      SEQUENCE
      {
         webServiceComponentRuntimeIndex OCTET STRING,
         webServiceComponentRuntimeObjectName OCTET STRING,
         webServiceComponentRuntimeType OCTET STRING,
         webServiceComponentRuntimeName OCTET STRING
      }
      
   
   webServiceComponentRuntimeIndex OBJECT-TYPE
      SYNTAX      OCTET STRING
      MAX-ACCESS  not-accessible
      STATUS      current
      DESCRIPTION "Index column"
      ::= { webServiceComponentRuntimeEntry 1  }
   
   
   webServiceComponentRuntimeObjectName OBJECT-TYPE
      SYNTAX      OCTET STRING
      MAX-ACCESS  read-only
      STATUS      current
      DESCRIPTION "ObjectName column"
      ::= { webServiceComponentRuntimeEntry 2  }
   
   
   webServiceComponentRuntimeType OBJECT-TYPE
      SYNTAX      OCTET STRING
      MAX-ACCESS  read-only
      STATUS      current
      DESCRIPTION "Returns the type of the MBean."
      ::= { webServiceComponentRuntimeEntry 3  }
   
   
   webServiceComponentRuntimeName OBJECT-TYPE
      SYNTAX      OCTET STRING
      MAX-ACCESS  read-only
      STATUS      current
      DESCRIPTION "The name of this configuration. WebLogic Server uses an MBean to implement and persist the configuration."
      ::= { webServiceComponentRuntimeEntry 4  }
   
   
   webServiceHandlerRuntimeTable OBJECT-TYPE
      SYNTAX      SEQUENCE OF WebServiceHandlerRuntimeEntry
      MAX-ACCESS  not-accessible
      STATUS      current
      DESCRIPTION "Provides runtime information about a JAX-RPC handler.  Note that JAX-RPC handlers can be installed at both the service and operation levels; accordingly, instances of this interface are associated with both WebServiceRuntimeMBeans and WebServiceOperationRuntimeMBeans."
      ::= { wls 1475  }
      
   
   webServiceHandlerRuntimeEntry OBJECT-TYPE
      SYNTAX      WebServiceHandlerRuntimeEntry
      MAX-ACCESS  not-accessible
      STATUS      current
      DESCRIPTION "Generated SNMP Table Entry."
      INDEX { webServiceHandlerRuntimeIndex}
      ::= { webServiceHandlerRuntimeTable 1 }
      
   WebServiceHandlerRuntimeEntry ::=
      SEQUENCE
      {
         webServiceHandlerRuntimeIndex OCTET STRING,
         webServiceHandlerRuntimeObjectName OCTET STRING,
         webServiceHandlerRuntimeType OCTET STRING,
         webServiceHandlerRuntimeName OCTET STRING
      }
      
   
   webServiceHandlerRuntimeIndex OBJECT-TYPE
      SYNTAX      OCTET STRING
      MAX-ACCESS  not-accessible
      STATUS      current
      DESCRIPTION "Index column"
      ::= { webServiceHandlerRuntimeEntry 1  }
   
   
   webServiceHandlerRuntimeObjectName OBJECT-TYPE
      SYNTAX      OCTET STRING
      MAX-ACCESS  read-only
      STATUS      current
      DESCRIPTION "ObjectName column"
      ::= { webServiceHandlerRuntimeEntry 2  }
   
   
   webServiceHandlerRuntimeType OBJECT-TYPE
      SYNTAX      OCTET STRING
      MAX-ACCESS  read-only
      STATUS      current
      DESCRIPTION "Returns the type of the MBean."
      ::= { webServiceHandlerRuntimeEntry 3  }
   
   
   webServiceHandlerRuntimeName OBJECT-TYPE
      SYNTAX      OCTET STRING
      MAX-ACCESS  read-only
      STATUS      current
      DESCRIPTION "The name of this configuration. WebLogic Server uses an MBean to implement and persist the configuration."
      ::= { webServiceHandlerRuntimeEntry 4  }
   
   
   webServiceOperationRuntimeTable OBJECT-TYPE
      SYNTAX      SEQUENCE OF WebServiceOperationRuntimeEntry
      MAX-ACCESS  not-accessible
      STATUS      current
      DESCRIPTION "Describes the state of an individual webservice operation. This mbean provides some deployment information about the operation (such as it's backend component) as well as detailed performance statistics about its execution. A few notes about these statististics:    All times are in milliseconds.   Dispatch time  refers to the time required to parse an incoming SOAP message and locate an operation to invoke.   Excecution time  refers to the time required to execute the appropriate method on the backend component, as well as execute all of the service- and operation-level handlers associated with the operation.   Response time  refers to the time required to construct a SOAP response and send it back to the client.    The accuracy of the timings are dependent upon the operating system and JVM in use. In general, timings of very small periods of time are less likely to be accurate, and may be reported as zero."
      ::= { wls 1480  }
      
   
   webServiceOperationRuntimeEntry OBJECT-TYPE
      SYNTAX      WebServiceOperationRuntimeEntry
      MAX-ACCESS  not-accessible
      STATUS      current
      DESCRIPTION "Generated SNMP Table Entry."
      INDEX { webServiceOperationRuntimeIndex}
      ::= { webServiceOperationRuntimeTable 1 }
      
   WebServiceOperationRuntimeEntry ::=
      SEQUENCE
      {
         webServiceOperationRuntimeIndex OCTET STRING,
         webServiceOperationRuntimeObjectName OCTET STRING,
         webServiceOperationRuntimeType OCTET STRING,
         webServiceOperationRuntimeName OCTET STRING
      }
      
   
   webServiceOperationRuntimeIndex OBJECT-TYPE
      SYNTAX      OCTET STRING
      MAX-ACCESS  not-accessible
      STATUS      current
      DESCRIPTION "Index column"
      ::= { webServiceOperationRuntimeEntry 1  }
   
   
   webServiceOperationRuntimeObjectName OBJECT-TYPE
      SYNTAX      OCTET STRING
      MAX-ACCESS  read-only
      STATUS      current
      DESCRIPTION "ObjectName column"
      ::= { webServiceOperationRuntimeEntry 2  }
   
   
   webServiceOperationRuntimeType OBJECT-TYPE
      SYNTAX      OCTET STRING
      MAX-ACCESS  read-only
      STATUS      current
      DESCRIPTION "Returns the type of the MBean."
      ::= { webServiceOperationRuntimeEntry 3  }
   
   
   webServiceOperationRuntimeName OBJECT-TYPE
      SYNTAX      OCTET STRING
      MAX-ACCESS  read-only
      STATUS      current
      DESCRIPTION "The name of this configuration. WebLogic Server uses an MBean to implement and persist the configuration."
      ::= { webServiceOperationRuntimeEntry 4  }
   
   
   webServiceRuntimeTable OBJECT-TYPE
      SYNTAX      SEQUENCE OF WebServiceRuntimeEntry
      MAX-ACCESS  not-accessible
      STATUS      current
      DESCRIPTION "Describes the state of a single webservice."
      ::= { wls 1485  }
      
   
   webServiceRuntimeEntry OBJECT-TYPE
      SYNTAX      WebServiceRuntimeEntry
      MAX-ACCESS  not-accessible
      STATUS      current
      DESCRIPTION "Generated SNMP Table Entry."
      INDEX { webServiceRuntimeIndex}
      ::= { webServiceRuntimeTable 1 }
      
   WebServiceRuntimeEntry ::=
      SEQUENCE
      {
         webServiceRuntimeIndex OCTET STRING,
         webServiceRuntimeObjectName OCTET STRING,
         webServiceRuntimeType OCTET STRING,
         webServiceRuntimeName OCTET STRING
      }
      
   
   webServiceRuntimeIndex OBJECT-TYPE
      SYNTAX      OCTET STRING
      MAX-ACCESS  not-accessible
      STATUS      current
      DESCRIPTION "Index column"
      ::= { webServiceRuntimeEntry 1  }
   
   
   webServiceRuntimeObjectName OBJECT-TYPE
      SYNTAX      OCTET STRING
      MAX-ACCESS  read-only
      STATUS      current
      DESCRIPTION "ObjectName column"
      ::= { webServiceRuntimeEntry 2  }
   
   
   webServiceRuntimeType OBJECT-TYPE
      SYNTAX      OCTET STRING
      MAX-ACCESS  read-only
      STATUS      current
      DESCRIPTION "Returns the type of the MBean."
      ::= { webServiceRuntimeEntry 3  }
   
   
   webServiceRuntimeName OBJECT-TYPE
      SYNTAX      OCTET STRING
      MAX-ACCESS  read-only
      STATUS      current
      DESCRIPTION "The name of this configuration. WebLogic Server uses an MBean to implement and persist the configuration."
      ::= { webServiceRuntimeEntry 4  }
   
   
   wseeHandlerRuntimeTable OBJECT-TYPE
      SYNTAX      SEQUENCE OF WseeHandlerRuntimeEntry
      MAX-ACCESS  not-accessible
      STATUS      current
      DESCRIPTION "Provides runtime information about a SOAP message handler that has been associated with a Web Service.  SOAP message handlers are used to intercept both the inbound (request) and outbound (response) SOAP messages so that extra processing can be done on the messages. Programmers specify SOAP message handlers for a Web Service using the @SOAPMessageHandlers and @HandlerChain JWS annotations."
      ::= { wls 1490  }
      
   
   wseeHandlerRuntimeEntry OBJECT-TYPE
      SYNTAX      WseeHandlerRuntimeEntry
      MAX-ACCESS  not-accessible
      STATUS      current
      DESCRIPTION "Generated SNMP Table Entry."
      INDEX { wseeHandlerRuntimeIndex}
      ::= { wseeHandlerRuntimeTable 1 }
      
   WseeHandlerRuntimeEntry ::=
      SEQUENCE
      {
         wseeHandlerRuntimeIndex OCTET STRING,
         wseeHandlerRuntimeObjectName OCTET STRING,
         wseeHandlerRuntimeType OCTET STRING,
         wseeHandlerRuntimeName OCTET STRING
      }
      
   
   wseeHandlerRuntimeIndex OBJECT-TYPE
      SYNTAX      OCTET STRING
      MAX-ACCESS  not-accessible
      STATUS      current
      DESCRIPTION "Index column"
      ::= { wseeHandlerRuntimeEntry 1  }
   
   
   wseeHandlerRuntimeObjectName OBJECT-TYPE
      SYNTAX      OCTET STRING
      MAX-ACCESS  read-only
      STATUS      current
      DESCRIPTION "ObjectName column"
      ::= { wseeHandlerRuntimeEntry 2  }
   
   
   wseeHandlerRuntimeType OBJECT-TYPE
      SYNTAX      OCTET STRING
      MAX-ACCESS  read-only
      STATUS      current
      DESCRIPTION "Returns the type of the MBean."
      ::= { wseeHandlerRuntimeEntry 3  }
   
   
   wseeHandlerRuntimeName OBJECT-TYPE
      SYNTAX      OCTET STRING
      MAX-ACCESS  read-only
      STATUS      current
      DESCRIPTION "The name of this configuration. WebLogic Server uses an MBean to implement and persist the configuration."
      ::= { wseeHandlerRuntimeEntry 4  }
   
   
   wseeOperationRuntimeTable OBJECT-TYPE
      SYNTAX      SEQUENCE OF WseeOperationRuntimeEntry
      MAX-ACCESS  not-accessible
      STATUS      current
      DESCRIPTION "Describes the state of a particular Web Service operation, such as deployment state and runtime statistics about the execution of the operation."
      ::= { wls 1495  }
      
   
   wseeOperationRuntimeEntry OBJECT-TYPE
      SYNTAX      WseeOperationRuntimeEntry
      MAX-ACCESS  not-accessible
      STATUS      current
      DESCRIPTION "Generated SNMP Table Entry."
      INDEX { wseeOperationRuntimeIndex}
      ::= { wseeOperationRuntimeTable 1 }
      
   WseeOperationRuntimeEntry ::=
      SEQUENCE
      {
         wseeOperationRuntimeIndex OCTET STRING,
         wseeOperationRuntimeObjectName OCTET STRING,
         wseeOperationRuntimeType OCTET STRING,
         wseeOperationRuntimeResponseTimeHigh Counter64,
         wseeOperationRuntimeDispatchTimeLow Counter64,
         wseeOperationRuntimeDispatchTimeTotal Counter64,
         wseeOperationRuntimeResponseTimeLow Counter64,
         wseeOperationRuntimeResponseCount Integer32,
         wseeOperationRuntimeDispatchTimeAverage Counter64,
         wseeOperationRuntimeResponseErrorCount Integer32,
         wseeOperationRuntimeExecutionTimeLow Counter64,
         wseeOperationRuntimeOperationName OCTET STRING,
         wseeOperationRuntimeResponseTimeAverage Counter64,
         wseeOperationRuntimeExecutionTimeHigh Counter64,
         wseeOperationRuntimeExecutionTimeTotal Counter64,
         wseeOperationRuntimeDispatchTimeHigh Counter64,
         wseeOperationRuntimeExecutionTimeAverage Counter64,
         wseeOperationRuntimeInvocationCount Integer32,
         wseeOperationRuntimeResponseTimeTotal Counter64,
         wseeOperationRuntimeName OCTET STRING
      }
      
   
   wseeOperationRuntimeIndex OBJECT-TYPE
      SYNTAX      OCTET STRING
      MAX-ACCESS  not-accessible
      STATUS      current
      DESCRIPTION "Index column"
      ::= { wseeOperationRuntimeEntry 1  }
   
   
   wseeOperationRuntimeObjectName OBJECT-TYPE
      SYNTAX      OCTET STRING
      MAX-ACCESS  read-only
      STATUS      current
      DESCRIPTION "ObjectName column"
      ::= { wseeOperationRuntimeEntry 2  }
   
   
   wseeOperationRuntimeType OBJECT-TYPE
      SYNTAX      OCTET STRING
      MAX-ACCESS  read-only
      STATUS      current
      DESCRIPTION "Returns the type of the MBean."
      ::= { wseeOperationRuntimeEntry 3  }
   
   
   wseeOperationRuntimeResponseTimeHigh OBJECT-TYPE
      SYNTAX      Counter64
      MAX-ACCESS  read-only
      STATUS      current
      DESCRIPTION "Specifies the longest response time from the responses generated from invocations of this operation."
      ::= { wseeOperationRuntimeEntry 4  }
   
   
   wseeOperationRuntimeDispatchTimeLow OBJECT-TYPE
      SYNTAX      Counter64
      MAX-ACCESS  read-only
      STATUS      current
      DESCRIPTION "Specifies the lowest dispatch time for the current measurement period.  Dispatch time refer to the time for WebLogic Server to process the invocation.  The measurement period typically starts when WebLogic Server was first started."
      ::= { wseeOperationRuntimeEntry 5  }
   
   
   wseeOperationRuntimeDispatchTimeTotal OBJECT-TYPE
      SYNTAX      Counter64
      MAX-ACCESS  read-only
      STATUS      current
      DESCRIPTION "Specifies the total time for all dispatches of this operation in the current measurement period.   Dispatches refer to the time for WebLogic Server to process the invocation.  The measurement period typically starts when WebLogic Server was first started."
      ::= { wseeOperationRuntimeEntry 6  }
   
   
   wseeOperationRuntimeResponseTimeLow OBJECT-TYPE
      SYNTAX      Counter64
      MAX-ACCESS  read-only
      STATUS      current
      DESCRIPTION "Specifies the lowest response time from the responses generated from invocations of this operation."
      ::= { wseeOperationRuntimeEntry 7  }
   
   
   wseeOperationRuntimeResponseCount OBJECT-TYPE
      SYNTAX      Integer32
      MAX-ACCESS  read-only
      STATUS      current
      DESCRIPTION "Specifies the total number of responses generated from invocations of this operation."
      ::= { wseeOperationRuntimeEntry 8  }
   
   
   wseeOperationRuntimeDispatchTimeAverage OBJECT-TYPE
      SYNTAX      Counter64
      MAX-ACCESS  read-only
      STATUS      current
      DESCRIPTION "Specifies the average dispatch time for the current measurement period.  Dispatch time refer to the time for WebLogic Server to process the invocation.  The measurement period typically starts when WebLogic Server was first started."
      ::= { wseeOperationRuntimeEntry 9  }
   
   
   wseeOperationRuntimeResponseErrorCount OBJECT-TYPE
      SYNTAX      Integer32
      MAX-ACCESS  read-only
      STATUS      current
      DESCRIPTION "Specifies the total number of errors from responses generated from invocations of this operation."
      ::= { wseeOperationRuntimeEntry 10  }
   
   
   wseeOperationRuntimeExecutionTimeLow OBJECT-TYPE
      SYNTAX      Counter64
      MAX-ACCESS  read-only
      STATUS      current
      DESCRIPTION "Specifies the lowest execution time of this operation."
      ::= { wseeOperationRuntimeEntry 11  }
   
   
   wseeOperationRuntimeOperationName OBJECT-TYPE
      SYNTAX      OCTET STRING
      MAX-ACCESS  read-only
      STATUS      current
      DESCRIPTION "Specifies the name of the operation for which runtime information is being provided."
      ::= { wseeOperationRuntimeEntry 12  }
   
   
   wseeOperationRuntimeResponseTimeAverage OBJECT-TYPE
      SYNTAX      Counter64
      MAX-ACCESS  read-only
      STATUS      current
      DESCRIPTION "Specifies the average response time from the responses generated from invocations of this operation."
      ::= { wseeOperationRuntimeEntry 13  }
   
   
   wseeOperationRuntimeExecutionTimeHigh OBJECT-TYPE
      SYNTAX      Counter64
      MAX-ACCESS  read-only
      STATUS      current
      DESCRIPTION "Specifies the longest execution time of this operation."
      ::= { wseeOperationRuntimeEntry 14  }
   
   
   wseeOperationRuntimeExecutionTimeTotal OBJECT-TYPE
      SYNTAX      Counter64
      MAX-ACCESS  read-only
      STATUS      current
      DESCRIPTION "Specifies the total time for all executions of this operation."
      ::= { wseeOperationRuntimeEntry 15  }
   
   
   wseeOperationRuntimeDispatchTimeHigh OBJECT-TYPE
      SYNTAX      Counter64
      MAX-ACCESS  read-only
      STATUS      current
      DESCRIPTION "Specifies the longest dispatch time for the current measurement period.  Dispatch time refer to the time for WebLogic Server to process the invocation.  The measurement period typically starts when WebLogic Server was first started."
      ::= { wseeOperationRuntimeEntry 16  }
   
   
   wseeOperationRuntimeExecutionTimeAverage OBJECT-TYPE
      SYNTAX      Counter64
      MAX-ACCESS  read-only
      STATUS      current
      DESCRIPTION "Specifies the average execution time of this operation."
      ::= { wseeOperationRuntimeEntry 17  }
   
   
   wseeOperationRuntimeInvocationCount OBJECT-TYPE
      SYNTAX      Integer32
      MAX-ACCESS  read-only
      STATUS      current
      DESCRIPTION "Specifies the total number of times that this operation has been invoked in the current measurement period.  The measurement period typically starts when WebLogic Server was first started."
      ::= { wseeOperationRuntimeEntry 18  }
   
   
   wseeOperationRuntimeResponseTimeTotal OBJECT-TYPE
      SYNTAX      Counter64
      MAX-ACCESS  read-only
      STATUS      current
      DESCRIPTION "Specifies the total time for all responses generated from invocations of this operation."
      ::= { wseeOperationRuntimeEntry 19  }
   
   
   wseeOperationRuntimeName OBJECT-TYPE
      SYNTAX      OCTET STRING
      MAX-ACCESS  read-only
      STATUS      current
      DESCRIPTION "The name of this configuration. WebLogic Server uses an MBean to implement and persist the configuration."
      ::= { wseeOperationRuntimeEntry 20  }
   
   
   wseePolicyRuntimeTable OBJECT-TYPE
      SYNTAX      SEQUENCE OF WseePolicyRuntimeEntry
      MAX-ACCESS  not-accessible
      STATUS      current
      DESCRIPTION "Specifies runtime information about the WS-Policy files that are available for the Web Service.  Web Services can have one or more WS-Policy files associated with the endpoint itself or its operations; the WS-Policy files specify configuration options for Web Service message-level security (encryption and digital signatures) and reliable SOAP messaging.  Programmers can use the @Policy JWS annotation to associate a WS-Policy file to a Web Service at development time.  Administrators can also associate additional WS-Policy files at runtime."
      ::= { wls 1500  }
      
   
   wseePolicyRuntimeEntry OBJECT-TYPE
      SYNTAX      WseePolicyRuntimeEntry
      MAX-ACCESS  not-accessible
      STATUS      current
      DESCRIPTION "Generated SNMP Table Entry."
      INDEX { wseePolicyRuntimeIndex}
      ::= { wseePolicyRuntimeTable 1 }
      
   WseePolicyRuntimeEntry ::=
      SEQUENCE
      {
         wseePolicyRuntimeIndex OCTET STRING,
         wseePolicyRuntimeObjectName OCTET STRING,
         wseePolicyRuntimeType OCTET STRING,
         wseePolicyRuntimeName OCTET STRING
      }
      
   
   wseePolicyRuntimeIndex OBJECT-TYPE
      SYNTAX      OCTET STRING
      MAX-ACCESS  not-accessible
      STATUS      current
      DESCRIPTION "Index column"
      ::= { wseePolicyRuntimeEntry 1  }
   
   
   wseePolicyRuntimeObjectName OBJECT-TYPE
      SYNTAX      OCTET STRING
      MAX-ACCESS  read-only
      STATUS      current
      DESCRIPTION "ObjectName column"
      ::= { wseePolicyRuntimeEntry 2  }
   
   
   wseePolicyRuntimeType OBJECT-TYPE
      SYNTAX      OCTET STRING
      MAX-ACCESS  read-only
      STATUS      current
      DESCRIPTION "Returns the type of the MBean."
      ::= { wseePolicyRuntimeEntry 3  }
   
   
   wseePolicyRuntimeName OBJECT-TYPE
      SYNTAX      OCTET STRING
      MAX-ACCESS  read-only
      STATUS      current
      DESCRIPTION "The name of this configuration. WebLogic Server uses an MBean to implement and persist the configuration."
      ::= { wseePolicyRuntimeEntry 4  }
   
   
   wseePortRuntimeTable OBJECT-TYPE
      SYNTAX      SEQUENCE OF WseePortRuntimeEntry
      MAX-ACCESS  not-accessible
      STATUS      current
      DESCRIPTION "Describes the state of a particular Web Service port."
      ::= { wls 1505  }
      
   
   wseePortRuntimeEntry OBJECT-TYPE
      SYNTAX      WseePortRuntimeEntry
      MAX-ACCESS  not-accessible
      STATUS      current
      DESCRIPTION "Generated SNMP Table Entry."
      INDEX { wseePortRuntimeIndex}
      ::= { wseePortRuntimeTable 1 }
      
   WseePortRuntimeEntry ::=
      SEQUENCE
      {
         wseePortRuntimeIndex OCTET STRING,
         wseePortRuntimeObjectName OCTET STRING,
         wseePortRuntimeType  OCTET STRING,
         wseePortRuntimePortName OCTET STRING,
         wseePortRuntimeTransportProtocolType OCTET STRING,
         wseePortRuntimeName  OCTET STRING
      }
      
   
   wseePortRuntimeIndex OBJECT-TYPE
      SYNTAX      OCTET STRING
      MAX-ACCESS  not-accessible
      STATUS      current
      DESCRIPTION "Index column"
      ::= { wseePortRuntimeEntry 1  }
   
   
   wseePortRuntimeObjectName OBJECT-TYPE
      SYNTAX      OCTET STRING
      MAX-ACCESS  read-only
      STATUS      current
      DESCRIPTION "ObjectName column"
      ::= { wseePortRuntimeEntry 2  }
   
   
   wseePortRuntimeType OBJECT-TYPE
      SYNTAX      OCTET STRING
      MAX-ACCESS  read-only
      STATUS      current
      DESCRIPTION "Returns the type of the MBean."
      ::= { wseePortRuntimeEntry 3  }
   
   
   wseePortRuntimePortName OBJECT-TYPE
      SYNTAX      OCTET STRING
      MAX-ACCESS  read-only
      STATUS      current
      DESCRIPTION "Specifies the name of this port.  This attribute corresponds to the 'name' attribute of the 'port' element in the WSDL that describes the Web Service.  Programmers specify the name of the port using the portName attribute of the"
      ::= { wseePortRuntimeEntry 4  }
   
   
   wseePortRuntimeTransportProtocolType OBJECT-TYPE
      SYNTAX      OCTET STRING
      MAX-ACCESS  read-only
      STATUS      current
      DESCRIPTION "Specifies the transport protocol used to invoke this Web Service, such as HTTP, HTTPS, or JMS.  This attribute determines the transport that is published in the endpoint address section of the WSDL of the Web Service. Programmers specify the transport by the type of @WLXXXTransport JWS annotation they specify, where XXX refers to the type of transport (HTTP, HTTPS, or JMS).  Programmers can also use the WLXXXTransport child element of the jwsc Ant task to specify this attribute."
      ::= { wseePortRuntimeEntry 5  }
   
   
   wseePortRuntimeName OBJECT-TYPE
      SYNTAX      OCTET STRING
      MAX-ACCESS  read-only
      STATUS      current
      DESCRIPTION "The name of this configuration. WebLogic Server uses an MBean to implement and persist the configuration."
      ::= { wseePortRuntimeEntry 6  }
   
   
   wseeRuntimeTable OBJECT-TYPE
      SYNTAX      SEQUENCE OF WseeRuntimeEntry
      MAX-ACCESS  not-accessible
      STATUS      current
      DESCRIPTION "Encapsulates runtime information about a particular Web Service."
      ::= { wls 1510  }
      
   
   wseeRuntimeEntry OBJECT-TYPE
      SYNTAX      WseeRuntimeEntry
      MAX-ACCESS  not-accessible
      STATUS      current
      DESCRIPTION "Generated SNMP Table Entry."
      INDEX { wseeRuntimeIndex}
      ::= { wseeRuntimeTable 1 }
      
   WseeRuntimeEntry ::=
      SEQUENCE
      {
         wseeRuntimeIndex     OCTET STRING,
         wseeRuntimeObjectName OCTET STRING,
         wseeRuntimeType      OCTET STRING,
         wseeRuntimeWebserviceDescriptionName OCTET STRING,
         wseeRuntimeImplementationType OCTET STRING,
         wseeRuntimeURI       OCTET STRING,
         wseeRuntimeName      OCTET STRING,
         wseeRuntimeServiceName OCTET STRING
      }
      
   
   wseeRuntimeIndex OBJECT-TYPE
      SYNTAX      OCTET STRING
      MAX-ACCESS  not-accessible
      STATUS      current
      DESCRIPTION "Index column"
      ::= { wseeRuntimeEntry 1  }
   
   
   wseeRuntimeObjectName OBJECT-TYPE
      SYNTAX      OCTET STRING
      MAX-ACCESS  read-only
      STATUS      current
      DESCRIPTION "ObjectName column"
      ::= { wseeRuntimeEntry 2  }
   
   
   wseeRuntimeType OBJECT-TYPE
      SYNTAX      OCTET STRING
      MAX-ACCESS  read-only
      STATUS      current
      DESCRIPTION "Returns the type of the MBean."
      ::= { wseeRuntimeEntry 3  }
   
   
   wseeRuntimeWebserviceDescriptionName OBJECT-TYPE
      SYNTAX      OCTET STRING
      MAX-ACCESS  read-only
      STATUS      current
      DESCRIPTION "webservice description name for this webservice"
      ::= { wseeRuntimeEntry 4  }
   
   
   wseeRuntimeImplementationType OBJECT-TYPE
      SYNTAX      OCTET STRING
      MAX-ACCESS  read-only
      STATUS      current
      DESCRIPTION "Specifies the implementation type of this service.  The allowed values are: JAX-WS 2.0 JAX-RPC 1.1"
      ::= { wseeRuntimeEntry 5  }
   
   
   wseeRuntimeURI OBJECT-TYPE
      SYNTAX      OCTET STRING
      MAX-ACCESS  read-only
      STATUS      current
      DESCRIPTION "Specifies the URI of this Web Service.  This attribute corresponds to the final part of the endpoint address in the WSDL that describes the Web Services.  It is specified at development time using the contextPath and serviceURI attributes of the"
      ::= { wseeRuntimeEntry 6  }
   
   
   wseeRuntimeName OBJECT-TYPE
      SYNTAX      OCTET STRING
      MAX-ACCESS  read-only
      STATUS      current
      DESCRIPTION "The name of this configuration. WebLogic Server uses an MBean to implement and persist the configuration."
      ::= { wseeRuntimeEntry 7  }
   
   
   wseeRuntimeServiceName OBJECT-TYPE
      SYNTAX      OCTET STRING
      MAX-ACCESS  read-only
      STATUS      current
      DESCRIPTION "Specifies the name of this service.  This attribute corresponds to the 'name' attribute of the 'service' element in the WSDL that describes the Web Service.  It is specified at development time using the serviceName attribute of the @WebService JWS annotation."
      ::= { wseeRuntimeEntry 8  }
   
   
   scaContainerTable OBJECT-TYPE
      SYNTAX      SEQUENCE OF ScaContainerEntry
      MAX-ACCESS  not-accessible
      STATUS      current
      DESCRIPTION " "
      ::= { wls 1515  }
      
   
   scaContainerEntry OBJECT-TYPE
      SYNTAX      ScaContainerEntry
      MAX-ACCESS  not-accessible
      STATUS      current
      DESCRIPTION "Generated SNMP Table Entry."
      INDEX { scaContainerIndex}
      ::= { scaContainerTable 1 }
      
   ScaContainerEntry ::=
      SEQUENCE
      {
         scaContainerIndex    OCTET STRING,
         scaContainerObjectName OCTET STRING,
         scaContainerAllowsPassByReference OCTET STRING,
         scaContainerTimeout  Integer32,
         scaContainerType     OCTET STRING,
         scaContainerRemotable OCTET STRING,
         scaContainerName     OCTET STRING,
         scaContainerSinglePrincipal OCTET STRING,
         scaContainerAutowire OCTET STRING,
         scaContainerMaxAge   OCTET STRING,
         scaContainerMaxIdleTime OCTET STRING
      }
      
   
   scaContainerIndex OBJECT-TYPE
      SYNTAX      OCTET STRING
      MAX-ACCESS  not-accessible
      STATUS      current
      DESCRIPTION "Index column"
      ::= { scaContainerEntry 1  }
   
   
   scaContainerObjectName OBJECT-TYPE
      SYNTAX      OCTET STRING
      MAX-ACCESS  read-only
      STATUS      current
      DESCRIPTION "ObjectName column"
      ::= { scaContainerEntry 2  }
   
   
   scaContainerAllowsPassByReference OBJECT-TYPE
      SYNTAX      OCTET STRING
      MAX-ACCESS  read-only
      STATUS      current
      DESCRIPTION " "
      ::= { scaContainerEntry 3  }
   
   
   scaContainerTimeout OBJECT-TYPE
      SYNTAX      Integer32
      MAX-ACCESS  read-only
      STATUS      current
      DESCRIPTION " "
      ::= { scaContainerEntry 4  }
   
   
   scaContainerType OBJECT-TYPE
      SYNTAX      OCTET STRING
      MAX-ACCESS  read-only
      STATUS      current
      DESCRIPTION "Returns the type of the MBean. "
      ::= { scaContainerEntry 5  }
   
   
   scaContainerRemotable OBJECT-TYPE
      SYNTAX      OCTET STRING
      MAX-ACCESS  read-only
      STATUS      current
      DESCRIPTION " "
      ::= { scaContainerEntry 6  }
   
   
   scaContainerName OBJECT-TYPE
      SYNTAX      OCTET STRING
      MAX-ACCESS  read-only
      STATUS      current
      DESCRIPTION "The user-specified name of this MBean instance.  This name is included as one of the key properties in the MBean's javax.management.ObjectName: Name=user-specified-name "
      ::= { scaContainerEntry 7  }
   
   
   scaContainerSinglePrincipal OBJECT-TYPE
      SYNTAX      OCTET STRING
      MAX-ACCESS  read-only
      STATUS      current
      DESCRIPTION " "
      ::= { scaContainerEntry 8  }
   
   
   scaContainerAutowire OBJECT-TYPE
      SYNTAX      OCTET STRING
      MAX-ACCESS  read-only
      STATUS      current
      DESCRIPTION " "
      ::= { scaContainerEntry 9  }
   
   
   scaContainerMaxAge OBJECT-TYPE
      SYNTAX      OCTET STRING
      MAX-ACCESS  read-only
      STATUS      current
      DESCRIPTION "Get max of a stateful service "
      ::= { scaContainerEntry 10  }
   
   
   scaContainerMaxIdleTime OBJECT-TYPE
      SYNTAX      OCTET STRING
      MAX-ACCESS  read-only
      STATUS      current
      DESCRIPTION "Get max idle time of the a stateful service "
      ::= { scaContainerEntry 11  }
   
   
   channelRuntimeTable OBJECT-TYPE
      SYNTAX      SEQUENCE OF ChannelRuntimeEntry
      MAX-ACCESS  not-accessible
      STATUS      current
      DESCRIPTION " "
      ::= { wls 1520  }
      
   
   channelRuntimeEntry OBJECT-TYPE
      SYNTAX      ChannelRuntimeEntry
      MAX-ACCESS  not-accessible
      STATUS      current
      DESCRIPTION "Generated SNMP Table Entry."
      INDEX { channelRuntimeIndex}
      ::= { channelRuntimeTable 1 }
      
   ChannelRuntimeEntry ::=
      SEQUENCE
      {
         channelRuntimeIndex  OCTET STRING,
         channelRuntimeObjectName OCTET STRING,
         channelRuntimePublishedMessageCount Counter64,
         channelRuntimeSubscriberCount Integer32,
         channelRuntimeType   OCTET STRING,
         channelRuntimeName   OCTET STRING
      }
      
   
   channelRuntimeIndex OBJECT-TYPE
      SYNTAX      OCTET STRING
      MAX-ACCESS  not-accessible
      STATUS      current
      DESCRIPTION "Index column"
      ::= { channelRuntimeEntry 1  }
   
   
   channelRuntimeObjectName OBJECT-TYPE
      SYNTAX      OCTET STRING
      MAX-ACCESS  read-only
      STATUS      current
      DESCRIPTION "ObjectName column"
      ::= { channelRuntimeEntry 2  }
   
   
   channelRuntimePublishedMessageCount OBJECT-TYPE
      SYNTAX      Counter64
      MAX-ACCESS  read-only
      STATUS      current
      DESCRIPTION "Get the number of published messages to this Channel "
      ::= { channelRuntimeEntry 3  }
   
   
   channelRuntimeSubscriberCount OBJECT-TYPE
      SYNTAX      Integer32
      MAX-ACCESS  read-only
      STATUS      current
      DESCRIPTION "Get the number of subscribers for this channel currently "
      ::= { channelRuntimeEntry 4  }
   
   
   channelRuntimeType OBJECT-TYPE
      SYNTAX      OCTET STRING
      MAX-ACCESS  read-only
      STATUS      current
      DESCRIPTION "Returns the type of the MBean. "
      ::= { channelRuntimeEntry 5  }
   
   
   channelRuntimeName OBJECT-TYPE
      SYNTAX      OCTET STRING
      MAX-ACCESS  read-only
      STATUS      current
      DESCRIPTION "Get the qualified name for this channel "
      ::= { channelRuntimeEntry 6  }
   
   
   manAsyncReplicationRuntimeTable OBJECT-TYPE
      SYNTAX      SEQUENCE OF ManAsyncReplicationRuntimeEntry
      MAX-ACCESS  not-accessible
      STATUS      current
      DESCRIPTION "Deprecation of MBeanHome and Type-Safe Interfaces  This is a type-safe interface for a WebLogic Server MBean, which you can import into your client classes and access through weblogic.management.MBeanHome. As of 9.0, the MBeanHome interface and all type-safe interfaces for WebLogic Server MBeans are deprecated. Instead, client classes that interact with WebLogic Server MBeans should use standard JMX design patterns in which clients use the javax.management.MBeanServerConnection interface to discover MBeans, attributes, and attribute types at runtime. For more information, see 'Developing Manageable Applications with JMX' on http://edocs.bea.com. "
      ::= { wls 1525  }
      
   
   manAsyncReplicationRuntimeEntry OBJECT-TYPE
      SYNTAX      ManAsyncReplicationRuntimeEntry
      MAX-ACCESS  not-accessible
      STATUS      current
      DESCRIPTION "Generated SNMP Table Entry."
      INDEX { manAsyncReplicationRuntimeIndex}
      ::= { manAsyncReplicationRuntimeTable 1 }
      
   ManAsyncReplicationRuntimeEntry ::=
      SEQUENCE
      {
         manAsyncReplicationRuntimeIndex OCTET STRING,
         manAsyncReplicationRuntimeObjectName OCTET STRING,
         manAsyncReplicationRuntimeSecondaryServerName OCTET STRING,
         manAsyncReplicationRuntimeType OCTET STRING,
         manAsyncReplicationRuntimePrimaryCount Counter64,
         manAsyncReplicationRuntimeName OCTET STRING,
         manAsyncReplicationRuntimeRemoteClusterReachable OCTET STRING,
         manAsyncReplicationRuntimeSecondaryServerDetails OCTET STRING,
         manAsyncReplicationRuntimeSecondaryCount Counter64
      }
      
   
   manAsyncReplicationRuntimeIndex OBJECT-TYPE
      SYNTAX      OCTET STRING
      MAX-ACCESS  not-accessible
      STATUS      current
      DESCRIPTION "Index column"
      ::= { manAsyncReplicationRuntimeEntry 1  }
   
   
   manAsyncReplicationRuntimeObjectName OBJECT-TYPE
      SYNTAX      OCTET STRING
      MAX-ACCESS  read-only
      STATUS      current
      DESCRIPTION "ObjectName column"
      ::= { manAsyncReplicationRuntimeEntry 2  }
   
   
   manAsyncReplicationRuntimeSecondaryServerName OBJECT-TYPE
      SYNTAX      OCTET STRING
      MAX-ACCESS  read-only
      STATUS      current
      DESCRIPTION " Answer the name of the secondary server  "
      ::= { manAsyncReplicationRuntimeEntry 3  }
   
   
   manAsyncReplicationRuntimeType OBJECT-TYPE
      SYNTAX      OCTET STRING
      MAX-ACCESS  read-only
      STATUS      current
      DESCRIPTION "Returns the type of the MBean. "
      ::= { manAsyncReplicationRuntimeEntry 4  }
   
   
   manAsyncReplicationRuntimePrimaryCount OBJECT-TYPE
      SYNTAX      Counter64
      MAX-ACCESS  read-only
      STATUS      current
      DESCRIPTION "Answer the number of object that the local server hosts as primaries.  Answer the number of object that the local server hosts as primaries. "
      ::= { manAsyncReplicationRuntimeEntry 5  }
   
   
   manAsyncReplicationRuntimeName OBJECT-TYPE
      SYNTAX      OCTET STRING
      MAX-ACCESS  read-only
      STATUS      current
      DESCRIPTION "The name of this configuration. WebLogic Server uses an MBean to implement and persist the configuration. "
      ::= { manAsyncReplicationRuntimeEntry 6  }
   
   
   manAsyncReplicationRuntimeRemoteClusterReachable OBJECT-TYPE
      SYNTAX      OCTET STRING
      MAX-ACCESS  read-only
      STATUS      current
      DESCRIPTION "Answer if the remote cluster is reachable or not. "
      ::= { manAsyncReplicationRuntimeEntry 7  }
   
   
   manAsyncReplicationRuntimeSecondaryServerDetails OBJECT-TYPE
      SYNTAX      OCTET STRING
      MAX-ACCESS  read-only
      STATUS      current
      DESCRIPTION " Answer detailed information about the secondary server  "
      ::= { manAsyncReplicationRuntimeEntry 8  }
   
   
   manAsyncReplicationRuntimeSecondaryCount OBJECT-TYPE
      SYNTAX      Counter64
      MAX-ACCESS  read-only
      STATUS      current
      DESCRIPTION "Answer the number of object that the local server hosts as secondaries.  Answer the number of object that the local server hosts as secondaries. "
      ::= { manAsyncReplicationRuntimeEntry 9  }
   
   
   scaCompositeRuntimeTable OBJECT-TYPE
      SYNTAX      SEQUENCE OF ScaCompositeRuntimeEntry
      MAX-ACCESS  not-accessible
      STATUS      current
      DESCRIPTION " "
      ::= { wls 1530  }
      
   
   scaCompositeRuntimeEntry OBJECT-TYPE
      SYNTAX      ScaCompositeRuntimeEntry
      MAX-ACCESS  not-accessible
      STATUS      current
      DESCRIPTION "Generated SNMP Table Entry."
      INDEX { scaCompositeRuntimeIndex}
      ::= { scaCompositeRuntimeTable 1 }
      
   ScaCompositeRuntimeEntry ::=
      SEQUENCE
      {
         scaCompositeRuntimeIndex OCTET STRING,
         scaCompositeRuntimeObjectName OCTET STRING,
         scaCompositeRuntimeType OCTET STRING,
         scaCompositeRuntimeCompositeName OCTET STRING,
         scaCompositeRuntimeName OCTET STRING,
         scaCompositeRuntimeDescriptor OCTET STRING
      }
      
   
   scaCompositeRuntimeIndex OBJECT-TYPE
      SYNTAX      OCTET STRING
      MAX-ACCESS  not-accessible
      STATUS      current
      DESCRIPTION "Index column"
      ::= { scaCompositeRuntimeEntry 1  }
   
   
   scaCompositeRuntimeObjectName OBJECT-TYPE
      SYNTAX      OCTET STRING
      MAX-ACCESS  read-only
      STATUS      current
      DESCRIPTION "ObjectName column"
      ::= { scaCompositeRuntimeEntry 2  }
   
   
   scaCompositeRuntimeType OBJECT-TYPE
      SYNTAX      OCTET STRING
      MAX-ACCESS  read-only
      STATUS      current
      DESCRIPTION "Returns the type of the MBean. "
      ::= { scaCompositeRuntimeEntry 3  }
   
   
   scaCompositeRuntimeCompositeName OBJECT-TYPE
      SYNTAX      OCTET STRING
      MAX-ACCESS  read-only
      STATUS      current
      DESCRIPTION " "
      ::= { scaCompositeRuntimeEntry 4  }
   
   
   scaCompositeRuntimeName OBJECT-TYPE
      SYNTAX      OCTET STRING
      MAX-ACCESS  read-only
      STATUS      current
      DESCRIPTION "The name of this configuration. WebLogic Server uses an MBean to implement and persist the configuration. "
      ::= { scaCompositeRuntimeEntry 5  }
   
   
   scaCompositeRuntimeDescriptor OBJECT-TYPE
      SYNTAX      OCTET STRING
      MAX-ACCESS  read-only
      STATUS      current
      DESCRIPTION " "
      ::= { scaCompositeRuntimeEntry 6  }
   
   
   scaPojoComponentRuntimeTable OBJECT-TYPE
      SYNTAX      SEQUENCE OF ScaPojoComponentRuntimeEntry
      MAX-ACCESS  not-accessible
      STATUS      current
      DESCRIPTION " "
      ::= { wls 1535  }
      
   
   scaPojoComponentRuntimeEntry OBJECT-TYPE
      SYNTAX      ScaPojoComponentRuntimeEntry
      MAX-ACCESS  not-accessible
      STATUS      current
      DESCRIPTION "Generated SNMP Table Entry."
      INDEX { scaPojoComponentRuntimeIndex}
      ::= { scaPojoComponentRuntimeTable 1 }
      
   ScaPojoComponentRuntimeEntry ::=
      SEQUENCE
      {
         scaPojoComponentRuntimeIndex OCTET STRING,
         scaPojoComponentRuntimeObjectName OCTET STRING,
         scaPojoComponentRuntimeType OCTET STRING,
         scaPojoComponentRuntimeModuleId OCTET STRING,
         scaPojoComponentRuntimeName OCTET STRING,
         scaPojoComponentRuntimeDeploymentState Integer32
      }
      
   
   scaPojoComponentRuntimeIndex OBJECT-TYPE
      SYNTAX      OCTET STRING
      MAX-ACCESS  not-accessible
      STATUS      current
      DESCRIPTION "Index column"
      ::= { scaPojoComponentRuntimeEntry 1  }
   
   
   scaPojoComponentRuntimeObjectName OBJECT-TYPE
      SYNTAX      OCTET STRING
      MAX-ACCESS  read-only
      STATUS      current
      DESCRIPTION "ObjectName column"
      ::= { scaPojoComponentRuntimeEntry 2  }
   
   
   scaPojoComponentRuntimeType OBJECT-TYPE
      SYNTAX      OCTET STRING
      MAX-ACCESS  read-only
      STATUS      current
      DESCRIPTION "Returns the type of the MBean. "
      ::= { scaPojoComponentRuntimeEntry 3  }
   
   
   scaPojoComponentRuntimeModuleId OBJECT-TYPE
      SYNTAX      OCTET STRING
      MAX-ACCESS  read-only
      STATUS      current
      DESCRIPTION "Returns the identifier for this Component.  The identifier is unique within the application.  Typical modules will use the URI for their id.  Web Modules will return their context-root since the web-uri may not be unique within an EAR. "
      ::= { scaPojoComponentRuntimeEntry 4  }
   
   
   scaPojoComponentRuntimeName OBJECT-TYPE
      SYNTAX      OCTET STRING
      MAX-ACCESS  read-only
      STATUS      current
      DESCRIPTION "The name of this configuration. WebLogic Server uses an MBean to implement and persist the configuration. "
      ::= { scaPojoComponentRuntimeEntry 5  }
   
   
   scaPojoComponentRuntimeDeploymentState OBJECT-TYPE
      SYNTAX      Integer32
      MAX-ACCESS  read-only
      STATUS      current
      DESCRIPTION "The current deployment state of the module.  A module can be in one and only one of the following states. State can be changed via deployment or administrator console.  - UNPREPARED. State indicating at this  module is neither  prepared or active.  - PREPARED. State indicating at this module of this application is prepared, but not active. The classes have been loaded and the module has been validated.  - ACTIVATED. State indicating at this module  is currently active.  - NEW. State indicating this module has just been created and is being initialized. "
      ::= { scaPojoComponentRuntimeEntry 6  }
   
   
   scaSpringComponentRuntimeTable OBJECT-TYPE
      SYNTAX      SEQUENCE OF ScaSpringComponentRuntimeEntry
      MAX-ACCESS  not-accessible
      STATUS      current
      DESCRIPTION " "
      ::= { wls 1540  }
      
   
   scaSpringComponentRuntimeEntry OBJECT-TYPE
      SYNTAX      ScaSpringComponentRuntimeEntry
      MAX-ACCESS  not-accessible
      STATUS      current
      DESCRIPTION "Generated SNMP Table Entry."
      INDEX { scaSpringComponentRuntimeIndex}
      ::= { scaSpringComponentRuntimeTable 1 }
      
   ScaSpringComponentRuntimeEntry ::=
      SEQUENCE
      {
         scaSpringComponentRuntimeIndex OCTET STRING,
         scaSpringComponentRuntimeObjectName OCTET STRING,
         scaSpringComponentRuntimeType OCTET STRING,
         scaSpringComponentRuntimeModuleId OCTET STRING,
         scaSpringComponentRuntimeName OCTET STRING,
         scaSpringComponentRuntimeDeploymentState Integer32
      }
      
   
   scaSpringComponentRuntimeIndex OBJECT-TYPE
      SYNTAX      OCTET STRING
      MAX-ACCESS  not-accessible
      STATUS      current
      DESCRIPTION "Index column"
      ::= { scaSpringComponentRuntimeEntry 1  }
   
   
   scaSpringComponentRuntimeObjectName OBJECT-TYPE
      SYNTAX      OCTET STRING
      MAX-ACCESS  read-only
      STATUS      current
      DESCRIPTION "ObjectName column"
      ::= { scaSpringComponentRuntimeEntry 2  }
   
   
   scaSpringComponentRuntimeType OBJECT-TYPE
      SYNTAX      OCTET STRING
      MAX-ACCESS  read-only
      STATUS      current
      DESCRIPTION "Returns the type of the MBean. "
      ::= { scaSpringComponentRuntimeEntry 3  }
   
   
   scaSpringComponentRuntimeModuleId OBJECT-TYPE
      SYNTAX      OCTET STRING
      MAX-ACCESS  read-only
      STATUS      current
      DESCRIPTION "Returns the identifier for this Component.  The identifier is unique within the application.  Typical modules will use the URI for their id.  Web Modules will return their context-root since the web-uri may not be unique within an EAR. "
      ::= { scaSpringComponentRuntimeEntry 4  }
   
   
   scaSpringComponentRuntimeName OBJECT-TYPE
      SYNTAX      OCTET STRING
      MAX-ACCESS  read-only
      STATUS      current
      DESCRIPTION "The name of this configuration. WebLogic Server uses an MBean to implement and persist the configuration. "
      ::= { scaSpringComponentRuntimeEntry 5  }
   
   
   scaSpringComponentRuntimeDeploymentState OBJECT-TYPE
      SYNTAX      Integer32
      MAX-ACCESS  read-only
      STATUS      current
      DESCRIPTION "The current deployment state of the module.  A module can be in one and only one of the following states. State can be changed via deployment or administrator console.  - UNPREPARED. State indicating at this  module is neither  prepared or active.  - PREPARED. State indicating at this module of this application is prepared, but not active. The classes have been loaded and the module has been validated.  - ACTIVATED. State indicating at this module  is currently active.  - NEW. State indicating this module has just been created and is being initialized. "
      ::= { scaSpringComponentRuntimeEntry 6  }
   
   
   webPubSubRuntimeTable OBJECT-TYPE
      SYNTAX      SEQUENCE OF WebPubSubRuntimeEntry
      MAX-ACCESS  not-accessible
      STATUS      current
      DESCRIPTION " "
      ::= { wls 1545  }
      
   
   webPubSubRuntimeEntry OBJECT-TYPE
      SYNTAX      WebPubSubRuntimeEntry
      MAX-ACCESS  not-accessible
      STATUS      current
      DESCRIPTION "Generated SNMP Table Entry."
      INDEX { webPubSubRuntimeIndex}
      ::= { webPubSubRuntimeTable 1 }
      
   WebPubSubRuntimeEntry ::=
      SEQUENCE
      {
         webPubSubRuntimeIndex OCTET STRING,
         webPubSubRuntimeObjectName OCTET STRING,
         webPubSubRuntimeType OCTET STRING,
         webPubSubRuntimeName OCTET STRING
      }
      
   
   webPubSubRuntimeIndex OBJECT-TYPE
      SYNTAX      OCTET STRING
      MAX-ACCESS  not-accessible
      STATUS      current
      DESCRIPTION "Index column"
      ::= { webPubSubRuntimeEntry 1  }
   
   
   webPubSubRuntimeObjectName OBJECT-TYPE
      SYNTAX      OCTET STRING
      MAX-ACCESS  read-only
      STATUS      current
      DESCRIPTION "ObjectName column"
      ::= { webPubSubRuntimeEntry 2  }
   
   
   webPubSubRuntimeType OBJECT-TYPE
      SYNTAX      OCTET STRING
      MAX-ACCESS  read-only
      STATUS      current
      DESCRIPTION "Returns the type of the MBean. "
      ::= { webPubSubRuntimeEntry 3  }
   
   
   webPubSubRuntimeName OBJECT-TYPE
      SYNTAX      OCTET STRING
      MAX-ACCESS  read-only
      STATUS      current
      DESCRIPTION "Get the context-root of the webapp associated with the event router "
      ::= { webPubSubRuntimeEntry 4  }
   
   
   wlsLogNotification NOTIFICATION-TYPE
      OBJECTS {trapTime, trapServerName, trapMachineName, trapLogThreadId, trapLogTransactionId, trapLogUserId, trapLogSubsystem, trapLogMsgId, trapLogSeverity, trapLogMessage}
      STATUS      current
      DESCRIPTION "The server log."
      ::= { wls 0 60  }
   
   wlsServerStart NOTIFICATION-TYPE
      OBJECTS {trapTime, trapServerName}
      STATUS      current
      DESCRIPTION "This trap is generated when the server was started."
      ::= { wls 0 65  }
   
   wlsServerShutDown NOTIFICATION-TYPE
      OBJECTS {trapTime, trapServerName}
      STATUS      current
      DESCRIPTION "This trap is generated when the server has been shut down."
      ::= { wls 0 70  }
   
   wlsMonitorNotification NOTIFICATION-TYPE
      OBJECTS {trapTime, trapServerName, trapMonitorType, trapMonitorThreshold, trapMonitorValue, trapMBeanName, trapMBeanType, trapAttributeName}
      STATUS      current
      DESCRIPTION "This trap is generated when any JMX Monitor Notification is received."
      ::= { wls 0 75  }
   
   wlsAttributeChange NOTIFICATION-TYPE
      OBJECTS {trapTime, trapServerName, trapMBeanName, trapMBeanType, trapAttributeName, trapAttributeType, trapAttributeChangeType, trapAttributeOldVal, trapAttributeNewVal}
      STATUS      current
      DESCRIPTION "This trap is generated when an attribute change is observed."
      ::= { wls 0 80  }
   
   wlsWatchNotification NOTIFICATION-TYPE
      OBJECTS {trapTime, trapDomainName, trapServerName, trapWatchName, trapWatchRuleType, trapWatchRule, trapWatchSeverity, trapWatchData, trapWatchAlarmType, trapWatchAlarmResetPeriod, trapWatchSNMPNotificationName}
      STATUS      current
      DESCRIPTION "This trap is generated when a watch rule evaluates to true."
      ::= { wls 0 85  }
   
   wlsALSBAlert NOTIFICATION-TYPE
      OBJECTS {trapALSBAlertTrapType, trapALSBAlertSeverity, trapALSBAlertDomainName, trapALSBAlertServerName, trapALSBAlertAlertId, trapALSBAlertRuleId, trapALSBAlertRuleName, trapALSBAlertRuleCondition, trapALSBAlertAlertTime, trapALSBAlertAnnotation, trapALSBAlertServiceName, trapALSBAlertServicePath}
      STATUS      current
      DESCRIPTION "This trap is generated only in an ALSB environment where an Alert situation has occurred."
      ::= { alsb 0 90  }
   
   
END
