------------------------------------------------------------------------------
--
--  File         : sys.mi2
--  Description  : 
--  Version      :  
--  Date         : March 3, 2003
-- 	Copyright    : 2003 by maipu (sichuan) communication technology co.,ltd.
--					All rights reserved.
--
-- $Id:
-- 
------------------------------------------------------------------------------

------------------------------------------------------------------------------
MPPANELMIB DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress, 
	RowStatus, DisplayString, DateAndTime 
                                                 FROM SNMPv2-TC
        MODULE-COMPLIANCE, OBJECT-GROUP         
        	FROM SNMPv2-CONF        
        mpMgmt, MInterfaceName, MVrfName
        	FROM MAIPU-SMI
        ObjectName, ObjectSyntax, NetworkAddress
                FROM RFC1155-SMI;



mpPanelMib          	MODULE-IDENTITY
                    		LAST-UPDATED 	"0611270945Z"
                    		ORGANIZATION 	"四川迈普数据通信股份有限公司,
                    		             	 Maipu (Sichuan) Communication Technology Co. LTD."
                    		CONTACT-INFO
                    			"编 写 人:  ???
                    			 联系地址：四川省 成都市 高新区 九兴大道16号
                    			 邮    编：    610041
                    			 电    话：
                    			 传    真：
                    			 电子邮件： ????"
                    		DESCRIPTION
                      			""
                    		::= { mpMgmt  1 }



panelTable          	OBJECT-TYPE
                    		SYNTAX  SEQUENCE OF  PanelEntry
                    		MAX-ACCESS  not-accessible
                    		STATUS  
                    		DESCRIPTION
                    			"面板组件表。"
                    		::= { mpPanelMib 1 }

panelEntry          	OBJECT-TYPE
                    		SYNTAX  PanelEntry
                    		MAX-ACCESS  not-accessible
                    		STATUS  
                    		DESCRIPTION
                    			"面板组件表。"
                    		INDEX  { panelIndex }
                    		::= { panelTable 1 }

PanelEntry          	::= SEQUENCE {
                    			panelIndex             DisplayString,
                    			panelType              INTEGER,
                    			panelIfIndex           INTEGER
                    	             }


panelIndex          	OBJECT-TYPE
                    		SYNTAX  DisplayString
                    		MAX-ACCESS  read-only
                    		STATUS  
                    		DESCRIPTION
                    			"面板组件索引。"
                    		::= { panelEntry 1 }

panelType           	OBJECT-TYPE
                    		SYNTAX  INTEGER
                    		MAX-ACCESS  read-only
                    		STATUS  
                    		DESCRIPTION
                    			"面板组件类型。"
                    		::= { panelEntry 2 }

panelIfIndex        	OBJECT-TYPE
                    		SYNTAX  INTEGER
                    		MAX-ACCESS  read-only
                    		STATUS  
                    		DESCRIPTION
                    			"接口组件对应的接口表中的索引。"
                    		::= { panelEntry 3 }

cE1TimeslotsTable   	OBJECT-TYPE
                    		SYNTAX  SEQUENCE OF  CE1TimeslotsEntry
                    		MAX-ACCESS  not-accessible
                    		STATUS  
                    		DESCRIPTION
                    			"cE1时隙表。"
                    		::= { mpPanelMib 3 }

cE1TimeslotsEntry   	OBJECT-TYPE
                    		SYNTAX  CE1TimeslotsEntry
                    		MAX-ACCESS  not-accessible
                    		STATUS  
                    		DESCRIPTION
                    			"cE1时隙表。"
                    		INDEX  { cE1IfIndex }
                    		::= { cE1TimeslotsTable 1 }

CE1TimeslotsEntry   	::= SEQUENCE {
                    			cE1IfIndex             INTEGER,
                    			cE1Timeslots           INTEGER
                    	             }


cE1IfIndex          	OBJECT-TYPE
                    		SYNTAX  INTEGER
                    		MAX-ACCESS  read-only
                    		STATUS  
                    		DESCRIPTION
                    			"cE1逻辑接口索引。"
                    		::= { cE1TimeslotsEntry 1 }

cE1Timeslots        	OBJECT-TYPE
                    		SYNTAX  INTEGER
                    		MAX-ACCESS  read-only
                    		STATUS  
                    		DESCRIPTION
                    			"cE1逻辑接口上所占用的时隙。"
                    		::= { cE1TimeslotsEntry 2 }

mprSwPortTable      	OBJECT-TYPE
                    		SYNTAX  SEQUENCE OF   MprSwPortEntry
                    		MAX-ACCESS  not-accessible
                    		STATUS  current
                    		DESCRIPTION
                    			""
                    		::= { mpPanelMib 10 }

mprSwPortEntry      	OBJECT-TYPE
                    		SYNTAX  MprSwPortEntry
                    		MAX-ACCESS  not-accessible
                    		STATUS  current
                    		DESCRIPTION
                    			""
                    		INDEX  { mprSwSlotNo, mprSwPortNo }
                    		::= { mprSwPortTable 1 }

MprSwPortEntry      	::= SEQUENCE {
                    			mprSwSlotNo            INTEGER,
                    			mprSwPortNo            INTEGER,
                    			mprSwPortLinkStatus    INTEGER,
                    			mprSwPortSpeed         INTEGER,
                    			mprSwPortDeplux        INTEGER
                    	             }


mprSwSlotNo         	OBJECT-TYPE
                    		SYNTAX  INTEGER
                    		MAX-ACCESS  read-only
                    		STATUS  current
                    		DESCRIPTION
                    			"slot number"
                    		::= { mprSwPortEntry 1 }

mprSwPortNo         	OBJECT-TYPE
                    		SYNTAX  INTEGER
                    		MAX-ACCESS  read-only
                    		STATUS  current
                    		DESCRIPTION
                    			"port number"
                    		::= { mprSwPortEntry 2 }

mprSwPortLinkStatus 	OBJECT-TYPE
                    		SYNTAX  INTEGER {
                    			         up(1),
                    			          down(2)
                    			        }
                    		MAX-ACCESS  read-only
                    		STATUS  current
                    		DESCRIPTION
                    			"port link status"
                    		::= { mprSwPortEntry 3 }

mprSwPortSpeed      	OBJECT-TYPE
                    		SYNTAX  INTEGER {
                    			         unkown(1),
                    			          speed10(2),
                    			          speed100(3),
                    			          speed1000(4)
                    			        }
                    		MAX-ACCESS  read-only
                    		STATUS  current
                    		DESCRIPTION
                    			"port speed"
                    		::= { mprSwPortEntry 4 }

mprSwPortDeplux     	OBJECT-TYPE
                    		SYNTAX  INTEGER {
                    			         unkown(1),
                    			          half(2),
                    			          full(3)
                    			        }
                    		MAX-ACCESS  read-only
                    		STATUS  current
                    		DESCRIPTION
                    			"port deplux"
                    		::= { mprSwPortEntry 5 }



END
------------------------------------------------------------------------------
-- ============================================================================
-- $Log: mpPanelMib.mib,v $
-- Revision 1.1  2010/06/21 11:18:46  liyh
-- first commit
--
--
--
-- ============================================================================
