--
--  (C) Copyright IBM Corp. 1995, 1996.  All rights reserved.
--
--  U.S. Government Users Restricted Rights - Use, duplication
--  or disclosure restricted by GSA ADP Scheduled Contract
--  with IBM Corp.
--

-- ====================================================================
-- Version: 1.1 - 07/07/95
-- + agents OID for different products
-- + administrative OID for test types
-- + interface new administrative state wrap-reply
-- + interface new operational states for wrap & failing
-- + interface clocking, scrambling, subslot
-- + interface available and reserved bandwidth
-- + swap microcode
-- + switch statistics
--
-- Version: 1.2 - 08/17/95
-- + interface new operational states for bandwidth configuration
-- + switch max bandwidth
-- + version of backup microcode
--
-- Version: 1.3
-- + new tftp error code: file-already-exists
-- + new interfaceMediaType: coaxial-cable and backplane
-- + switchStatistics: rename into globalThroughput
-- + atm kit (utopia) carrier module support
-- + interfaceTable: new attribute maxBandwidth
-- + interfaceTable: new attribute frame format
-- + interfaceTable: new value for interfaceOperState:
--   disabled-no-bandwidth
-- + interfaceTable: interfaceScrambling becomes read-only
--
-- Version: 1.4
-- + support for the 8285: expansion group, featureTable
-- + moduleTable: support for the daughter cards on the atm kit
-- + support for the redundant switch
-- + support for config filetype and the save/revert option
--
-- Version: 1.5
-- + expansion group
-- + 25M module support
-- + LAN Emulation group
-- + integrated MSS server
-- + WAN interfaces
-- + functionsConfiguration
-- + Hub Chassis: chassisAgents, conc, env, modules, ocPower, ocInventory.
-- + moduleOperState: incompatible-level
-- + interfaceTable: interfaceScrambling becomes read-write
--
-- Version: 1.6
-- + 3x155M module support
-- + chassis traps
-- + PVC multicast calltype added
-- + PVC multicast : Add createAndWait value for atmPvcEpRowStatus
--
-- Version: 1.7
-- + support of the atm video module
-- + support of the atm MAN module
-- + support of a minimum proxy management
-- + support of the atm lan switch module
--
-- Version: 2.0
-- + support of pNNI port management, logical ports
-- + enhanced services
-- + enhanced signalling management
-- + support for the 8285: concType
-- + nbrTable: ipAddress2 is deprecated
-- + security
--
-- ====================================================================

ATM-SWITCHING-NODE-MIB DEFINITIONS ::= BEGIN

IMPORTS
        Counter, Gauge, IpAddress, DisplayString, enterprises,
               TimeTicks
            FROM RFC1155-SMI

        OBJECT-TYPE
            FROM RFC-1212

        MacAddress
            FROM RFC1286-MIB

        sysObjectID, ifPhysAddress, ifIndex
            FROM RFC1213-MIB;


ibm                           OBJECT IDENTIFIER ::= { enterprises 2 }

ibmProd                       OBJECT IDENTIFIER ::= { ibm 6 }

atmSw                         OBJECT IDENTIFIER ::= { ibmProd 33 }
                              -- Contact JB. Schmitt (SCHMITT at LGEPROFS)

-- TEXTUAL CONVENTIONS =====================================================

DateAndTime ::= OCTET STRING (SIZE(8))

            -- A date and time specification, from SNMPv2 RFC 1443
            --
            -- Octets Contents        Range
            -- ====== ========        =====
            --  1-2   year            0..65535
            --  3     month           1..12
            --  4     day             1..31
            --  5     hour            0..23
            --  6     minutes         0..59
            --  7     seconds         0..60  (use 60 for leap-second)
            --  8     deci-seconds    0..9

RowStatus ::= INTEGER {
                       active(1),
                       notInService(2),
                       notReady(3),
                       createAndGo(4),
                       createAndWait(5),
                       destroy(6)
                      }

            -- A way of creating/deleting rows in tables,
            -- from RMON RFC 1271 and SNMPv2 RFC 1443
            --
            -- active: row available for use by the managed device
            -- notInService: row exists but is unavailable for use
            -- notReady: row exists but some information is missing
            -- createAndGo: create and use row
            -- createAndWait: create row but do not use it now
            -- destroy: remove row

NetPrefix ::= OCTET STRING (SIZE(0..13))

           -- A network prefix part, as defined in the UNI V3.0 specification

AtmAddress ::= OCTET STRING (SIZE(0..20))

           -- An ATM Address, as defined in the UNI V3.0 specification
           -- It consists of a network prefix part and an End-User part
           --
           -- Three types of format exist for the network prefix part:
           --  a = DCC Format
           --  b = ICD Format
           --  c = E.164 Format
           --
           -- The End-User part consists of an ESI and a SEL area.
           --
           --    01 02 03 04 05 06 07 08 09 10 11 12 13 14 15 16 17 18 19 20
           --
           -- a=AFI!.DCC.!DFI!..AA...!RSRVD!.RD..!AREA.!.....ESI........!SEL
           -- b=AFI!.ICD.!DFI!..AA...!RSRVD!.RD..!AREA.!.....ESI........!SEL
           -- c=AFI!....E.164..............!.RD..!AREA.!.....ESI........!SEL


-- IBM-8260 ATM MIB ========================================================

-- ATM sub-system: ATM switch + ATM modules

node OBJECT IDENTIFIER ::= { atmSw 1 }

-- Agent Identification

agents OBJECT IDENTIFIER ::= { atmSw 2 }

ibm8260 OBJECT IDENTIFIER ::= { agents 1 }
ibm8285 OBJECT IDENTIFIER ::= { agents 2 }

-- Administrative Objects

admin OBJECT IDENTIFIER ::= { atmSw 3 }

testType OBJECT IDENTIFIER ::= { admin 1 }
internalLoopback OBJECT IDENTIFIER ::= { testType 1 }
externalLoopback OBJECT IDENTIFIER ::= { testType 2 }

-- Node Objects

base OBJECT IDENTIFIER ::= { node 1 }

dateTime OBJECT-TYPE
        SYNTAX  DateAndTime
        ACCESS  read-write
        STATUS  mandatory
        DESCRIPTION
                "The local date and time in the ATM agent."
        ::= { base 1 }

lastChange OBJECT-TYPE
        SYNTAX  DateAndTime
        ACCESS  read-only
        STATUS  deprecated
        DESCRIPTION
                "The date and time of the last major change detected:
                 - date and time reset
                 - agent IP address(es), subnet mask(s), default gateway changed
                 - LAN Emulation or IP ARP server address(es) changed
                 - system parameters (name, contact, location) changed
                 - module Changed
                   -- module added/removed
                   -- administrative State changed (isolate/attached)
                 - interface changed:
                   -- administrative State changed (enabled/disabled)
                   -- operational state changed

                 This variable is updated in relation with the following traps:
                 - hello trap
                 - change trap
                 - linkUp/linkDown traps."
        ::= { base 2 }

lock OBJECT-TYPE
        SYNTAX  INTEGER {
                         secured (1),
                         unlock (2),
                         disabled (3)
                        }
        ACCESS  read-write
        STATUS  mandatory
        DESCRIPTION
                "The purpose of this variable is to protect the path between
                 the hub and the network management station.

                 When set to secure (1), it is not possible to:
                 - disable a port:
                   -- if the SNMP request was received on this port
                   -- if a LAN Emulation or an IP ARP server is on this port
                 - isolate a module:
                   -- if the SNMP request was received on this port
                   -- if a LAN Emulation or an IP ARP server is on this port

                 When set to unlock (2), the parameters referenced
                 above can be modified for a limited time (30 seconds).

                 When set to disabled (3), no protection is provided.

                 Trying to modify one of these parameters results in a
                 genErr error code in the Get-Response and a trap is
                 returned to the agent."
        ::= { base 3 }

ipArpServerAtmAddress OBJECT-TYPE
        SYNTAX  AtmAddress
        ACCESS  read-write
        STATUS  mandatory
        DESCRIPTION
                "The ATM address of the ARP server used when communicating
                 with the switch agent using Classical IP over ATM (RFC 1577)."
        ::= { base 4 }

-- base.5 intentionnally left unused

systemState OBJECT-TYPE
        SYNTAX  INTEGER {
                         reset (1),
                         switch-a (2),
                         switch-b (3),
                         base-only (4)
                        }
        ACCESS  read-write
        STATUS  mandatory
        DESCRIPTION
                "This variables indicates the currently active switch.
                 When the active switch is in slots 9/10, switch-a is returned.
                 When the active switch is in slots 11/12, switch-b is returned.
                 On a 8285 ATM workgroup, when there is no expansion
                 installed, base-only is returned; when there is an
                 expansion installed, switch-a is returned.
                 When reset is set, the complete atm-subsystem is reset and a
                 switch swap over may occur if the switch electing conditions
                 have changed since the last reset."
        ::= { base 6 }

backupMode  OBJECT-TYPE
        SYNTAX  INTEGER {
                         noBackUp (1),
                         primary (2),
                         secondary (3)
                        }
        ACCESS  read-write
        STATUS  mandatory
        DESCRIPTION
                "This variable controls the way the active switch
                 will be elected at the next reset of the atm subsystem,
                 and controls also the reset of the atm-subsystem.
                 When set to primary, the switch module currently in use
                 is defined as the primary switch to elect as the active
                 switch, if possible, at the next reset of the atm subsystem.
                 When set to secondary, the switch module currently in use
                 is defined as the secondary switch. If another switch
                 module is present, and can be elected then this
                 other switch will become the active
                 switch, at the next reset of the atm subsystem.
                 noBackUp is returned for the atm subsystems which do
                 not support the redundant switch function."
        ::= { base 7 }

functionsConfiguration  OBJECT-TYPE
        SYNTAX  INTEGER {
                         dynamicRouting-noLanEmulationServer (1),
                         staticRouting-LanEmulationServer (2),
                         dynamicRouting-LanEmulationServer (3)
                        }
        ACCESS  read-write
        STATUS  mandatory
        DESCRIPTION
                "This variable controls the configuration of the
                 functions in the control point.
                 This attribute cannot be set in the 8285, when read,
                 on a 8285 functionsConfiguration is always equal to
                 dynamicRouting-LanEmulationServer.
                 When this attribute is set, the configuration of
                 the functions is saved in the non volatile memory
                 and the atm subsystem is automatically reset.
                 When dynamicRouting-noLanEmulationServer is set
                 the dynamic routing function is active. The selection
                 of the routes when a connection is established
                 will be automatic through the SSI ports.
                 The LAN emulation servers cannot be started if
                 functionsConfiguration is equal to
                 dynamicRouting-noLanEmulationServer.
                 When staticRouting-LanEmulationServer is set, no automatic
                 route selection accross the SSI ports will be performed
                 by the atm-subsystem.
                 The routing will be performed only through the
                 defined static routes.
                 The ports cannot be set with the atm access equal to SSI.
                 All the ports previously configured as SSI ports are
                 changed to UNI, when the atm-subsystem is restarts after
                 the change of functionsConfiguration into
                 staticRouting-LanEmulationServer.
                 dynamicRouting-LanEmulationServer cannot be set on an
                 8260."
        ::= { base 8 }


-- Traps Control

traps OBJECT IDENTIFIER ::= { node 2 }

hello OBJECT-TYPE
        SYNTAX  INTEGER  {
                          enabled (1),
                          disabled (2)
                         }
        ACCESS  read-write
        STATUS  mandatory
        DESCRIPTION
                "When disabled, the hello trap is neither sent.
                 When enabled, the hello trap can be sent by the agent when the
                 appropriate trap condition is detected."
        ::= { traps 1 }

-- Physical Description

physical OBJECT IDENTIFIER ::= { node 3 }

-- Switch Control

switchTable  OBJECT-TYPE
        SYNTAX  SEQUENCE OF SwitchEntry
        ACCESS  not-accessible
        STATUS  mandatory
        DESCRIPTION
                "This table controls slot attachement to the ATM switch.
                 An ATM module is operational only when inserted in a slot which
                 is defined as attached to the switch."
        ::= { physical 1}

switchEntry OBJECT-TYPE
        SYNTAX  SwitchEntry
        ACCESS  not-accessible
        STATUS  mandatory
        DESCRIPTION
                "Entries of switchTable. Each entry corresponds to a slot that
                 is physically wired to the switch. These slots may be attached
                 to or isolated from the ATM switch."
        INDEX { switchSlotIndex }
        ::= { switchTable 1 }

SwitchEntry ::= SEQUENCE {
        switchSlotIndex
                INTEGER,
        switchAdminState
                INTEGER,
        switchOperState
                INTEGER
       }

switchSlotIndex OBJECT-TYPE
        SYNTAX  INTEGER (1..64)
        ACCESS  read-only
        STATUS  mandatory
        DESCRIPTION
                "A slot number controlled by the switch."
        ::= { switchEntry 1 }

switchAdminState OBJECT-TYPE
        SYNTAX  INTEGER {
                         isolate (1),
                         attach (2)
                        }
        ACCESS  read-write
        STATUS  mandatory
        DESCRIPTION
                "The desired state of the slot connection to the switch.

                 When a slot is isolated from the switch, the switch traffic
                 from this slot to the switch is disabled. As a result, if
                 an ATM module is plugged in this slot, it will not be
                 operational.

                 When a slot is attached to the switch, the switch is ready
                 to receive ATM traffic from this slot. As a result, if an
                 ATM module is plugged in this slot, it can be used for
                 ATM traffic."
        ::= { switchEntry 2 }

switchOperState  OBJECT-TYPE
        SYNTAX  INTEGER {
                         isolated (1),
                         attached (2)
                        }
        ACCESS  read-only
        STATUS  mandatory
        DESCRIPTION
                "The actual state of the slot connection to the switch.

                When the administrative state is set to ISOLATE, the
                operational state becomes ISOLATED.

                When the operational state is set to ATTACH, the operational
                state may become either ATTACHED or ISOLATED depending on
                the hardware current status of the slot."
        ::= { switchEntry 3 }

-- ATM modules

moduleTable  OBJECT-TYPE
        SYNTAX  SEQUENCE OF ModuleEntry
        ACCESS  not-accessible
        STATUS  mandatory
        DESCRIPTION
                "This table provides the list of ATM modules in the hub."
        ::= { physical 2}

moduleEntry OBJECT-TYPE
         SYNTAX  ModuleEntry
        ACCESS  not-accessible
        STATUS  mandatory
        DESCRIPTION
                "Entries of moduleTable."
        INDEX { moduleSlotIndex }
        ::= { moduleTable 1 }

ModuleEntry ::= SEQUENCE {
        moduleSlotIndex
                INTEGER,
        moduleType
                INTEGER,
        moduleDescription
                DisplayString,
        moduleSerialNumber
                DisplayString,
        moduleSoftwareVersion
                DisplayString,
        moduleHardwareVersion
                INTEGER,
        moduleAdminState
                INTEGER,
        moduleOperState
                INTEGER,
        moduleErrors
                Counter,
        moduleMaxVpc
                INTEGER,
        moduleUsedVpc
                INTEGER,
        moduleMaxVcc
                INTEGER,
        moduleUsedVcc
                INTEGER
        }

moduleSlotIndex OBJECT-TYPE
        SYNTAX  INTEGER (1..64)
        ACCESS  read-only
        STATUS  mandatory
        DESCRIPTION
                "The slot number for this module."
        ::= { moduleEntry 1 }

moduleType OBJECT-TYPE
        SYNTAX  INTEGER {
                         unknown (1),
                         switch (2),
                         atm-100-Mbps (3),
                         atm-155-Mbps-2-ports-LAN (4),
                         atm-kit (5),
                         atm-base (6),
                         atm-25-Mbps-and-155-Mbps-LAN (7),
                         atm-155-Mbps-3-ports-LAN (8),
                         atm-lan-bridge (51),
                         atm-wan (52),
                         atm-mss-server (53),
                         atm-lan-switch (54),
                         atm-man (55),
                         atm-video (56),
                         atm-622-Mbps-left (57),
                         atm-622-Mbps-right (58),
                         atm-circuit-emulation-service (59),
                         atm-8271-ethernet (60),
                         atm-8272-token-ring (61)
                        }
        ACCESS  read-only
        STATUS  mandatory
        DESCRIPTION
                "The type of module attached to the ATM switch in this
                 slot.
                 The 'unknown' value is used when the ATM agent
                 is unable to get information for this module (the
                 module is isolated from the switch or is not operational)."
        ::= { moduleEntry 2 }

moduleDescription OBJECT-TYPE
        SYNTAX  DisplayString (SIZE (0..255))
        ACCESS  read-only
        STATUS  mandatory
        DESCRIPTION
                "A textual description of this module.
                 This description is blank when no description is available."
        ::= { moduleEntry 3 }

moduleSerialNumber OBJECT-TYPE
        SYNTAX  DisplayString (SIZE (0..13))
        ACCESS  read-only
        STATUS  mandatory
        DESCRIPTION
                "The serial number for this module."
        ::= { moduleEntry 4 }

moduleSoftwareVersion OBJECT-TYPE
        SYNTAX  DisplayString
        ACCESS  read-only
        STATUS  mandatory
        DESCRIPTION
                "The version and release number for this module
                 firmware (microcode)."
        ::= { moduleEntry 5 }

moduleHardwareVersion OBJECT-TYPE
        SYNTAX  DisplayString
        ACCESS  read-only
        STATUS  mandatory
        DESCRIPTION
                "The Part Number (P/N) and Engineering Change (EC) level
                 for this module and Plant Location."
        ::= { moduleEntry 6 }

moduleAdminState OBJECT-TYPE
        SYNTAX  INTEGER {
                         ready (1),
                         reset (2)
                        }
        ACCESS  read-write
        STATUS  mandatory
        DESCRIPTION
                "The administrative state of this module.
                On an 8260, when set to reset for an entry associated to
                the active switch/control point module, the whole atm subsystem is
                reset and a switch swap over may occur if the backupMode
                criterium has been changed since the last reset.
                When set to reset for an entry associated to a module
                which is not the active Control Point/Switch module,
                only this module is reset."
        ::= { moduleEntry 7 }

moduleOperState OBJECT-TYPE
        SYNTAX  INTEGER {
                         unknown (1),
                         operational (2),
                         not-operational (3),
                         standby (4),
                         maintenance (5),
                         testing (6),
                         switch-error (7),
                         incompatible-level (8)
                        }
        ACCESS  read-only
        STATUS  mandatory
        DESCRIPTION
                "The operational state of this module.
                When unknown, the module cannot be accessed
                by the Control Point.
                When operational, the module is operational.
                When not-operational, the module is not operational.
                When standby, the module is a redundant switch module
                ready to be used.
                When maintenance, the module is a redundant switch
                module currently in maintenance mode.
                When testing, the module is a redundant switch module
                currently running diagnostics.
                When switch-error, the module is a redundant switch module
                not operational, not ready to be used because an error
                has been detected.
                When incompatible-level the module is a redundant switch module
                operational, but its microcode level is not compatible with
                the microcode level of the active control point switch
                module and the active configuration is not copied in the
                redundant module. If a switch over is performed, the
                current configuration is not restored. To guarantee a
                good restoration, the back level switch must be upgraded.
                "
        ::= { moduleEntry 8 }

moduleErrors    OBJECT-TYPE
        SYNTAX  Counter
        ACCESS  read-only
        STATUS  mandatory
        DESCRIPTION
                "The number of errors detected by this module on the traffic
                 from the switch to this module."
        ::= { moduleEntry 9 }

moduleMaxVpc OBJECT-TYPE
        SYNTAX  INTEGER
        ACCESS  read-only
        STATUS  mandatory
        DESCRIPTION
                "The maximum number of VPC supported by this module.
                 The current number of VPC that can be used is the difference
                 between moduleMaxVpc and moduleUsedVpc."
        ::= { moduleEntry 10 }

moduleUsedVpc OBJECT-TYPE
        SYNTAX  INTEGER
        ACCESS  read-only
        STATUS  mandatory
        DESCRIPTION
                "The number of VPCs currently in use for this module.
                 The current number of VPCs that can be used is the difference
                 between moduleMaxVpc and moduleUsedVpc."
        ::= { moduleEntry 11 }

moduleMaxVcc OBJECT-TYPE
        SYNTAX  INTEGER
        ACCESS  read-only
        STATUS  mandatory
        DESCRIPTION
                "The maximum number of VCCs supported by this module.
                 The current number of VCCs that can be used is the difference
                 between moduleMaxVcc and moduleUsedVcc."
        ::= { moduleEntry 12  }

moduleUsedVcc OBJECT-TYPE
        SYNTAX  INTEGER
        ACCESS  read-only
        STATUS  mandatory
        DESCRIPTION
                "The number of VCC currently in use for this module.
                 The current number of VCC that can be used is the difference
                 between moduleMaxVcc and moduleUsedVcc."
        ::= { moduleEntry 13  }

-- ATM ports

portTable  OBJECT-TYPE
        SYNTAX  SEQUENCE OF PortEntry
        ACCESS  not-accessible
        STATUS  mandatory
        DESCRIPTION
                "This table provides the list of ports attached to
                 the ATM switch (ATM ports). These ports belong to ATM modules
                 inserted in slots that are attached to the ATM switch."
        ::= { physical 3}

portEntry OBJECT-TYPE
        SYNTAX  PortEntry
        ACCESS  not-accessible
        STATUS  mandatory
        DESCRIPTION
                "Entries of portTable. Each entry corresponds to a port that
                 belongs to an ATM module. This module must be inserted in a
                 slot that is attached to the ATM switch."
        INDEX { portSlotIndex,
                portIndex }
        ::= { portTable 1 }

PortEntry ::= SEQUENCE {
        portSlotIndex
              INTEGER,
        portIndex
              INTEGER,
        portInterface
              INTEGER
        }

portSlotIndex OBJECT-TYPE
        SYNTAX  INTEGER (1..64)
        ACCESS  read-only
        STATUS  mandatory
        DESCRIPTION
                "The slot number of this port's module."
        ::= { portEntry 1 }

portIndex OBJECT-TYPE
        SYNTAX  INTEGER (1..64)
        ACCESS  read-only
        STATUS  mandatory
        DESCRIPTION
                "The port number for this module."
        ::= { portEntry 2 }

portInterface OBJECT-TYPE
        SYNTAX  INTEGER
        ACCESS  read-only
        STATUS  mandatory
        DESCRIPTION
                "The interface number of this port."
        ::= { portEntry 3 }

-- ATM interfaces

interfaceTable  OBJECT-TYPE
        SYNTAX  SEQUENCE OF InterfaceEntry
        ACCESS  not-accessible
        STATUS  mandatory
        DESCRIPTION
                "For each ATM port, this table maps the MIB-II interface
                 index for this port with its physical slot and port numbers."
        ::= { physical 4}

interfaceEntry OBJECT-TYPE
        SYNTAX  InterfaceEntry
        ACCESS  not-accessible
        STATUS  mandatory
        DESCRIPTION
                "Entries of the interfaceTable.
                 Each entry corresponds to a port that belongs to an ATM module.
                 This module must be inserted in a slot
                 that is attached to the ATM switch."
        INDEX { interfaceIndex }
        ::= { interfaceTable 1 }

InterfaceEntry ::= SEQUENCE {
        interfaceIndex
              INTEGER,
        interfaceSlot
              INTEGER,
        interfacePort
              INTEGER,
        interfaceConnector
              INTEGER,
        interfaceAdminState
              INTEGER,
        interfaceOperState
              INTEGER,
        interfaceAtmAccess
              INTEGER,
        interfaceMediaType
               INTEGER,
        interfaceMediaSpeed
              INTEGER,
        interfaceMediaErrors
              Counter,
        interfaceSubSlot
              INTEGER,
        interfaceClocking
              INTEGER,
        interfaceScrambling
              INTEGER,
        interfaceAvailableBandwidth
              INTEGER,
        interfaceAllocatedBandwidth
              INTEGER,
        interfaceMaxBandwidth
              INTEGER,
        interfaceFrameFormat
              INTEGER
        }

interfaceIndex OBJECT-TYPE
        SYNTAX  INTEGER
        ACCESS  read-only
        STATUS  mandatory
        DESCRIPTION
                "The interface number of the port represented by this entry.
                 This is the same number as the index used to represent this
                 interface in the MIB-II interface table."
        ::= { interfaceEntry 1 }

interfaceSlot OBJECT-TYPE
        SYNTAX  INTEGER (1..64)
        ACCESS  read-only
        STATUS  mandatory
        DESCRIPTION
                "The slot number of this ATM port's module."
        ::= { interfaceEntry 2 }

interfacePort OBJECT-TYPE
        SYNTAX  INTEGER (1..64)
        ACCESS  read-only
        STATUS  mandatory
        DESCRIPTION
                "The port number of this ATM port."
        ::= { interfaceEntry 3 }

interfaceConnector OBJECT-TYPE
        SYNTAX  INTEGER {
                        unknown (1),
                        internal (2),
                        mic   (3),
                        sc-Duplex (4),
                        monomode (5),
                        db-9 (6),
                        rj45 (7),
                        bnc (8),
                        db-15 (9)
                        }
        ACCESS  read-only
        STATUS  mandatory
        DESCRIPTION
                "Whether this port is an internal port (on the backplane)
                 or an external connector."
        ::= { interfaceEntry 4 }

interfaceAdminState OBJECT-TYPE
        SYNTAX  INTEGER {
                        enabled (1),
                        disabled (2),
                        wrap-reply (3),
                        wrap-far-end (4),
                        reset-to-default (5)
                        }
         ACCESS  read-write
        STATUS  mandatory
        DESCRIPTION
                "The administrative state for this port.
                 When set to disabled, no ATM traffic can pass on this
                 port; all connections (SVC and PVC) are cleared.
                 When set to wrap-reply, this interface is wrapped so that
                 all the traffic received from the attached line is sent
                 back on this line. If the interface state is not changed,
                 it will automatically go back to the disabled state after
                 one minute.
                 When interfaceAdminState is equal to wrap-far-end,
                 then the interface located on the other side of the
                 link is now wrapped.
                 wrap-reply can only be set for 155 and wan ports.
                 wrap-far-end cannot be set.
                 When reset-to-default is set, the port is disabled
                 and its attributes are reset to the default values.
                 reset-to-default cannot be read.
                 reset-to-default applies only for 8260 agents v3.0
                 or 8285 agents v2.0 and higher."
        ::= { interfaceEntry 5 }

interfaceOperState OBJECT-TYPE
        SYNTAX  INTEGER {
                        unknown (1),
                        disabled-nosignal (2),
                        disabled-idle (3),
                        no-signal (4),
                        idle (5),
                        in-service (6),
                        in-service-no-address-registration (7),
                        failing-internal (8),
                        misConfigured (9),
                        wrongNetworkPrefix (10),
                        wrongNodeNumber (11),
                        disabled-failing (12),
                        failing-line (13),
                        wrap-no-signal (14),
                        wrap-idle (15),
                        wrap-failing-internal (16),
                        wrap-failing-line (17),
                        idle-no-bandwidth (18),
                        idle-internal-error (19),
                        disabled-no-bandwidth (20),
                        wrap-far-end-no-signal (21),
                        wrap-far-end-idle (22),
                        wrap-far-end-failing (23),
                        wrap-far-end-failing-line (24),
                        insufficient-connection-handles (25),
                        invalid-remote-vpi-vci-range (26),
                        control-vpi-already-used (27),
                        missing-signalling-version (28)
                        }
        ACCESS  read-only
        STATUS  mandatory
        DESCRIPTION
                "The operational state for this port:
                 - unknown: the status of this port is unknown (this can
                            be the result of a module in error)
                 - disabled-nosignal: no activity is detected at the physical
                                      layer while the port is disabled.
                                      If the port is a SSI port, the
                                      bandwidth configuration is valid.
                 - disabled-idle:: activity from the remote device
                                   attached to this port has been
                                   detected by the physical layer.
                                   The port is disabled.
                                   If the port is a SSI port, the bandwidth
                                   configuration is valid.
                 - failing: an internal hard error has been detected on
                            this port while the port is enabled
                 - no signal: no activity is detected at the physical
                              layer while the port is enabled
                 - idle: activity from the remote device attached to this
                         port has been detected by the physical layer.
                         The port is enabled.
                 - in-service: the remote device successfully acknowledges
                               ILMI polling requests and SVC registration
                 - in-service-no-address-registration:
                            the remote device succesfully acknowledges
                            ILMI polling requests but it rejects the ATM
                            prefix registration. Only PVCs are supported.
                 - misConfigured:
                                  This value is only reported by 8260 agents
                                  before v3.0 (8285 agents before v2.0).
                                  In that case, misConfigured is returned when
                                  a privateNetwork port is attached to a
                                  privateUni or to a publicUni port.
                 - wrongNetworkPrefix:
                                  This value is only reported by 8260 agents
                                  before v3.0 (8285 agents before v2.0).
                                  In that case, wrongNetworkPrefix is returned
                                  when
                                  the switches on each end of a privateNetwork
                                  link have incompatible network prefixes (the
                                  12 first bytes have different values)
                 - wrongNodeNumber:
                                  This value is only reported by 8260 agents
                                  before v3.0 (8285 agents before v2.0).
                                  In that case, wrongNodeNumber is returned
                                  when
                                  the switches on each end of an privateNetwork
                                  link have the same ATM node Numbers.
                 - failing-line: the port is enabled and a invalid
                                 signal is detected on the line
                 - disabled-failing: the port is disabled and an
                                     anomaly is detected, either internal
                                     or external.
                 - wrap-no-signal: the port is internally wrapped so that
                               all the traffic received on the attached line is
                               returned unchanged on the line.
                               No activity is detected at the physical
                               layer.
                 - wrap-idle: the port is internally wrapped so that
                              all the traffic received on the attached line is
                              returned unchanged on the line and
                              a valid signal is detected on the line.
                 - wrap-failing-internal: an internal failure has been
                                          detected when the port has been
                                          turned into the wrap-reply state.
                                          The actual state of the port is
                                          undefined.
                 - wrap-failing-line: the port is internally wrapped so that
                                      all the traffic received on the attached
                                      line is returned unchanged on the line
                                      and an invalid signal is detected
                                      on the line.
                 - idle-no-bandwidth: the port is enabled and activity
                                 from the remote device is detected but
                                 there is no enough bandwidth to operate
                                 the port with its current configuration.
                                 This state applies for privateNetwork.
                 - idle-internal-error: The port is enabled and activity
                                 from the remote device is detected but
                                 an internal error has occurred during
                                 the checking of the port configuration.
                 - disabled-no-bandwidth:
                                 This value is only reported by 8260 agents
                                 before v3.0 (8285 agents before v2.0).
                                 the enabling of the port is not
                                 possible because
                                 there is not enough bandwidth to operate
                                 the port with its current configuration.
                                 This state applies for privateNetwork.
                 - wrap-far-end-no-signal:
                                 the port is in wrap-far-end
                                 mode, ie the remote end of the line is
                                 wrapped, and no signal is detected on the
                                 line.
                 - wrap-far-end-idle:
                                 the port is in wrap-far-end
                                 mode, ie the remote end of the line is
                                 wrapped, and a valid signal is detected
                                 on the line.
                 - wrap-far-end-failing:
                                 the port is in wrap-far-end
                                 mode, ie the remote end of the line is
                                 wrapped, and an internal error is detected.
                 - wrap-far-end-failing-line:
                                 the port is in wrap-far-end
                                 mode, ie the remote end of the line is
                                 wrapped, and an invalid signal is detected
                                 on the line.
                 - insufficient-connection-handles
                                 For 8260 agents v3.0 (8285 v2.0) and higher.
                                 The port is enabled and activity is
                                 detected on the line but too many
                                 connections are active on the module
                                 and the control connections for this port
                                 cannot be set.
                 - invalid-remote-vpi-vci-range
                                 For 8260 agents v3.0 (8285 v2.0) and higher.
                                 The port is enabled and activity is
                                 detected on the line but the number of bits
                                 for the vpi or the vci reported by the
                                 attached device is not supported in the atm
                                 subsystem.
                 - control-vpi-already-used
                                 For 8260 agents v3.0 (8285 v2.0) and higher.
                                 The port is enabled and activity is
                                 detected on the line but the vpi value
                                 assigned for the ilmi, signalling and
                                 routing channels is already used by a
                                 VP tunnel.
                 - missing-signalling-version:
                                 For 8260 agents v3.0 (8285 v2.0) and higher.
                                 The port is enabled and activity is
                                 detected on the line but the ilmi is
                                 disabled and the signalling version is set
                                 to autoConfig.


                 When disabled, the port may be in only one of the following
                 states:
                 - unknown, disabled-failing, disabled-nosignal or
                   disabled-idle, disabled-no-bandwidth."
        ::= { interfaceEntry 6 }

interfaceAtmAccess OBJECT-TYPE
        SYNTAX  INTEGER {
                        unknown (1),
                        privateUni (2),
                        privateNetwork (3),
                        publicUni (4),
                        void (7)
                        }
        ACCESS  read-write
        STATUS  mandatory
        DESCRIPTION
                "The type of ATM access offered on this port:
                 - privateUni: User Network Interface
                 - privateNetwork: Switch-to-Switch interface
                     This atmAccess was called SSI in the 8260 agents
                     before v3.0 (v2.0 for 8285).
                     NOTE: If a port is set to this value from a different type,
                           the corresponding atmConfigSigType (in the atmSigTable)
                           will be set to atmfIispUni3Dot1 by default, and
                           atmConfigSigSide will be set by default to user.
                           To set different values for these parameters, use the
                           atmSigTable.
                 - publicUni: public User to Network interface.
                     This atmAccess was called NNI in the 8260 agents
                     before v3.0 (v2.0 for 8285).
                     ILMI can run on the publicUni ports.
                     A VP tunnel can be created on such a port.
                 - void: public User to Network interface
                     without signalling and ILMI.
                     A VP tunnel can be created on such a port.

                 The ATM access can be modified only when the
                 port is disabled.
                 The only valid ATM access for the utopia
                 port connecting the atm-lan-bridge, or atm-mss-server,
                 or atm-man or atm-video modules is uni."
        ::= { interfaceEntry 7 }

interfaceMediaType OBJECT-TYPE
        SYNTAX  INTEGER {
                        unknown (1),
                        monomode-fiber (2),
                        multimode-fiber (3),
                        twistedPair (4),
                        utp (5),
                        stp (6),
                        coaxial-cable (7),
                        backplane (8),
                        long-range-fiber (9),
                        unspecified-fiber (10)
                        }
        ACCESS  read-only
        STATUS  mandatory
        DESCRIPTION
                "The type of media supported on  this port."
        ::= { interfaceEntry 8 }

interfaceMediaSpeed OBJECT-TYPE
        SYNTAX  INTEGER
        ACCESS read-only
        STATUS  mandatory
        DESCRIPTION
                "The speed of this interface, in bits per second."
         ::= { interfaceEntry 9 }

interfaceMediaErrors OBJECT-TYPE
        SYNTAX  Counter
        ACCESS  read-only
        STATUS  mandatory
        DESCRIPTION
                "The number of physical layer errors detected on this media
                such as violation errors and length errors."
        ::= { interfaceEntry 10}

interfaceSubSlot OBJECT-TYPE
        SYNTAX  INTEGER
        ACCESS  read-only
        STATUS  mandatory
        DESCRIPTION
                "When equal to 0, this interface (and its physical connector)
                is directly located on the module identified by the slot
                number.
                When equal to a non-zero value, this number identifies a
                feature card of the module that is used by this interface."
        ::= { interfaceEntry 11}

interfaceClocking OBJECT-TYPE
        SYNTAX  INTEGER {
                         internal (1),
                         external (2)
                        }
        ACCESS  read-write
        STATUS  mandatory
        DESCRIPTION
                "The source of the bit clock used for data transmission.
                When set to external, the source is the clock received
                from the line.
                The clocking can be modified only when the
                port is disabled.
                In the 8260 agents before v3.0 (8285 v2.0),
                the clocking can only be modified on 155 Mbits ports
                for which the atm access is privateUni (previously called UNI)
                or publicUni (previously called NNI)."
        ::= { interfaceEntry 12}

interfaceScrambling OBJECT-TYPE
        SYNTAX  INTEGER {
                         off (1),
                         cell (2),
                         frame (3),
                         cell-and-frame (4),
                         cell-in-receive-only (5),
                         cell-in-transmit-only (6)
                        }
        ACCESS  read-write
        STATUS  mandatory
        DESCRIPTION
                "Whether data scrambling is used when transmitting on this
                line. Scrambling may be applied at the cell level,
                at the frame level or at cell and frame level.
                The scrambling configuration can only be modified
                for a wan interface.
                cell-in-receive-only applies only for a wan interface.
                In this case, the cells are descrambled when received,
                and are not scrambled when transmitted.
                cell-in-transmit-only can only be set for a wan interface.
                In this case, the cells are not descrambled when received,
                and are scrambled when transmitted."
        ::= { interfaceEntry 13}

interfaceAvailableBandwidth OBJECT-TYPE
        SYNTAX  INTEGER
        ACCESS  read-only
        STATUS  mandatory
        DESCRIPTION
                "The current bandwidth available                     $$$$
                 for the reserved bandwidth connections on this port.
                 In the 8260 agents before v3.0 (v2.0 for the 8285),
                 interfaceAvailableBandwidth is defined as:
                 - for a privateUni or a publicUni port:
                   the current bandwidth available
                   for the reserved bandwidth connections on this port.
                 - for a privateNetwork port: the current bandwidth available
                   on this port.
                 It is in bits per second."
        ::= { interfaceEntry 14}

interfaceAllocatedBandwidth OBJECT-TYPE
        SYNTAX  INTEGER
        ACCESS  read-only
        STATUS  mandatory
        DESCRIPTION
                "The bandwidth, in bits per second, currently used by  $$$$
                 the reserved bandwidth connections on this port.
                 In the 8260 agents before v3.0 (v2.0 for the 8285),
                 interfaceAllocatedBandwidth is defined as:
                 - for a privateUni or a publicUni port: the bandwidth,
                   in bits per second, currently used by the reserved
                   bandwidth connections on this port.
                 - for a privateNetwork port: the bandwidth,
                   in bits per second, currently reserved on this port."
        ::= { interfaceEntry 15}

interfaceMaxBandwidth OBJECT-TYPE
        SYNTAX  INTEGER
        ACCESS  read-write
        STATUS  mandatory
        DESCRIPTION
                "For a privateNetwork port: the maximum bandwidth usable
                 on this port.
                 The interfaceMaxBandwidth must not exceed the
                 physical bandwidth of this port: interfaceMediaSpeed.
                 The minimum valid value to set for the
                 interfaceMaxBandwidth is 60000 bps, which is the
                 bandwidth requested to set a non-reserved bandwidth
                 connection on this ssi link.
                 The interfaceMaxBandwidth must be equal on each side  $$$$
                 of a privateNetwork link to avoid route computation deadlocks.
                 The default value is equal to interfaceMediaSpeed.
                 For a port which is not a privateNetwork port, the maximum
                 bandwidth cannot be changed and remains equal to
                 interfaceMediaSpeed.
                 The interfaceMaxBandwidth is given in bits per second.
                 The interfaceMaxBandwidth can be modified only when the
                 port is disabled.
                 For the 8260 agents prior v3.0 (8285: v2.0),
                 out of interfaceMaxBandwidth: at most 85% are usable for
                 the reserved bandwidth connections and at least 15% are
                 usable for the  non reserved bandwidth connections."
        ::= { interfaceEntry 16}

interfaceFrameFormat OBJECT-TYPE
        SYNTAX  INTEGER {
                     none (1),
                     sonet-sts-3c (2),
                     sdh-stm-1 (3),
                     ds3 (4),
                     e3 (5),
                     e1 (6),
                     t1 (7),
                     sonet-sts-12c (8)
                     }
        ACCESS  read-write
        STATUS  mandatory
        DESCRIPTION
                "The format of the frames exchanged on this port.
                 For a 155 Mbits LAN port, 2 formats are supported:
                 sonet-sts-3c and sdh-stm-1. It can only be
                 modified if the port atm access is UNI or NNI.
                 For the other ports, the frame format cannot be
                 modified and is always returned as none.
                 The frame format can be changed only when the port
                 is disabled."
        ::= { interfaceEntry 17}

-- switch statistics

globalThroughputStats  OBJECT IDENTIFIER ::= { physical 5 }

globalThroughputMonitoring OBJECT-TYPE
        SYNTAX  INTEGER {
                         on (1),
                         off (2)
                        }
        ACCESS  read-write
        STATUS  mandatory
        DESCRIPTION
              "When on, the switch throughput is monitored.
               When off, the switch thoughput is not monitored.
               Note that the monitoring decreases the system
               overall performances."
        ::= { globalThroughputStats 1 }

globalThroughputAggregateOutCells OBJECT-TYPE
              SYNTAX  Counter
              ACCESS  read-only
              STATUS  mandatory
              DESCRIPTION
                      "The total number of cells transmitted from the
                      switch.
                      Note that this value is the aggregate throughput
                      of all the ports on several minutes."
              ::= { globalThroughputStats 2 }

receiveTopList OBJECT-TYPE
        SYNTAX  DisplayString
        ACCESS  read-only
        STATUS  mandatory
        DESCRIPTION
                "The ifindexes of the five most receiving interfaces.
                 The first ifindex given is the one corresponding to
                 the interface which has received the more cells
                 during the last polling interval.
                 All ifIndexes are separated by a blank character.
                 If there are less than 5 interfaces receiving data,
                 there are less than 5 ifindexes listed."
        ::= { globalThroughputStats 3 }

transmitTopList OBJECT-TYPE
        SYNTAX  DisplayString
        ACCESS  read-only
        STATUS  mandatory
        DESCRIPTION
                "The ifindexes of the five most transmitting interfaces.
                 The first ifindex given is the one corresponding to
                 the interface which has sent the more cells
                 during the last polling interval.
                 All ifIndexes are separated by a blank character.
                 If there are less than 5 interfaces transmitting data,
                 there are less than 5 ifindexes listed."
        ::= { globalThroughputStats 4 }

globalMaximumCellThroughput OBJECT-TYPE
              SYNTAX  INTEGER
              ACCESS  read-only
              STATUS  mandatory
              DESCRIPTION
                      "The maximal number of cells that can be transmitted
                      through the switch in one second."
        ::= { globalThroughputStats 5 }


-- ATM optional features

optionalFeatureTable  OBJECT-TYPE
        SYNTAX  SEQUENCE OF OptionalFeatureEntry
        ACCESS  not-accessible
        STATUS  mandatory
        DESCRIPTION
                "This table provides the list of the optional ATM features
                installed in the ATM subsystem."
        ::= { physical 6 }

optionalFeatureEntry OBJECT-TYPE
        SYNTAX  OptionalFeatureEntry
        ACCESS  not-accessible
        STATUS  mandatory
        DESCRIPTION
                "Entries of the optionalFeatureTable."
        INDEX { optionalFeatureSlotIndex,
                optionalFeatureSubslotIndex }
        ::= { optionalFeatureTable 1 }

OptionalFeatureEntry ::= SEQUENCE {
        optionalFeatureSlotIndex
                INTEGER,
        optionalFeatureSubslotIndex
                INTEGER,
        optionalFeatureHardwareVersion
                DisplayString,
        optionalFeatureNumberOfPorts
                INTEGER,
        optionalFeatureDescription
                DisplayString
        }

optionalFeatureSlotIndex OBJECT-TYPE
        SYNTAX  INTEGER (1..64)
        ACCESS  read-only
        STATUS  mandatory
        DESCRIPTION
                "The slot number for this optional feature card."
        ::= { optionalFeatureEntry 1 }

optionalFeatureSubSlotIndex OBJECT-TYPE
        SYNTAX  INTEGER (1..16)
        ACCESS  read-only
        STATUS  mandatory
        DESCRIPTION
                "The sub-slot number for this optional feature card."
        ::= { optionalFeatureEntry 2 }

optionalFeatureHardwareVersion OBJECT-TYPE
        SYNTAX  DisplayString
        ACCESS  read-only
        STATUS  mandatory
        DESCRIPTION
                "The Part Number (P/N) and Engineering Change (EC) level
                 and Plant Location for this optional feature card."
        ::= { optionalFeatureEntry 3 }

optionalFeatureNumberOfPorts OBJECT-TYPE
        SYNTAX  INTEGER
        ACCESS  read-only
        STATUS  mandatory
        DESCRIPTION
                "The number of ports present on this feature card."
        ::= { optionalFeatureEntry 4 }

optionalFeatureDescription OBJECT-TYPE
        SYNTAX  DisplayString (SIZE (0..255))
        ACCESS  read-only
        STATUS  mandatory
        DESCRIPTION
                "A textual description of this optional feature.
                 This description is blank when no description is available."
        ::= { optionalFeatureEntry 5 }


-- ATM extended interfaces configuration
--       supported only by 8260 agents v3 (v2 for 8285) and higher

interfaceLogicalTable  OBJECT-TYPE
        SYNTAX  SEQUENCE OF InterfaceLogicalEntry
        ACCESS  not-accessible
        STATUS  mandatory
        DESCRIPTION
                "For each ATM interface, physical or logical (VP tunnel),
                 this table defines additional
                 configuration parameters."
        ::= { physical 7 }

interfaceLogicalEntry OBJECT-TYPE
        SYNTAX  InterfaceLogicalEntry
        ACCESS  not-accessible
        STATUS  mandatory
        DESCRIPTION
                "Entries of the interfaceLogicalTable.
                 In the current release,
                 there is one entry per privateUni and privateNetwork
                 interface in the atm-subsystem."
        INDEX { ifIndex }
        ::= { interfaceLogicalTable 1 }

InterfaceLogicalEntry ::= SEQUENCE {
        interfaceMaxReservedBandwidth
              INTEGER,
        interfaceControlVpi
              INTEGER,
        interfaceSignallingVci
              INTEGER,
        interfaceRoutingVci
              INTEGER
        }


interfaceMaxReservedBandwidth OBJECT-TYPE
        SYNTAX  INTEGER
        ACCESS  read-write
        STATUS  mandatory
        DESCRIPTION
                "The maximum bandwidth that can be allocated
                 on this port for the reserved bandwidth connections
                 (Constant Bit Rate -CBR-, real time Variable Bit
                 Rate -rtVBR-, non real time Variable Bit Rate -nrtVBR-,
                 Available Bit Rate with Minimum Cell rate -MCR- not
                 null).
                 interfaceMaxReservedBandwidth cannot exceed
                 interfaceMaxBandwidth.
                 The actual reserved bandwidth granted by the signalling
                 layer will not exceed the minimum between
                 interfaceMaxReservedBandwidth and 85% of
                 interfaceMaxBandwidth.
                 If interfaceMaxReservedBandwidth is set equal to
                 interfaceMaxBandwidth, then no UBR and no ABR call
                 can be established.
                 If interfaceMaxReservedBandwidth is set equal to 0,
                 then no reserved bandwidth connection can be
                 established.
                 If interfaceMaxReservedBandwidth is set equal to
                 -1, it means unlimited reserved bandwidth."

        ::= { interfaceLogicalEntry 1 }

interfaceControlVpi OBJECT-TYPE
        SYNTAX  INTEGER
        ACCESS  read-write
        STATUS  mandatory
        DESCRIPTION
                "The vpi of the control channels: ilmi, signalling, routing."

        ::= { interfaceLogicalEntry 2 }

interfaceSignallingVci OBJECT-TYPE
        SYNTAX  INTEGER
        ACCESS  read-write
        STATUS  mandatory
        DESCRIPTION
                "The vci of the signalling channel.For Public Uni or Void
                 ports, this value is always 0."

        ::= { interfaceLogicalEntry 3 }

interfaceRoutingVci OBJECT-TYPE
        SYNTAX  INTEGER
        ACCESS  read-write
        STATUS  mandatory
        DESCRIPTION
                "The vci of the routing channel. For Public Uni or void
                 ports, this value is always 0."

        ::= { interfaceLogicalEntry 4 }


-- Cross-Connect Table

connections  OBJECT IDENTIFIER ::= { node 4 }

-- VCL Cross Connect Table

vcXConnectTable  OBJECT-TYPE
        SYNTAX  SEQUENCE OF VcXConnectEntry
        ACCESS  not-accessible
        STATUS  mandatory
        DESCRIPTION
                "This table contains the cross-connections set-up in
                 the switch for all existing VCL-based PVCs and SVCs."
        ::= { connections 1}

vcXConnectEntry OBJECT-TYPE
        SYNTAX  VcXConnectEntry
        ACCESS  not-accessible
        STATUS  mandatory
        DESCRIPTION
                "Entries of vcXConnectTable."
        INDEX { vcXInIndex ,
                vcXInVpi,
                vcXInVci,
                vcXOutIndex,
                vcXOutVpi,
                vcXOutVci }
        ::= { vcXConnectTable 1 }

VcXConnectEntry ::= SEQUENCE {
        vcXInIndex
                   INTEGER,
        vcXInVpi
                   INTEGER,
        vcXInVci
                   INTEGER,
        vcXOutIndex
                   INTEGER,
        vcXOutVpi
                   INTEGER,
        vcXOutVci
                   INTEGER,
        vcXType
                   INTEGER,
        vcXDirection
                   INTEGER
        }

vcXInIndex OBJECT-TYPE
        SYNTAX  INTEGER
        ACCESS  read-only
        STATUS  mandatory
        DESCRIPTION
                "The interface number for this ATM port."
        ::= { vcXConnectEntry 1 }

vcXInVpi OBJECT-TYPE
        SYNTAX  INTEGER
        ACCESS  read-only
        STATUS  mandatory
        DESCRIPTION
                "The VPI value for this connection."
        ::= { vcXConnectEntry 2 }

vcXInVci OBJECT-TYPE
        SYNTAX  INTEGER
        ACCESS  read-only
        STATUS  mandatory
        DESCRIPTION
                "The VCI value for this connection."
        ::= { vcXConnectEntry 3 }

vcXOutIndex OBJECT-TYPE
        SYNTAX  INTEGER
        ACCESS  read-only
        STATUS  mandatory
        DESCRIPTION
                "The interface number for this ATM port."
        ::= { vcXConnectEntry 4 }

vcXOutVpi OBJECT-TYPE
        SYNTAX  INTEGER
        ACCESS  read-only
        STATUS  mandatory
        DESCRIPTION
                "The VPI value for this connection."
        ::= { vcXConnectEntry 5 }

vcXOutVci OBJECT-TYPE
        SYNTAX  INTEGER
        ACCESS  read-only
        STATUS  mandatory
        DESCRIPTION
                "The VCI value for this connection."
        ::= { vcXConnectEntry 6 }

vcXType   OBJECT-TYPE
        SYNTAX  INTEGER { unicast (1),
                          multicast (2)
                        }
        ACCESS  read-only
        STATUS  mandatory
        DESCRIPTION
                "Whether this cross-connection is part of a unicast or a
                 multicast connection."
        ::= { vcXConnectEntry 7 }

vcXDirection OBJECT-TYPE
        SYNTAX  INTEGER { upstream (1),
                          downstream (2)
                        }
        ACCESS  read-only
        STATUS  mandatory
        DESCRIPTION
                "Whether this entry identifies this cross-connection in
                 the upstream or downstream flow, as seen from the root.

                 Downstream means that the connection was set up from the
                 in parameters (interface, VPI, VCI) to the out parameters
                 (interface, VPI, VCI).

                 In particular, for a multicast SVC, this means that the
                 call initiator (the root in this case) is on the interface
                 side labeled vcXInIndex.

                 Upstream means that the connection was set up from the
                 out parameters (interface, VPI, VCI) to the in parameters
                 (interface, VPI, VCI).

                 As a result, any cross-connection is modeled in this table
                 as two entries, depending on whether it is seen in the
                 up or down stream."
        ::= { vcXConnectEntry 8 }


-- VPL Cross-Connect Table

vpXConnectTable  OBJECT-TYPE
        SYNTAX  SEQUENCE OF VpXConnectEntry
        ACCESS  not-accessible
        STATUS  mandatory
        DESCRIPTION
                "This table contains the cross-connections set-up in
                 the switch for all existing VPL-based PVCs and SVCs."
        ::= { connections 2}

vpXConnectEntry OBJECT-TYPE
        SYNTAX  VpXConnectEntry
        ACCESS  not-accessible
        STATUS  mandatory
        DESCRIPTION
                "Entries of vpXConnectTable."
        INDEX { vpXInIndex ,
                vpXInVpi,
                vpXOutIndex,
                vpXOutVpi}
        ::= { vpXConnectTable 1 }

VpXConnectEntry ::= SEQUENCE {
        vpXInIndex
                   INTEGER,
        vpXInVpi
                   INTEGER,
        vpXOutIndex
                   INTEGER,
        vpXOutVpi
                   INTEGER,
        vpXType
                   INTEGER,
        vpXDirection
                   INTEGER
        }

vpXInIndex OBJECT-TYPE
        SYNTAX  INTEGER
        ACCESS  read-only
        STATUS  mandatory
        DESCRIPTION
                "The interface number for this ATM port."
        ::= { vpXConnectEntry 1 }

vpXInVpi OBJECT-TYPE
        SYNTAX  INTEGER
        ACCESS  read-only
        STATUS  mandatory
        DESCRIPTION
                "The VPI value for this connection."
        ::= { vpXConnectEntry 2 }

vpXOutIndex OBJECT-TYPE
        SYNTAX  INTEGER
        ACCESS  read-only
        STATUS  mandatory
        DESCRIPTION
                "The interface number for this ATM port."
        ::= { vpXConnectEntry 3 }

vpXOutVpi OBJECT-TYPE
        SYNTAX  INTEGER
        ACCESS  read-only
        STATUS  mandatory
        DESCRIPTION
                "The VPI value for this connection."
        ::= { vpXConnectEntry 4 }

vpXType   OBJECT-TYPE
        SYNTAX  INTEGER { unicast (1),
                          multicast (2)
                        }
        ACCESS  read-only
        STATUS  mandatory
        DESCRIPTION
                "Whether this cross-connection is part of a unicast or a
                 multicast connection."
        ::= { vpXConnectEntry 5 }

vpXDirection OBJECT-TYPE
        SYNTAX  INTEGER { upstream (1),
                          downstream (2)
                        }
        ACCESS  read-only
        STATUS  mandatory
        DESCRIPTION
                "Whether this entry identifies this cross-connection in
                 the upstream or downstream flow, as seen from the root.

                 Downstream means that the connection was set up from the
                 in parameters (interface, VPI) to the out parameters
                 (interface, VPI).

                 Upstream means that the connection was set up from the
                 out parameters (interface, VPI) to the in parameters
                 (interface, VPI).

                 As a result, any cross-connection is modeled in this table
                 as two entries, depending on whether it is seen in the
                 up or down stream."
        ::= { vpXConnectEntry 6 }


-- Neighbor Devices

neighbor OBJECT IDENTIFIER ::= { node 5 }

nbrTable  OBJECT-TYPE
        SYNTAX  SEQUENCE OF NbrEntry
        ACCESS  not-accessible
        STATUS  mandatory
        DESCRIPTION
                "This table contains basic characteristics on adjacent
                 ATM devices attached to this switch."
        ::= { neighbor 1}

nbrEntry OBJECT-TYPE
        SYNTAX  NbrEntry
        ACCESS  not-accessible
        STATUS  mandatory
        DESCRIPTION
                "Entries of neighborTable. Each entry corresponds to a port that
                 belongs to an ATM module. This module must be inserted in a slot
                 that is attached to the ATM switch."
        INDEX { nbrIndex }
        ::= { nbrTable 1 }

NbrEntry ::= SEQUENCE {
        localIndex
              INTEGER,
        nbrIpAddress1
              IpAddress,
        nbrIpAddress2
              IpAddress,
        nbrAtmAddress
              AtmAddress,
        nbrIndex
              INTEGER,
        nbrDescriptor
              DisplayString,
        nbrOid
              OBJECT IDENTIFIER,
        nbrName
              DisplayString,
        nbrLocation
              DisplayString,
        trunkId
              INTEGER,
        proxyId
              INTEGER
        }


localIndex OBJECT-TYPE
        SYNTAX  INTEGER
        ACCESS  read-only
        STATUS  mandatory
        DESCRIPTION
                "The interface number for the port represented by this
                 entry."
        ::= { nbrEntry 1 }

nbrIpAddress1 OBJECT-TYPE
        SYNTAX  IpAddress
        ACCESS  read-only
        STATUS  mandatory
        DESCRIPTION
                "One of the IP addresses of the ATM SNMP agent of the node
                 attached to the port/slot defined by this entry.
                 When not available, 0.0.0.0 is returned."
        ::= { nbrEntry 2 }

nbrIpAddress2 OBJECT-TYPE
        SYNTAX  IpAddress
        ACCESS  read-only
        STATUS  deprecated
        DESCRIPTION
                "One of the IP addresses of the ATM SNMP agent of the node
                 attached to the port/slot defined by this entry.
                 When not available, 0.0.0.0 is returned."
        ::= { nbrEntry 3 }

nbrAtmAddress OBJECT-TYPE
        SYNTAX  AtmAddress
        ACCESS  read-only
        STATUS  mandatory
        DESCRIPTION
                "The ATM identification of the node attached to the
                 port/slot defined by this entry.
                 When not available, a null string is returned."
        ::= { nbrEntry 4 }

nbrIndex OBJECT-TYPE
        SYNTAX  INTEGER
        ACCESS  read-only
        STATUS  mandatory
        DESCRIPTION
                "The interface number of the adjacent node to which the
                 connection defined by this entry is attending.
                 When not available, 0 is returned."
        ::= { nbrEntry 5 }

nbrDescriptor OBJECT-TYPE
        SYNTAX  DisplayString (SIZE (0..255))
        ACCESS  read-only
        STATUS  mandatory
        DESCRIPTION
                "The value of the MIB-II sysDescr as reported by the
                 device attached to this port.
                 When not available, a null string is returned."
        ::= { nbrEntry 6 }

nbrOid OBJECT-TYPE
        SYNTAX  OBJECT IDENTIFIER
        ACCESS  read-only
        STATUS  mandatory
        DESCRIPTION
                "The value of the MIB-II sysOID as reported by the
                 device attached to this port.
                 When not available, a null string is returned."
        ::= { nbrEntry 7 }

nbrName OBJECT-TYPE
        SYNTAX  DisplayString (SIZE (0..255))
        ACCESS  read-only
        STATUS  mandatory
        DESCRIPTION
                "The value of the MIB-II sysName as reported by the
                 device attached to this port.
                 When not available, a null string is returned."
        ::= { nbrEntry 8 }

nbrLocation OBJECT-TYPE
        SYNTAX  DisplayString (SIZE (0..255))
        ACCESS  read-only
        STATUS  mandatory
        DESCRIPTION
                "The value of the MIB-II sysLocation as reported by the
                 device attached to this port.
                 When not available, a null string is returned."
        ::= { nbrEntry 9 }

trunkId OBJECT-TYPE
        SYNTAX  INTEGER
        ACCESS  read-only
        STATUS  deprecated
        DESCRIPTION
                "The internal identifier for this trunk.
                 Set to 0 if not a trunk."
        ::= { nbrEntry 10 }

proxyId OBJECT-TYPE
        SYNTAX  INTEGER
        ACCESS  read-only
        STATUS  mandatory
        DESCRIPTION
                "The internal identifier for the proxy agent.
                 it is equal to 0 if there is no proxy management
                 for the attached device."
        ::= { nbrEntry 11 }


-- TFTP

tftp OBJECT IDENTIFIER ::= { node 6 }

transferControl OBJECT-TYPE
        SYNTAX  INTEGER {
                         ready (1),
                         download (2),
                         upload (3)
                        }
        ACCESS  read-write
        STATUS  mandatory
        DESCRIPTION
                "A file transfer is initiated through a start command."
        ::= { tftp 1 }

transferDate OBJECT-TYPE
        SYNTAX  DateAndTime
        ACCESS  read-only
        STATUS  mandatory
        DESCRIPTION
                "The date and time of the last transfer."
        ::= { tftp 2 }

serverIpAddress OBJECT-TYPE
        SYNTAX  IpAddress
        ACCESS  read-write
        STATUS  mandatory
        DESCRIPTION
                "The IP address of the server used for file transfer."
        ::= { tftp 3 }

fileName OBJECT-TYPE
        SYNTAX  DisplayString (SIZE(0..128))
        ACCESS  read-write
        STATUS  mandatory
        DESCRIPTION
                "The name of the file to transfer."
        ::= { tftp 4 }

fileType OBJECT-TYPE
        SYNTAX  INTEGER {
                         unknown (1),
                         bootCode (2),
                         operationalCode (3),
                         errorLog (4),
                         systemTrace (5),
                         trsTrace (6),
-- (7) intentionnally left unused
                         dump (8),
                         configuration (9)
                        }
        ACCESS  read-write
        STATUS  mandatory
        DESCRIPTION
                "The type of file to transfer.
                 Boot and operational codes can only be dowlnoaded.
                 Logs, traces and dumps can only be uploaded. "
        ::= { tftp 5 }

fileTarget OBJECT-TYPE
        SYNTAX  INTEGER
        ACCESS  read-write
        STATUS  mandatory
        DESCRIPTION
                "The module target to which the transfer applies.
                 When set to 0, the transfer applies to the agent itself."
        ::= { tftp 6 }

transferResult OBJECT-TYPE
        SYNTAX  INTEGER { not-initialized (1),
                          transfer-successful (2),
                          upload-in-progress (3),
                          download-in-progress (4),
                          generic-error (5),
                          no-response-from-host (6),
                          connection-lost (7),
                          file-not-found (8),
                          file-empty (9),
                          file-too-big (10),
                          access-rights-violation (11),
                          invalid-file-header (12),
                          checksum-error (13),
                          transfer-error (14),
                          hardware-error (15),
                          file-already-exists(16),
                          config-unreadable-version(17),
                          config-file-empty(18),
                          config-impossible(19),
                          config-internal-error(20),
                          config-applied-ok(21)
                          }
        ACCESS  read-only
        STATUS  mandatory
        DESCRIPTION
                "The result of the latest file transfer.
                 When one of the TFTP variables is modified, this
                 variable is reset to not-initialized.
                 When a configuration file is downloaded, the content of
                 the configuration file is checked. If the file is valid
                 and if a reset is mandatory then the atm subsystem is
                 reset automatically.
                 If the configuration file is not valid or if a reset
                 is not required, the following values are returned in
                 transferResult:
                  - config-unreadable-version: the control point
                        does not support the version of configuration file.
                        This configuration file has probably been built
                        by a further version of control point.
                  - config-file-empty: the configuration file is not valid
                  - config-impossible: the configuration file cannot
                        be applied (internal error, or file corrupted)
                  - config-internal-error: internal error detected while
                        checking the configuration file.
                  - config-applied-ok: the configuration file is valid
                        and a reset is not mandatory."
        ::= { tftp 7 }

-- Service

service OBJECT IDENTIFIER ::= { node 7 }

-- Traces

traces OBJECT IDENTIFIER ::= { service 1 }

traceControl OBJECT-TYPE
        SYNTAX  INTEGER { on (1),
                          off (2),
                          clear (3)
                        }
        ACCESS  read-write
        STATUS  mandatory
        DESCRIPTION

             "The state of the traced functions depends on the
             state of the traceControl object (on,off) defined
             in the ATM_SWITCHING_NODE_MIB for the release V3
             as following :

             When traceControl is set to on, the atm subsystem
             trace facility is started.
             In the atm subsystem release 3, the trace of each
             function in the atm subsystem may be enabled
             or disabled separately by setting the variables
             below functionTracing.
             The trace records are stored in an atm subsystem memory
             file that can be uploaded through TFTP.
             When traceControl is set to off, the trace facility
             is stopped and no function is traced anymore.
             When traceControl is set to clear,the trace records stored
             in the atm subsystem memory are cleared.
             If the traceControl state was ON before the traces clearing
             it will return to the state ON after the traces clearing.
             If the traceControl state was OFF before the traces clearing
             it will return to the state OFF after the traces clearing."
                 ::= { traces 1 }

trsTrace  OBJECT-TYPE
        SYNTAX  INTEGER { on (1),
                          off (2)
                        }
        ACCESS  read-write
        STATUS  mandatory
        DESCRIPTION
                "This variable does not exist anymore in agents release
                 3.0 (8285: agents release 2.0) and further.
                 When on, the Topology and Routing Selection trace is
                 started.
                 Messages are stored in the hub in a file that can be
                 retrieved through TFTP.
                 When off, the control point trace facility is stopped and
                 messages are no longer logged."
        ::= { traces 2 }

-- Function tracing

functionTracing OBJECT IDENTIFIER ::= { traces 3 }

allFunctionsTrace OBJECT-TYPE
        SYNTAX  INTEGER { enabled (1),
                          disabled (2),
                          active (3)
                        }
        ACCESS  read-write
        STATUS  mandatory
        DESCRIPTION
                "When set to enabled, the traces of all atm subsystem functions
                 will be logged provided the variable traceControl is equal
                 to on.
                 When logged, the trace records are stored in
                 an atm subsystem memory file that can be retrieved
                 through TFTP.
                 When set to disabled, the logging of all the traces currently
                 logged is stopped.
                 When read, if it is equal to enabled, then the traces
                 of all the atm subsystem functions are not logged
                 because traceControl is equal to off.
                 When read, if it is equal to disabled, then no trace
                 is logged even if traceControl is equal to on.
                 When read, if it is equal to active, then the
                 traces of all the atm subsystem functions are currently
                 logged."
        ::= { functionTracing 1 }

system OBJECT-TYPE
        SYNTAX  INTEGER { enabled (1),
                          disabled (2),
                          active (3)
                        }
        ACCESS  read-write
        STATUS  mandatory
        DESCRIPTION
                "When set to enabled, the traces of the basic system functions
                 are enabled. The trace records are logged only if the
                 variable traceControl is equal to on.
                 When set to disabled, the traces of the basic system functions
                 are disabled.
                 When logged, the trace records are stored in
                 an atm subsystem memory file that can be retrieved
                 through TFTP.
                 When read, if it is equal to enabled, then the traces of the basic
                 system functions are not logged because traceControl is
                 equal to off.
                 When read, if it is equal to disabled, then no trace of the
                 basic system functions is logged even if traceControl is
                 equal to on.
                 When read, if it is equal to active, then the traces of the
                 basic system functions are currently logged."
        ::= { functionTracing 2 }

lanEmulationClient  OBJECT-TYPE
        SYNTAX  INTEGER { enabled (1),
                          disabled (2),
                          active (3)
                        }
        ACCESS  read-write
        STATUS  mandatory
        DESCRIPTION
                "When set to enabled, the traces of the LEC functions
                 are enabled. The trace records are logged only if the
                 variable traceControl is equal to on.
                 When set to disabled, the traces of the LEC functions
                 are disabled.
                 When logged, the trace records are stored in
                 an atm subsystem memory file that can be retrieved
                 through TFTP.

                 When read, if it is equal to enabled, then the traces of the
                 LEC functions are not logged because traceControl is
                 equal to off.
                 When read, if it is equal to disabled, then no trace of the
                 LEC functions is logged even if traceControl is equal to on.
                 When read, if it is equal to active, then the traces of the
                 LEC functions are currently logged."
        ::= { functionTracing 3 }

lanEmulationServers  OBJECT-TYPE
        SYNTAX  INTEGER { enabled (1),
                          disabled (2),
                          active (3)
                        }
        ACCESS  read-write
        STATUS  mandatory
        DESCRIPTION
                "When set to enabled, the traces of the LES functions
                 are enabled. The trace records are logged only if the
                 variable traceControl is equal to on.
                 When set to disabled, the traces of the LES functions
                 are disabled.
                 When logged, the trace records are stored in
                 an atm subsystem memory file that can be retrieved
                 through TFTP.
                 When read, if it is equal to enabled, then the traces of the
                 LES functions are not logged because traceControl is
                 equal to off.
                 When read, if it is equal to disabled, then no trace of the
                 LES functions is logged even if traceControl is equal to on.
                 When read, if it is equal to active, then the traces of the
                 LES functions are currently logged."
        ::= { functionTracing 4 }

broadcastAndUnknownServer  OBJECT-TYPE
        SYNTAX  INTEGER { enabled (1),
                          disabled (2),
                          active (3)
                        }
        ACCESS  read-write
        STATUS  mandatory
        DESCRIPTION
                "When set to enabled, the traces of the BUS functions
                 are enabled. The trace records are logged only if the
                 variable traceControl is equal to on.
                 When set to disabled, the traces of the BUS functions
                 are disabled.
                 When logged, the trace records are stored in
                 an atm subsystem memory file that can be retrieved
                 through TFTP.
                 When read, if it is equal to enabled, then the traces of the
                 BUS functions are not logged because traceControl is
                 equal to off.
                 When read, if it is equal to disabled, then no trace of the
                 BUS functions is logged even if traceControl is equal to on.
                 When read, if it is equal to active, then the traces of the
                 BUS functions are currently logged."
        ::= { functionTracing 5 }

pnniHello  OBJECT-TYPE
        SYNTAX  INTEGER { enabled (1),
                          disabled (2),
                          active (3)
                        }
        ACCESS  read-write
        STATUS  mandatory
        DESCRIPTION
                "When set to enabled, the traces of the pNNI hello protocol
                 are enabled.
                 The trace records are logged only if the
                 variable traceControl is equal to on.
                 When set to disabled, the traces of the pNNI hello protocol
                 are disabled.
                 When logged, the trace records are stored in
                 an atm subsystem memory file that can be retrieved
                 through TFTP.
                 When read, if it is equal to enabled, then the traces of the
                 PNNI hello protocol are not logged because traceControl is
                 equal to off.
                 When read, if it is equal to disabled, then no trace of the
                 PNNI hello protocol is logged even if traceControl is equal to on.
                 When read, if it is equal to active, then the traces of the
                 PNNI hello protocol are currently logged."
        ::= { functionTracing 6 }

pnniNeighbor  OBJECT-TYPE
        SYNTAX  INTEGER { enabled (1),
                          disabled (2),
                          active (3)
                        }
        ACCESS  read-write
        STATUS  mandatory
        DESCRIPTION
                "When set to enabled, the traces of the pNNI neighbor protocol
                 are enabled. The trace records are logged only if the
                 variable traceControl is equal to on.
                 When set to disabled, the traces of the pNNI neighbor protocol
                 are disabled.
                 When logged, the trace records are stored in
                 an atm subsystem memory file that can be retrieved
                 through TFTP.
                 When read, if it is equal to enabled, then the traces of the
                 PNNI neighbor protocol are not logged because traceControl is
                 equal to off.
                 When read, if it is equal to disabled, then no trace of the
                 PNNI neighbor protocol is logged even if traceControl is equal to on.
                 When read, if it is equal to active, then the traces of the
                 PNNI neighbor protocol are currently logged."
        ::= { functionTracing 7 }

pnniPathSelection OBJECT-TYPE
        SYNTAX  INTEGER { enabled (1),
                          disabled (2),
                          active (3)
                        }
        ACCESS  read-write
        STATUS  mandatory
        DESCRIPTION
                "When set to enabled, the traces of the pNNI path selection functions
                 are enabled. The trace records are logged only if the
                 variable traceControl is equal to on.
                 When set to disabled, the traces of the pNNI path selection functions
                 are disabled.
                 When logged, the trace records are stored in
                 an atm subsystem memory file that can be retrieved
                 through TFTP.
                 When read, if it is equal to enabled, then the traces of the
                 PNNI path selection functions are not logged because traceControl is
                 equal to off.
                 When read, if it is equal to disabled, then no trace of the
                 PNNI path selection functions is logged even if traceControl is equal to on.
                 When read, if it is equal to active, then the traces of the
                 PNNI path selection functions are currently logged."
        ::= { functionTracing 8 }

pnniBase OBJECT-TYPE
        SYNTAX  INTEGER { enabled (1),
                          disabled (2),
                          active (3)
                        }
        ACCESS  read-write
        STATUS  mandatory
        DESCRIPTION
                "When set to enabled, the traces of the pNNI basic functions
                 are enabled. The trace records are logged only if the
                 variable traceControl is equal to on.
                 When set to disabled, the traces of the pNNI basic functions
                 are disabled.
                 When logged, the trace records are stored in
                 an atm subsystem memory file that can be retrieved
                 through TFTP.
                 When read, if it is equal to enabled, then the traces of the
                 PNNI basic functions are not logged because traceControl is
                 equal to off.
                 When read, if it is equal to disabled, then no trace of the
                 PNNI basic functions is logged even if traceControl is equal to on.
                 When read, if it is equal to active, then the traces of the
                 PNNI basic functions are currently logged."
        ::= { functionTracing 9 }

signalling  OBJECT-TYPE
        SYNTAX  INTEGER { enabled (1),
                          disabled (2),
                          active (3)
                        }
        ACCESS  read-write
        STATUS  mandatory
        DESCRIPTION
                "When set to enabled, the traces of the signalling protocol
                 are enabled. The trace records are logged only if the
                 variable traceControl is equal to on.
                 When set to disabled, the traces of the signalling protocol
                 are disabled.
                 When logged, the trace records are stored in
                 an atm subsystem memory file that can be retrieved
                 through TFTP.
                 When read, if it is equal to enabled, then the traces of the
                 signalling protocol are not logged because traceControl is
                 equal to off.
                 When read, if it is equal to disabled, then no trace of the
                 signalling protocol is logged even if traceControl is equal to on.
                 When read, if it is equal to active, then the traces of the
                 signalling protocol are currently logged."
        ::= { functionTracing 10 }

saal  OBJECT-TYPE
        SYNTAX  INTEGER { enabled (1),
                          disabled (2),
                          active (3)
                        }
        ACCESS  read-write
        STATUS  mandatory
        DESCRIPTION
                "When set to enabled, the traces of the SAAL protocol
                 are enabled. The trace records are logged only if the
                 variable traceControl is equal to on.
                 When set to disabled, the traces of the SAAL protocol
                 are disabled.
                 When logged, the trace records are stored in
                 an atm subsystem memory file that can be retrieved
                 through TFTP.
                 When read, if it is equal to enabled, then the traces of the
                 SAAL protocol are not logged because traceControl is
                 equal to off.
                 When read, if it is equal to disabled, then no trace of the
                 SAAL protocol is logged even if traceControl is equal to on.
                 When read, if it is equal to active, then the traces of the
                 SAAL protocol are currently logged."
        ::= { functionTracing 11 }

classicalIp  OBJECT-TYPE
        SYNTAX  INTEGER { enabled (1),
                          disabled (2),
                          active (3)
                        }
        ACCESS  read-write
        STATUS  mandatory
        DESCRIPTION
                "When set to enabled, the traces of the classical IP over ATM protocol
                 are enabled. The trace records are logged only if the
                 variable traceControl is equal to on.
                 When set to disabled, the traces of the classical IP over ATM protocol
                 are disabled.
                 When logged, the trace records are stored in
                 an atm subsystem memory file that can be retrieved
                 through TFTP.
                 When read, if it is equal to enabled, then the traces of the
                 classical IP over ATM protocol are not logged because traceControl is
                 equal to off.
                 When read, if it is equal to disabled, then no trace of the
                 classical IP over ATM protocol is logged even if traceControl is equal to on.
                 When read, if it is equal to active, then the traces of the
                 classical IP over ATM protocol are currently logged."
        ::= { functionTracing 12 }

pvc  OBJECT-TYPE
        SYNTAX  INTEGER { enabled (1),
                          disabled (2),
                          active (3)
                        }
        ACCESS  read-write
        STATUS  mandatory
        DESCRIPTION
                "When set to enabled, the traces of the PVC functions
                 are enabled. The trace records are logged only if the
                 variable traceControl is equal to on.
                 When set to disabled, the traces of the PVC functions
                 are disabled.
                 When logged, the trace records are stored in
                 an atm subsystem memory file that can be retrieved
                 through TFTP.
                 When read, if it is equal to enabled, then the traces of the
                 PVC functions are not logged because traceControl is
                 equal to off.
                 When read, if it is equal to disabled, then no trace of the
                 PVC functions is logged even if traceControl is equal to on.
                 When read, if it is equal to active, then the traces of the
                 PVC functions are currently logged."
        ::= { functionTracing 13 }

ilmi OBJECT-TYPE
        SYNTAX  INTEGER { enabled (1),
                          disabled (2),
                          active (3)
                        }
        ACCESS  read-write
        STATUS  mandatory
        DESCRIPTION
                "When set to enabled, the traces of the ILMI protocol
                 are enabled. The trace records are logged only if the
                 variable traceControl is equal to on.
                 When set to disabled, the traces of the ILMI protocol
                 are disabled.
                 When logged, the trace records are stored in
                 an atm subsystem memory file that can be retrieved
                 through TFTP.
                 When read, if it is equal to enabled, then the traces of the
                 ILMI protocol are not logged because traceControl is
                 equal to off.
                 When read, if it is equal to disabled, then no trace of the
                 ILMI protocol is logged even if traceControl is equal to on.
                 When read, if it is equal to active, then the traces of the
                 ILMI protocol are currently logged."
        ::= { functionTracing 14 }

snmp OBJECT-TYPE
        SYNTAX  INTEGER { enabled (1),
                          disabled (2),
                          active (3)
                        }
        ACCESS  read-write
        STATUS  mandatory
        DESCRIPTION
                "When set to enabled, the traces of the SNMP protocol
                 are enabled. The trace records are logged only if the
                 variable traceControl is equal to on.
                 When set to disabled, the traces of the SNMP protocol
                 are disabled.
                 When logged, the trace records are stored in
                 an atm subsystem memory file that can be retrieved
                 through TFTP.
                 When read, if it is equal to enabled, then the traces of the
                 SNMP protocol are not logged because traceControl is
                 equal to off.
                 When read, if it is equal to disabled, then no trace of the
                 SNMP protocol is logged even if traceControl is equal to on.
                 When read, if it is equal to active, then the traces of the
                 SNMP protocol are currently logged."
        ::= { functionTracing 15 }

-- Dumps

dumps OBJECT IDENTIFIER ::= { service 2 }

-- dumps.1 intentionnally left unused

trsDump  OBJECT-TYPE
        SYNTAX  INTEGER { ready (1),
                          start (2)
                        }
        ACCESS  read-write
        STATUS  mandatory
        DESCRIPTION
                "When start is selected, a dump of the Topology and Route
                 Services component is taken.
                 The dump is stored in the hub in a file that can be
                 retrieved through TFTP.
                 The variable trsDump is not supported by the agents
                 8260 release 3 (release 2 for the 8285) and further.
                "
        ::= { dumps 2 }

-- pnni Dump

pnniDump OBJECT IDENTIFIER ::= { dumps 3 }

pnniDumpControl OBJECT-TYPE
        SYNTAX  INTEGER {
                         ready (1),
                         dump-protocol (2),
                         dump-peer-to-peer-leader (3),
                         dump-topology (4),
                         dump-ptse (5),
                         dump-path-selection (6)
                        }
        ACCESS  read-write
        STATUS  mandatory
        DESCRIPTION
                 "When pnniDumpControl is set to dump-X the dump of
                 category X is taken and stored in ram. To
                 upload the dump information, refer to the tftp group."
        ::= { pnniDump 1 }

pnniDumpPtse OBJECT-TYPE
        SYNTAX  INTEGER
        ACCESS  read-write
        STATUS  mandatory
        DESCRIPTION
                 "The value of Ptse to be dumped.
                  When read, -1 means that no value has been set
                  (and therefore the dump is not possible)."
        ::= { pnniDump 2 }


-- Microcode swap

swap OBJECT IDENTIFIER ::= { service 3 }

swapControl OBJECT-TYPE
        SYNTAX  INTEGER { ready (1),
                          swap (2)
                        }
        ACCESS  read-write
        STATUS  mandatory
        DESCRIPTION
                "When swap is selected, the backup microcode image is
                 checked and, if valid, activated.
                 The previously active microcode image becomes
                 the backup image.
                 The atm subsystem is reset."
        ::= { swap 1 }


swapResult OBJECT-TYPE
        SYNTAX  INTEGER { not-initialized (1),
                          swap-successful (2),
                          swap-in-progress (3),
                          checksum-error (4) }
        ACCESS  read-only
        STATUS  mandatory
        DESCRIPTION
                "The result of the latest microcode swap.
                 When an operational code image is downloaded or
                 when the system is reset, swapControl becomes
                 not-initialized."
        ::= { swap 2 }


swapBackupVersion OBJECT-TYPE
        SYNTAX  DisplayString
        ACCESS  read-only
        STATUS  mandatory
        DESCRIPTION
                "The version and release number for the backup
                 firmware (microcode) saved in flash memory."
        ::= { swap 3 }


-- configuration save/revert

configuration OBJECT IDENTIFIER ::= { service 4 }

configurationControl OBJECT-TYPE
        SYNTAX  INTEGER {
                         ready (1),
                         save (2)
                        }
        ACCESS  read-write
        STATUS  mandatory
        DESCRIPTION
                "When set to save (2), the current configuration of the atm subsystem
                 is saved in non volatile memory.
                 This configuration will be restored at the next reset of the atm sub-system.
                 It may be useful before an upload of the configuration file is performed,
                 to save the current configuration (cf tftp group).
                 When a reset is performed, the last configuration saved in non volatile
                 memory is restored and not necessarily the current config at the
                 time of the reset."
        ::= { configuration 1 }


-- This MIB defines ATM signalling support, i.e. Q2931 and SAAL support
-- for SVCs.

atmSvc OBJECT IDENTIFIER ::= { node 9 }

-- This group defines support for the Q2931 protocol

atmQ2931 OBJECT IDENTIFIER ::= { atmSvc 1 }

-- This table defines the Q2931 configuration and status.

atmQ2931ConfTable  OBJECT-TYPE
        SYNTAX  SEQUENCE OF AtmQ2931ConfEntry
        ACCESS  not-accessible
        STATUS  mandatory
        DESCRIPTION
                "This table contains basic information on the Q2931 protocol
                 for each signalling link defined per port.
                 Usually, there is only one signalling channel per interface
                 and thus one Q2931 protocol definition entry per interface."
        ::= { atmQ2931 1}

atmQ2931ConfEntry OBJECT-TYPE
        SYNTAX  AtmQ2931ConfEntry
        ACCESS  not-accessible
        STATUS  mandatory
        DESCRIPTION
                "Entries of atmQ2931ConfTable. Each entry corresponds to a pair
                 of ATM interface, signalling channel.
                 A signalling channel is uniquely defined on each interface
                 by the VPI and VCI values allocated to it."
        INDEX { atmQ2931ConfIndex,
                atmQ2931SiVpi,
                atmQ2931SiVci }
        ::= { atmQ2931ConfTable 1 }

AtmQ2931ConfEntry ::= SEQUENCE {
        atmQ2931ConfIndex
                INTEGER,
        atmQ2931SiVpi
                INTEGER,
        atmQ2931SiVci
                INTEGER,
        atmQ2931T303
                INTEGER,
        atmQ2931T308
                INTEGER,
        atmQ2931T309
                INTEGER,
        atmQ2931T310
                INTEGER,
        atmQ2931T316
                INTEGER,
        atmQ2931T317
                INTEGER,
        atmQ2931T322
                INTEGER,
        atmQ2931T398
                INTEGER,
        atmQ2931T399
                INTEGER,
        atmQ2931SetupRetry
                INTEGER,
        atmQ2931ReleaseRetry
                INTEGER,
        atmQ2931RestartRetry
                INTEGER,
        atmQ2931StatusRetry
                INTEGER }

atmQ2931ConfIndex OBJECT-TYPE
        SYNTAX  INTEGER
        ACCESS  read-only
        STATUS  mandatory
        DESCRIPTION
                "The ifIndex value of the ATM interface which, with the
                 signalling channel defined by its Vpi/Vci values,
                 uniquely identifies this entry."
        ::= { atmQ2931ConfEntry 1 }

atmQ2931SiVpi OBJECT-TYPE
        SYNTAX  INTEGER
        ACCESS  read-only
        STATUS  mandatory
        DESCRIPTION
                "The Vpi value which, with the Vci value specified in
                 atmQ2931SiVci, defines the signalling channel for this
                 entry.
                 Usually, there is one signalling channel per interface
                 defined by Vpi=0,Vci=5."
        ::= { atmQ2931ConfEntry 2 }

atmQ2931SiVci OBJECT-TYPE
        SYNTAX  INTEGER
        ACCESS  read-only
        STATUS  mandatory
        DESCRIPTION
                "The Vci value which, with the Vpi value specified in
                 atmQ2931SiVpi, defines the signalling channel for this
                 entry.
                 Usually, there is one signalling channel per interface
                 defined by Vpi=0,Vci=5."
        ::= { atmQ2931ConfEntry 3 }

atmQ2931T303 OBJECT-TYPE
        SYNTAX  INTEGER
        ACCESS  read-only
        STATUS  mandatory
        DESCRIPTION
                "T303 timer as defined in the ATM UNI Specification."
        ::= { atmQ2931ConfEntry 4 }

atmQ2931T308 OBJECT-TYPE
        SYNTAX  INTEGER
        ACCESS  read-only
        STATUS  mandatory
        DESCRIPTION
                "T308 timer as defined in the ATM UNI Specification."
        ::= { atmQ2931ConfEntry 5 }

atmQ2931T309 OBJECT-TYPE
        SYNTAX  INTEGER
        ACCESS  read-only
        STATUS  mandatory
        DESCRIPTION
                "T309 timer as defined in the ATM UNI Specification."
        ::= { atmQ2931ConfEntry 6 }

atmQ2931T310 OBJECT-TYPE
        SYNTAX  INTEGER
        ACCESS  read-only
        STATUS  mandatory
        DESCRIPTION
                "T310 timer as defined in the ATM UNI Specification."
        ::= { atmQ2931ConfEntry 7 }

atmQ2931T316 OBJECT-TYPE
        SYNTAX  INTEGER
        ACCESS  read-only
        STATUS  mandatory
        DESCRIPTION
                "T316 timer as defined in the ATM UNI Specification."
        ::= { atmQ2931ConfEntry 8 }

atmQ2931T317 OBJECT-TYPE
        SYNTAX  INTEGER
        ACCESS  read-only
        STATUS  mandatory
        DESCRIPTION
                "T317 timer as defined in the ATM UNI Specification."
        ::= { atmQ2931ConfEntry 9 }

atmQ2931T322 OBJECT-TYPE
        SYNTAX  INTEGER
        ACCESS  read-only
        STATUS  mandatory
        DESCRIPTION
                "T322 timer as defined in the ATM UNI Specification."
        ::= { atmQ2931ConfEntry 10}

atmQ2931T398 OBJECT-TYPE
        SYNTAX  INTEGER
        ACCESS  read-only
        STATUS  mandatory
        DESCRIPTION
                "T398 timer as defined in the ATM UNI Specification."
        ::= { atmQ2931ConfEntry 11 }

atmQ2931T399 OBJECT-TYPE
        SYNTAX  INTEGER
        ACCESS  read-only
        STATUS  mandatory
        DESCRIPTION
                "T399 timer as defined in the ATM UNI Specification."
        ::= { atmQ2931ConfEntry 12 }

atmQ2931SetupRetry OBJECT-TYPE
        SYNTAX  INTEGER
        ACCESS  read-only
        STATUS  mandatory
        DESCRIPTION
                "Number of set-up retries as defined in the ATM UNI
                Specification."
        ::= { atmQ2931ConfEntry 13 }

atmQ2931ReleaseRetry OBJECT-TYPE
        SYNTAX  INTEGER
        ACCESS  read-only
        STATUS  mandatory
        DESCRIPTION
                "Number of release retries as defined in the ATM UNI
                Specification."
        ::= { atmQ2931ConfEntry 14 }

atmQ2931RestartRetry OBJECT-TYPE
        SYNTAX  INTEGER
        ACCESS  read-only
        STATUS  mandatory
        DESCRIPTION
                "Number of restart retries as defined in the ATM UNI
                Specification."
        ::= { atmQ2931ConfEntry 15 }

atmQ2931StatusRetry OBJECT-TYPE
        SYNTAX  INTEGER
        ACCESS  read-only
        STATUS  mandatory
        DESCRIPTION
                "Number of status retries as defined in the ATM UNI
                Specification."
        ::= { atmQ2931ConfEntry 16 }

-- This table defines the Q2931 statistics.

atmQ2931StatsTable  OBJECT-TYPE
        SYNTAX  SEQUENCE OF AtmQ2931StatsEntry
        ACCESS  not-accessible
        STATUS  mandatory
        DESCRIPTION
                "This table contains statistics for the Q2931 protocol."
        ::= { atmQ2931 2 }

atmQ2931StatsEntry OBJECT-TYPE
        SYNTAX  AtmQ2931StatsEntry
        ACCESS  not-accessible
        STATUS  mandatory
        DESCRIPTION
                "Entries of atmQ2931ConfTable. Each entry corresponds to a pair
                 of ATM interface, signalling channel.
                 A signalling channel is uniquely defined on each interface
                 by the VPI and VCI values allocated to it."
        INDEX { atmQ2931StatsIndex,
                atmQ2931StatsVpi,
                atmQ2931StatsVci }
        ::= { atmQ2931StatsTable 1 }

AtmQ2931StatsEntry ::= SEQUENCE {
        atmQ2931StatsIndex
                INTEGER,
        atmQ2931StatsVpi
                INTEGER,
        atmQ2931StatsVci
                INTEGER,
        atmQ2931OutCallAttempts
                Counter,
        atmQ2931OutCallInProgress
                Gauge,
        atmQ2931OutCallFailures
                Counter,
        atmQ2931InCallAttempts
                Counter,
        atmQ2931InCallInProgress
                Gauge,
        atmQ2931InCallFailures
                Counter }

atmQ2931StatsIndex OBJECT-TYPE
        SYNTAX  INTEGER
        ACCESS  read-only
        STATUS  mandatory
        DESCRIPTION
                "The ifIndex value of the ATM interface which, with the
                 signalling channel defined by its Vpi/Vci values,
                 uniquely identifies this entry."
        ::= { atmQ2931StatsEntry 1 }

atmQ2931StatsVpi OBJECT-TYPE
        SYNTAX  INTEGER
        ACCESS  read-only
        STATUS  mandatory
        DESCRIPTION
                "The Vpi value which, with the Vci value specified in
                 atmQ2931StatsVci, defines the signalling channel for this
                 entry.
                 Usually, there is one signalling channel per interface
                 defined by Vpi=0,Vci=5."
        ::= { atmQ2931StatsEntry 2 }

atmQ2931StatsVci OBJECT-TYPE
        SYNTAX  INTEGER
        ACCESS  read-only
        STATUS  mandatory
        DESCRIPTION
                "The Vci value which, with the Vpi value specified in
                 atmQ2931StatsVpi, defines the signalling channel for this
                 entry.
                 Usually, there is one signalling channel per interface
                 defined by Vpi=0,Vci=5."
        ::= { atmQ2931StatsEntry 3 }

atmQ2931OutCallAttempts OBJECT-TYPE
        SYNTAX  Counter
        ACCESS  read-only
        STATUS  mandatory
        DESCRIPTION
                "This is the number of outgoing call attempts on this
                 interface, including accepted as well as rejected calls."
        ::= { atmQ2931StatsEntry 4 }

atmQ2931OutCallInProgress OBJECT-TYPE
        SYNTAX  Gauge
        ACCESS  read-only
        STATUS  mandatory
        DESCRIPTION
                "This is the current number of outgoing calls in progress
                 on this interface."
        ::= { atmQ2931StatsEntry 5 }

atmQ2931OutCallFailures OBJECT-TYPE
        SYNTAX  Counter
        ACCESS  read-only
        STATUS  mandatory
        DESCRIPTION
                "This is the number of outgoing calls that were cleared
                 for a reason other than a DTE or operator initiated action."
        ::= { atmQ2931StatsEntry 6 }

atmQ2931InCallAttempts  OBJECT-TYPE
        SYNTAX  Counter
        ACCESS  read-only
        STATUS  mandatory
        DESCRIPTION
                "This is the number of incoming call attempts on this
                 interface, including accepted as well as rejected calls."
        ::= { atmQ2931StatsEntry 7 }

atmQ2931InCallInProgress OBJECT-TYPE
        SYNTAX  Gauge
        ACCESS  read-only
        STATUS  mandatory
        DESCRIPTION
                "This is the current number of incoming calls in progress
                 on this interface."
        ::= { atmQ2931StatsEntry 8 }

atmQ2931InCallFailures   OBJECT-TYPE
        SYNTAX  Counter
        ACCESS  read-only
        STATUS  mandatory
        DESCRIPTION
                "This is the number of calls that were rejected by the
                 receiver."
        ::= { atmQ2931StatsEntry 9 }

-- This table contains basic information about calls in progress.
-- It allows the network operater to force clear an SVC.
-- Its implementation is optional.

atmSvcTable  OBJECT-TYPE
        SYNTAX  SEQUENCE OF AtmSvcEntry
        ACCESS  not-accessible
        STATUS  mandatory
        DESCRIPTION
                "This table contains basic information for each active
                 Switched Virtual Connection (SVC)."
        ::= { atmQ2931 3 }

atmSvcEntry OBJECT-TYPE
        SYNTAX  AtmSvcEntry
        ACCESS  not-accessible
        STATUS  mandatory
        DESCRIPTION
                "Entries of atmSvcTable. Each entry uniquely
                 defines two end-points of an SVC. In the case of a
                 multicast SVC, each entry is defined by the
                 association of the root and one party."
        INDEX { atmSvcInterfaceIndex,
                atmSvcSiVpi,
                atmSvcSiVci,
                atmSvcCallReference,
                atmSvcEndPointReference }
        ::= { atmSvcTable 1 }

AtmSvcEntry ::= SEQUENCE {
        atmSvcInterfaceIndex
                INTEGER,
        atmSvcSiVpi
                INTEGER,
        atmSvcSiVci
                INTEGER,
        atmSvcCallReference
                INTEGER,
        atmSvcEndPointReference
                INTEGER,
        atmSvcCallingNumber
                AtmAddress,
        atmSvcCalledNumber
                AtmAddress,
        atmSvcClear
                INTEGER,
        atmSvcCreationTime
                DateAndTime,
        atmSvcVpi
                INTEGER,
         atmSvcVci
                INTEGER }

atmSvcInterfaceIndex OBJECT-TYPE
        SYNTAX  INTEGER
        ACCESS  read-only
        STATUS  mandatory
        DESCRIPTION
                "The ifIndex value of the ATM interface used by this
                 SVC."
        ::= { atmSvcEntry 1 }

atmSvcSiVpi OBJECT-TYPE
        SYNTAX  INTEGER
        ACCESS  read-only
        STATUS  mandatory
        DESCRIPTION
                "The Vpi value which, with the Vci value specified in
                 atmSvcSiVci, defines the signalling channel for this
                 entry.
                 Usually, there is one signalling channel per interface
                 defined by Vpi=0,Vci=5."
        ::= { atmSvcEntry 2 }

atmSvcSiVci OBJECT-TYPE
        SYNTAX  INTEGER
        ACCESS  read-only
        STATUS  mandatory
        DESCRIPTION
                "The Vci value which, with the Vpi value specified in
                 atmSvcSiVpi, defines the signalling channel for this
                 entry.
                 Usually, there is one signalling channel per interface
                 defined by Vpi=0,Vci=5."
        ::= { atmSvcEntry 3 }

atmSvcCallReference OBJECT-TYPE
        SYNTAX  INTEGER (0..8388607)
        ACCESS  read-only
        STATUS  mandatory
        DESCRIPTION
                "The Q2931 call reference value used for this SVC."
        ::= { atmSvcEntry 4 }

atmSvcEndPointReference OBJECT-TYPE
        SYNTAX  INTEGER (0..16383)
        ACCESS  read-only
        STATUS  mandatory
        DESCRIPTION
                "One of the Q2931 end point reference values used by this
                 SVC.
                 In a unicast SVC, there is only one entry for this SVC in
                 the table.
                 In a multicast SVC, there is one entry per party."

        ::= { atmSvcEntry 5 }

atmSvcCallingNumber OBJECT-TYPE
        SYNTAX  AtmAddress
        ACCESS  read-only
        STATUS  mandatory
        DESCRIPTION
                "The calling number carried in the calling party number
                 information element of the call set-up message."
        ::= { atmSvcEntry 6 }

atmSvcCalledNumber OBJECT-TYPE
        SYNTAX  AtmAddress
        ACCESS  read-only
        STATUS  mandatory
        DESCRIPTION
                "The called number carried in the called party number
                 information element of the call set-up message."
        ::= { atmSvcEntry 7 }


atmSvcClear OBJECT-TYPE
        SYNTAX  INTEGER {
                         active (1),
                         clear (2)
                        }
        ACCESS  read-write
        STATUS  mandatory
        DESCRIPTION
                "This variable allows a network manager to clear this
                 SVC.
                 When this SVC is cleared (either by the manager using
                 this variable or by one of the parties), the entry is
                 deleted from this table and another entry is created
                 in the atmSvcClearTable."
        ::= { atmSvcEntry 8}

atmSvcCreationTime OBJECT-TYPE
        SYNTAX  DateAndTime
        ACCESS  read-only
        STATUS  mandatory
        DESCRIPTION
                "The date and time this call was placed."
        ::= { atmSvcEntry 9 }

atmSvcVpi   OBJECT-TYPE
        SYNTAX  INTEGER (0..255)
        ACCESS  read-only
        STATUS  mandatory
        DESCRIPTION
                "The VPI value used by this SVC for this interface."
        ::= { atmSvcEntry 10}

atmSvcVci   OBJECT-TYPE
        SYNTAX  INTEGER (0..65535)
        ACCESS  read-only
        STATUS  mandatory
        DESCRIPTION
                "The VCI value used by this SVC for this interface."
        ::= { atmSvcEntry 11}

-- This table keeps track of all SVCs that have been cleared.
-- It allows to build traffic mattrix and provide more in-depth.
-- statistics level on the use of the network.
-- It is optional.

atmSvcLogSize OBJECT-TYPE
        SYNTAX  INTEGER
        ACCESS  read-only
        STATUS  mandatory
        DESCRIPTION
                "The maximum number of entries supported by this local
                 SNMP agent.
                 When this value is exceeded, the entries are wrapped."
        ::= { atmQ2931 4 }

atmSvcLogLevel OBJECT-TYPE
        SYNTAX  INTEGER
        ACCESS  read-write
        STATUS  mandatory
        DESCRIPTION
                "The maximum number of entries that can be written in the
                 atmSvcLogTable before a trap is generated.
                 When this number is reached, an svcLogOverflow trap is
                 generated.
                 When set to 0, no trap is generated."
        ::= { atmQ2931 5 }

atmSvcLogTable  OBJECT-TYPE
        SYNTAX  SEQUENCE OF AtmSvcLogEntry
        ACCESS  not-accessible
        STATUS  mandatory
        DESCRIPTION
                "This table contains a list of the latest Switched
                 Virtual Connection (SVC) that were completed on this
                 ATM node.
                 An SVC is completed when it has been torn down at the
                 originator's request (normal completion) or by the
                 network operator (forced tear down), or when it has
                 been rejected or cleared by the network (exceptional
                 condition)."
        ::= { atmQ2931 6 }

atmSvcLogEntry OBJECT-TYPE
        SYNTAX  AtmSvcLogEntry
        ACCESS  not-accessible
        STATUS  mandatory
        DESCRIPTION
                "Entries of atmSvcLogTable."
        INDEX { atmSvcLogIndex }
        ::= { atmSvcLogTable 1 }

AtmSvcLogEntry ::= SEQUENCE {
        atmSvcLogIndex
                INTEGER,
        atmSvcLogInterfaceIndex
                INTEGER,
        atmSvcLogCallingNumber
                AtmAddress,
        atmSvcLogCalledNumber
                AtmAddress,
        atmSvcLogCreationTime
                DateAndTime,
        atmSvcLogTime
                DateAndTime,
        atmSvcLogClearCause
                INTEGER,
        atmSvcLogForwardQOS
                INTEGER,
        atmSvcLogBackwardQOS
                INTEGER,
        atmSvcLogForwardBW
                INTEGER,
        atmSvcLogBackwardBW
                INTEGER,
        atmSvcLogServiceCategory
                INTEGER,
        atmSvcLogClearCauseLocation
                INTEGER }

atmSvcLogIndex OBJECT-TYPE
        SYNTAX  INTEGER
        ACCESS  read-only
        STATUS  mandatory
        DESCRIPTION
                "An identification value for this entry, assigned by the
                 local SNMP agent.
                 This value is assigned for each new SVC call or
                 add-party request.
                 This index is allocated in a decreasing order, so that
                 a get-next request on the table allows to retrieve the
                 latest calls first."
        ::= { atmSvcLogEntry 1 }

atmSvcLogInterfaceIndex OBJECT-TYPE
        SYNTAX  INTEGER
        ACCESS  read-only
        STATUS  mandatory
        DESCRIPTION
                "The ifIndex value of the ATM interface used by this
                 SVC."
        ::= { atmSvcLogEntry 2 }

atmSvcLogCallingNumber OBJECT-TYPE
        SYNTAX  AtmAddress
        ACCESS  read-only
        STATUS  mandatory
        DESCRIPTION
                "The calling number carried in the calling party number
                 information element of the call set-up message."
        ::= { atmSvcLogEntry 3 }

atmSvcLogCalledNumber OBJECT-TYPE
        SYNTAX  AtmAddress
        ACCESS  read-only
        STATUS  mandatory
        DESCRIPTION
                "The called number carried in the called party number
                 information element of the call set-up message."
        ::= { atmSvcLogEntry 4 }

atmSvcLogCreationTime OBJECT-TYPE
        SYNTAX  DateAndTime
        ACCESS  read-only
        STATUS  mandatory
        DESCRIPTION
                "The date and time this call was placed."
        ::= { atmSvcLogEntry 5 }

atmSvcLogTime OBJECT-TYPE
        SYNTAX  DateAndTime
        ACCESS  read-only
        STATUS  mandatory
        DESCRIPTION
                "The date and time this call was cleared."
        ::= { atmSvcLogEntry 6 }

atmSvcLogClearCause OBJECT-TYPE
        SYNTAX  INTEGER
        ACCESS  read-only
        STATUS  mandatory
        DESCRIPTION
                "The cause of the clearing of this SVC."
        REFERENCE
                "ATM Forum/93-265R5 Signalling Specification Draft -
                 Apr. 14, 93."
        ::= { atmSvcLogEntry 7}

atmSvcLogForwardQOS   OBJECT-TYPE
        SYNTAX  INTEGER {
--                       unspecified (0),
                         class-A (1),
                         class-B (2),
                         class-C (3),
                         class-D (4)
                        }
        ACCESS  read-only
        STATUS  deprecated
        DESCRIPTION
                "The forward Quality Of Service requested for this
                  call."
        ::= { atmSvcLogEntry 8}

atmSvcLogBackwardQOS   OBJECT-TYPE
        SYNTAX  INTEGER {
--                       unspecified (0),
                         class-A (1),
                         class-B (2),
                         class-C (3),
                         class-D (4)
                        }
        ACCESS  read-only
        STATUS  deprecated
        DESCRIPTION
                "The backward Quality Of Service requested for this
                 call."
        ::= { atmSvcLogEntry 9}

atmSvcLogForwardBW   OBJECT-TYPE
        SYNTAX  INTEGER
        ACCESS  read-only
        STATUS  mandatory
        DESCRIPTION
                "The forward bandwidth requested for this
                  call."
        ::= { atmSvcLogEntry 10}

atmSvcLogBackwardBW   OBJECT-TYPE
        SYNTAX  INTEGER
        ACCESS  read-only
        STATUS  mandatory
        DESCRIPTION
                "The backward bandwidth requested for this
                 call."
        ::= { atmSvcLogEntry 11}

atmSvcLogServiceCategory  OBJECT-TYPE
        SYNTAX   INTEGER {
           other(1),   -- none of the following
           cbr(2),     -- constant bit rate
           rtVbr(3),   -- real-time variable bit rate
           nrtVbr(4),  -- non real-time variable bit rate
           abr(5),     -- available bit rate
           ubr(6)      -- unspecified bit rate
           }
        ACCESS  read-only
        STATUS  mandatory
        DESCRIPTION
                "The service category requested for this
                 call."
        ::= { atmSvcLogEntry 12}

atmSvcLogClearLocation   OBJECT-TYPE
        SYNTAX  INTEGER {
             user (0),
             private-netw-serving-the-local-user (1),
             public-netw-serving-the-local-user (2),
             transit-netw (3),
             public-netw-serving-the-remote-user (4),
             private-netw-serving-the-remote-user (5),
             international-netw (7),
             network-beyond-interworking-point (10)
        }
        ACCESS  read-only
        STATUS  mandatory
        DESCRIPTION
                "The originator that caused the clear of this
                 call."
        ::= { atmSvcLogEntry 13}


-- SAAL Group
-- This group defines support for the SAAL protocol.

atmSaal OBJECT IDENTIFIER ::= { atmSvc 2 }

-- This table defines the SAAL configuration and status.

atmSaalConfTable  OBJECT-TYPE
        SYNTAX  SEQUENCE OF AtmSaalConfEntry
        ACCESS  not-accessible
        STATUS  mandatory
        DESCRIPTION
                "This table contains basic information on the SAAL protocol
                 for each signalling link defined per port.
                 Usually, there is only one signalling channel per interface
                 and thus one SAAL protocol definition entry per interface."
        ::= { atmSaal 1 }

atmSaalConfEntry OBJECT-TYPE
        SYNTAX  AtmSaalConfEntry
        ACCESS  not-accessible
        STATUS  mandatory
        DESCRIPTION
                "Entries of atmSaalConfTable. Each entry corresponds to a pair
                 of ATM interface, signalling channel.
                 A signalling channel is uniquely defined on each interface
                 by the VPI and VCI values allocated to it."
        INDEX { atmSaalConfIndex,
                atmSaalConfSiVpi,
                atmSaalConfSiVci }
        ::= { atmSaalConfTable 1 }

AtmSaalConfEntry ::= SEQUENCE {
        atmSaalConfIndex
                INTEGER,
        atmSaalConfSiVpi
                INTEGER,
        atmSaalConfSiVci
                INTEGER,
        atmSaalState
                INTEGER,
        atmSaalTimerPoll
                INTEGER,
        atmSaalTimerKeepAlive
                INTEGER,
        atmSaalTimerNoResponse
                INTEGER,
        atmSaalTimerCC
                INTEGER,
        atmSaalTimerIdle
                INTEGER,
        atmSaalMaxCC
                INTEGER,
        atmSaalMaxPD
                INTEGER,
        atmSaalMaxStat
                INTEGER }

atmSaalConfIndex OBJECT-TYPE
        SYNTAX  INTEGER
        ACCESS  read-only
        STATUS  mandatory
        DESCRIPTION
                "The ifIndex value of the ATM interface which, with the
                 signalling channel defined by its Vpi/Vci values,
                 uniquely identifies this entry."
        ::= { atmSaalConfEntry 1 }

atmSaalConfSiVpi OBJECT-TYPE
        SYNTAX  INTEGER
        ACCESS  read-only
        STATUS  mandatory
        DESCRIPTION
                "The Vpi value which, with the Vci value specified in
                 atmSaalConfSiVci, defines the signalling channel for this
                 entry.
                 Usually, there is one signalling channel per interface
                 defined by Vpi=0,Vci=5."
        ::= { atmSaalConfEntry 2 }

atmSaalConfSiVci OBJECT-TYPE
        SYNTAX  INTEGER
        ACCESS  read-only
        STATUS  mandatory
        DESCRIPTION
                "The Vci value which, with the Vpi value specified in
                 atmSaalConfSiVpi, defines the signalling channel for this
                 entry.
                 Usually, there is one signalling channel per interface
                 defined by Vpi=0,Vci=5."
        ::= { atmSaalConfEntry 3 }

atmSaalState OBJECT-TYPE
        SYNTAX  INTEGER
        ACCESS  read-only
        STATUS  mandatory
        DESCRIPTION
                "The state of the SAAL for this interface as defined in
                 the Q.2110 Specification, Chapter 7.3."
        ::= { atmSaalConfEntry 4 }

atmSaalTimerPoll OBJECT-TYPE
        SYNTAX  INTEGER
        ACCESS  read-only
        STATUS  mandatory
        DESCRIPTION
                "Timer_POLL as defined in the Q.2110 Specification.
                 This timer is running in the active phase to assure that
                 the peer receiver is polled often enough to return
                 its status."
        ::= { atmSaalConfEntry 5 }

atmSaalTimerKeepAlive OBJECT-TYPE
        SYNTAX  INTEGER
        ACCESS  read-only
        STATUS  mandatory
        DESCRIPTION
                "Timer_KEEP-ALIVE as defined in the Q.2110 Specification.
                 This timer is started when entering the transient phase."
        ::= { atmSaalConfEntry 6 }

atmSaalTimerNoResponse OBJECT-TYPE
        SYNTAX  INTEGER
        ACCESS  read-only
        STATUS  mandatory
        DESCRIPTION
                "Timer_NO-RESPONSE as defined in the Q.2110 Specification.
                 This timer indicates the maximum time interval during
                 which at least one STAT PDU needs to be received."
        ::= { atmSaalConfEntry 7 }

atmSaalTimerCC  OBJECT-TYPE
        SYNTAX  INTEGER
        ACCESS  read-only
        STATUS  mandatory
        DESCRIPTION
                "Timer_CC as defined in the Q.2110 Specification.
                 Transmission of PDUs is protected by this timer during
                 establishment and release of a connection and during
                 resynchronization or recovery."
        ::= { atmSaalConfEntry 8 }

atmSaalTimerIdle OBJECT-TYPE
        SYNTAX  INTEGER
        ACCESS  read-only
        STATUS  mandatory
        DESCRIPTION
                "Timer_IDLE as defined in the Q.2110 Specification.
                 This timer is started upon receipt of a STAT PDU
                 when entering the idle phase (no POLL PDUs sent)."
        ::= { atmSaalConfEntry 9 }

atmSaalMaxCC    OBJECT-TYPE
        SYNTAX  INTEGER
        ACCESS  read-only
        STATUS  mandatory
        DESCRIPTION
                "MaxCC as defined in the Q.2110 Specification.
                 This is the maximum value for the state variable
                 VT(CC), corresponding to the maximum number of
                 transmissions of a BGN, END, ER or RS PDU."
        ::= { atmSaalConfEntry 10 }

atmSaalMaxPD    OBJECT-TYPE
        SYNTAX  INTEGER
        ACCESS  read-only
        STATUS  mandatory
        DESCRIPTION
                "MaxPD as defined in the Q.2110 Specification.
                This is the maximum iacceptable value for the state
                variable VT(PD) before sending a POLL PDU and
                resetting VT(PD) to zero.
                This parameter is an upper limit for counter VT(PD)
                that sends a POLL PDU after every (MaxPD) SD PDUs."
        ::= { atmSaalConfEntry 11}

atmSaalMaxStat  OBJECT-TYPE
        SYNTAX  INTEGER
        ACCESS  read-only
        STATUS  mandatory
        DESCRIPTION
                "MaxSTAT as defined in the Q.2110 Specification.
                This is the maximum number of list elements
                placed in a STAT PDU."
        ::= { atmSaalConfEntry 12}

-- This table defines the SAAL statistics.

atmSaalStatsTable  OBJECT-TYPE
        SYNTAX  SEQUENCE OF AtmSaalStatsEntry
        ACCESS  not-accessible
        STATUS  mandatory
        DESCRIPTION
                "This table contains statistics for the SAAL protocol,
                 for outgoing calls only."
        ::= { atmSaal 2 }

atmSaalStatsEntry OBJECT-TYPE
        SYNTAX  AtmSaalStatsEntry
        ACCESS  not-accessible
        STATUS  mandatory
        DESCRIPTION
                "Entries of atmSaalConfTable. Each entry corresponds to a pair
                 of ATM interface, signalling channel.
                 A signalling channel is uniquely defined on each interface
                 by the VPI and VCI values allocated to it."
        INDEX { atmSaalStatsIndex,
                atmSaalStatsSiVpi,
                atmSaalStatsSiVci }
        ::= { atmSaalStatsTable 1 }

AtmSaalStatsEntry ::= SEQUENCE {
        atmSaalStatsIndex
                INTEGER,
        atmSaalStatsSiVpi
                INTEGER,
        atmSaalStatsSiVci
                INTEGER,
        atmSaalUnexpectPdus
                Counter,
        atmSaalUnsuccessPdus
                Counter,
        atmSaalFailedEstablishment
                Counter,
        atmSaalSequenceGap
                Counter,
        atmSaalGapNumbers
                Counter,
        atmSaalOtherListErrors
                Counter,
        atmSaalLackOfCredit
                Counter,
        atmSaalCreditObtained
                Counter }

atmSaalStatsIndex OBJECT-TYPE
        SYNTAX  INTEGER
        ACCESS  read-only
        STATUS  mandatory
        DESCRIPTION
                "The ifIndex value of the ATM interface which, with the
                 signalling channel defined by its Vpi/Vci values,
                 uniquely identifies this entry."
        ::= { atmSaalStatsEntry 1 }

atmSaalStatsSiVpi OBJECT-TYPE
        SYNTAX  INTEGER
        ACCESS  read-only
        STATUS  mandatory
        DESCRIPTION
                "The Vpi value which, with the Vci value specified in
                 atmSaalStatsSiVci, defines the signalling channel for this
                 entry.
                 Usually, there is one signalling channel per interface
                 defined by Vpi=0,Vci=5."
        ::= { atmSaalStatsEntry 2 }

atmSaalStatsSiVci OBJECT-TYPE
        SYNTAX  INTEGER
        ACCESS  read-only
        STATUS  mandatory
        DESCRIPTION
                "The Vci value which, with the Vpi value specified in
                 atmSaalStatsSiVpi, defines the signalling channel for this
                 entry.
                 Usually, there is one signalling channel per interface
                 defined by Vpi=0,Vci=5."
        ::= { atmSaalStatsEntry 3 }

atmSaalUnexpectPdus OBJECT-TYPE
        SYNTAX  Counter
        ACCESS  read-only
        STATUS  mandatory
        DESCRIPTION
                    "Error conditions A to M, as defined in the Q.2110
                     Specification.
                     This is the number of received unsolicited or
                     or inappropriate PDUs."
        ::= { atmSaalStatsEntry 4 }

atmSaalUnsuccessPdus OBJECT-TYPE
        SYNTAX  Counter
        ACCESS  read-only
        STATUS  mandatory
        DESCRIPTION
                    "Error condition O as defined in the Q.2110
                     Specification.
                     This is the number of failing retries."
        ::= { atmSaalStatsEntry 5 }

atmSaalFailedEstablishment OBJECT-TYPE
        SYNTAX  Counter
        ACCESS  read-only
        STATUS  mandatory
        DESCRIPTION
                    "Error condition P as defined in the Q.2110
                     Specification.
                     This is the number of failing polls."
        ::= { atmSaalStatsEntry 6 }

atmSaalSequenceGap OBJECT-TYPE
        SYNTAX  Counter
        ACCESS  read-only
        STATUS  mandatory
        DESCRIPTION
                    "The number of times sequence gaps were
                     detected by the peer entity. "
        ::= { atmSaalStatsEntry 7 }

atmSaalGapNumbers OBJECT-TYPE
        SYNTAX  Counter
        ACCESS  read-only
        STATUS  mandatory
        DESCRIPTION
                    "The number of times frames were
                     re-transmitted due to sequence gaps
                     detected by the peer entity."
        ::= { atmSaalStatsEntry 8 }

atmSaalOtherListErrors OBJECT-TYPE
        SYNTAX  Counter
        ACCESS  read-only
        STATUS  mandatory
        DESCRIPTION
                    "Error conditions Q to V as defined in the
                     Q.2110 Specification."
        ::= { atmSaalStatsEntry 9 }

atmSaalLackOfCredit OBJECT-TYPE
        SYNTAX  Counter
        ACCESS  read-only
        STATUS  mandatory
        DESCRIPTION
                    "Error condition W as defined in the Q.2110
                     Specification.
                     This is the number of times that transmission
                     was not permitted by the peer entity due to
                     a lack of credit."
        ::= { atmSaalStatsEntry 10 }

atmSaalCreditObtained OBJECT-TYPE
        SYNTAX  Counter
        ACCESS  read-only
        STATUS  mandatory
        DESCRIPTION
                    "Error condition X as defined in the Q.2110
                     Specification.
                     This is the number of times that credit was
                     obtained from the peer entity to allow
                     transmission."
        ::= { atmSaalStatsEntry 11 }


-- This MIB defines ATM support for Permanent Virtual Circuits.

atmPvc OBJECT IDENTIFIER ::= { node 10 }

-- Global PVC Parameter

atmPvcHandler OBJECT-TYPE
        SYNTAX  INTEGER {
                         ready (1),
                         out-of-memory (2)
                        }
        ACCESS  read-only
        STATUS  mandatory
        DESCRIPTION
                "The status of the PVC handler in the switch.
                 When no more memory is available, the creation of new PVCs
                 is rejected with a generic Error sense code."
        ::= { atmPvc 1 }


-- PVC Table

atmPvcTable  OBJECT-TYPE
        SYNTAX  SEQUENCE OF AtmPvcEntry
        ACCESS  not-accessible
        STATUS  mandatory
        DESCRIPTION
                "This table lists all PVCs defined per interface.
                 There is only one entry in this table per PVC
                 (point-to-point or point-to-multipoint PVC)."
        ::= { atmPvc 2 }

atmPvcEntry OBJECT-TYPE
        SYNTAX  AtmPvcEntry
        ACCESS  not-accessible
        STATUS  mandatory
        DESCRIPTION
                "Entries of atmPvcTable.
                 Policing parameters are those requested when
                 creating the PVC. The actual values used by the
                 network to satisfy these requirements may slightly
                 differ. These values are attached to virtual links
                 and are available in virtual link tables, such as
                 the RFC-1695 VPL/VCL tables."
        INDEX { atmPvcIndex,
                atmPvcIdentifier }
        ::= { atmPvcTable 1 }

AtmPvcEntry ::= SEQUENCE {
        atmPvcIndex
                INTEGER,
        atmPvcIdentifier
                INTEGER,
        atmPvcRowStatus
                RowStatus,
        atmPvcType
                INTEGER,
        atmPvcEndPoint
                INTEGER,
        atmPvcVpi
                INTEGER,
        atmPvcVci
                INTEGER,
        atmPvcBackwardQos
                INTEGER,
        atmPvcForwardQos
                INTEGER,
        atmPvcBackwardType
                INTEGER,
        atmPvcForwardType
                INTEGER,
        atmPvcBackwardParm1
                INTEGER,
        atmPvcForwardParm1
                INTEGER,
        atmPvcFrameDiscard
                INTEGER }

atmPvcIndex OBJECT-TYPE
        SYNTAX  INTEGER
        ACCESS  read-only
        STATUS  mandatory
        DESCRIPTION
                "The ifIndex value of the ATM interface used by this PVC."
        ::= { atmPvcEntry 1 }

atmPvcIdentifier OBJECT-TYPE
        SYNTAX  INTEGER
        ACCESS  read-only
        STATUS  mandatory
        DESCRIPTION
                "A value used to uniquely identify this PVC on this
                 interface.

                 To create a new PVC on a given interface, an unused PVC
                 identifier must be found."
        ::= { atmPvcEntry 2 }

atmPvcRowStatus OBJECT-TYPE
        SYNTAX  INTEGER { active (1),
                          notInService (2),
                          notReady (3),
                          createAndWait (5),
                          destroy (6) }
        ACCESS  read-write
        STATUS  mandatory
        DESCRIPTION
                "States values:
                 active: the PVC is operational
                 notInService: the PVC is failing
                 notReady: values are missing to be able to activate this PVC

                 Actions:
                 active: this requests to re-start a failing PVC (which status
                         was notInService)
                 destroy: this requests to delete a PVC
                 createAndWait: this requests to create a PVC

                 To create a new PVC, this variable must be set to
                 createAndWait with an index where:
                 - atmPvcIndex is the number of the interface from where the
                               PVC is created
                 - atmPvcIdentifier is an unused PVC identifier for this
                                    interface

                 To activate a PVC, this variable must be set to active.

                 Default values are provided for all attributes except for the
                 atmPvcEpRemIndex. If this attribute is not set, the PVC will
                 remain in the notReady state.

                 To delete a point-to-point PVC, this variable must be set to
                 destroy."
        ::= { atmPvcEntry  3 }

atmPvcType OBJECT-TYPE
        SYNTAX  INTEGER  { point2pointVP (1),
                           point2pointVC (2),
                           point2multipointVP (3),
                           point2multipointVC (4) }
        ACCESS  read-write
        STATUS  mandatory
        DESCRIPTION
                "A unicast PVC is defined between two endpoints, using
                 either a VP or a VC connection.
                 A Multicast PVC is defined :
                   - first between a source endpoint and a target endpoint
                   - then adding endpoints, thanks to the PvcEpTable
                 using either VP or VC connections.
                 The source endpoint is called Root,
                 while target endpoints are called multicast parties."
        DEFVAL { point2pointVC }
        ::= { atmPvcEntry 4 }

atmPvcEndPoint OBJECT-TYPE
        SYNTAX  INTEGER  { primaryRoot (1),
                           secondaryLeaf (2) }
        ACCESS  read-only
        STATUS  mandatory
        DESCRIPTION
                "The end-point where the PVC is created is identified as the
                 primary or root end-point.
                 the other end-point is the identified as the secondary or
                 leaf end-point."
        DEFVAL { primaryRoot }
        ::= { atmPvcEntry 5 }

atmPvcVpi OBJECT-TYPE
        SYNTAX  INTEGER (0..65536)
        ACCESS  read-write
        STATUS  mandatory
        DESCRIPTION
                "The VPI value assigned to this PVC at the origin.
                 A value of 65536 means that no value has been specified by
                 the operator.
                 If no value has been specified, the VPI value is then
                 automatically allocated by the agent when activating the PVC."
        DEFVAL { 65536 }
        ::= { atmPvcEntry 6 }

atmPvcVci OBJECT-TYPE
        SYNTAX  INTEGER (0..65536)
        ACCESS  read-write
        STATUS  mandatory
        DESCRIPTION
                "The VCI value assigned to this PVC at the origin.
                 For VP-type PVC, this value is not applicable and is
                 set to 0.
                 A value of 65536 means that no value has been specified by
                 the operator.
                 If no value has been specified, the VCI value is then
                 automatically allocated by the agent when activating the PVC."
        DEFVAL { 65536 }
        ::= { atmPvcEntry 7 }

atmPvcBackwardQos OBJECT-TYPE
        SYNTAX  INTEGER {
--                       unspecified (0),
                         class-A (1)
                        }
        ACCESS  read-write
        STATUS  deprecated
        DESCRIPTION
                "The QOS requested for this PVC to the originator."
        DEFVAL { unspecified }
        ::= { atmPvcEntry 8 }

atmPvcForwardQos OBJECT-TYPE
        SYNTAX  INTEGER {
--                       unspecified (0),
                         class-A (1)
                        }
        ACCESS  read-write
        STATUS  deprecated
        DESCRIPTION
                "The QOS requested for this PVC from the originator."
        DEFVAL { unspecified }
        ::= { atmPvcEntry 9 }

atmPvcBackwardType OBJECT-TYPE
        SYNTAX  OBJECT IDENTIFIER
        ACCESS  read-write
        STATUS  mandatory
        DESCRIPTION
                "The first parameter used to define the
                policy requested for this PVC."
        ::= { atmPvcEntry 10 }

atmPvcForwardType OBJECT-TYPE
        SYNTAX  OBJECT IDENTIFIER
        ACCESS  read-write
        STATUS  mandatory
        DESCRIPTION
                "The type of policy requested for this PVC."
        ::= { atmPvcEntry 11 }

atmPvcBackwardParm1 OBJECT-TYPE
        SYNTAX  INTEGER
        ACCESS  read-write
        STATUS  mandatory
        DESCRIPTION
                "The fourth parameter used to define the
                policy requested for this PVC."
        DEFVAL { 0 }
        ::= { atmPvcEntry 12 }

atmPvcForwardParm1 OBJECT-TYPE
        SYNTAX  INTEGER
        ACCESS  read-write
        STATUS  mandatory
        DESCRIPTION
                "The third parameter used to define the
                policy requested for this PVC."
        DEFVAL { 0 }
        ::= { atmPvcEntry 13 }

atmPvcFrameDiscard OBJECT-TYPE
        SYNTAX  INTEGER {
                         off  (0),
                         on   (1)
                         }
        ACCESS  read-write
        STATUS  mandatory
        DESCRIPTION
                "This variable allows to discard smart frames.
                If this value is set to 1, it is allowed to discard.
                If this value is set to 0, it is not allowed to discard."
        ::= { atmPvcEntry 14 }

-- A list of all the End-Points for each PVC defined.

atmPvcEpTable  OBJECT-TYPE
        SYNTAX  SEQUENCE OF AtmPvcEpEntry
        ACCESS  not-accessible
        STATUS  mandatory
        DESCRIPTION
                 "This table lists the characteristics of the remote
                  end-points of defined PVCs.
                  There is at least one entry for each PVC defined
                  in the atmPvcTable."
        ::= { atmPvc 3 }

atmPvcEpEntry OBJECT-TYPE
        SYNTAX  AtmPvcEpEntry
        ACCESS  not-accessible
        STATUS  mandatory
        DESCRIPTION
                "Entries of atmPvcEpTable.
                 One entry is automatically created by the agent when a
                 PVC is created in the PVC Table.
                 No additional entry can be created in this table if the
                 PVC is defined as point-to-point in the PVC table."
        INDEX { atmPvcEpIndex,
                atmPvcEpIdentifier,
                atmPvcEpParty }
        ::= { atmPvcEpTable 1 }

AtmPvcEpEntry ::= SEQUENCE {
        atmPvcEpIndex
                INTEGER,
        atmPvcEpIdentifier
                INTEGER,
        atmPvcEpParty
                INTEGER,
        atmPvcEpRowStatus
                RowStatus,
        atmPvcEpStatusCause
                INTEGER,
        atmPvcEpRemAddress
                NetPrefix,
        atmPvcEpRemIndex
                INTEGER,
        atmPvcEpRemVpi
                INTEGER,
        atmPvcEpRemVci
                INTEGER,
        atmPvcEpLastActive
                DateAndTime,
        atmPvcEpQ2931Cause
                INTEGER,
        atmPvcEpFailures
                Counter,
        atmPvcEpAtmAddress
                AtmAddress}

atmPvcEpIndex OBJECT-TYPE
        SYNTAX  INTEGER
        ACCESS  read-only
        STATUS  mandatory
        DESCRIPTION
                "The ifIndex value of the ATM interface used by this PVC."
        ::= { atmPvcEpEntry 1 }

atmPvcEpIdentifier OBJECT-TYPE
        SYNTAX  INTEGER
        ACCESS  read-only
        STATUS  mandatory
        DESCRIPTION
                "A value used to uniquely identify this PVC on this
                 interface.

                 This is the same identifier as the one used in the atmPvcTable
                 to identify the PVC that this end-point belongs to."
        ::= { atmPvcEpEntry 2 }

atmPvcEpParty OBJECT-TYPE
        SYNTAX  INTEGER
        ACCESS  read-only
        STATUS  mandatory
        DESCRIPTION
                "A value used to uniquely identify a remote end-point of a PVC,
                 when associated with an interface index and a PVC identifier.

                 For a point-to-point PVC, this value is always set to 0."
        ::= { atmPvcEpEntry 3 }

atmPvcEpRowStatus OBJECT-TYPE
        SYNTAX  INTEGER { active (1),
                          notInService (2),
                          notReady (3),
                          createAndWait (5),
                          destroy (6) }
        ACCESS  read-write
        STATUS  mandatory
        DESCRIPTION
                "States values:
                 active: the PVC is operational
                 notInService: the PVC is failing
                 notReady: values are missing to be able to activate this PVC

                 Actions:
                 active: this requests to re-start a failing unicast PVC
                         (status was notInService)
                 createAndWait: Add a new party in a multicast PVC
                                (the first party is created when
                                the root is created).
                 destroy: this requests to delete a unicast PVC."
        ::= { atmPvcEpEntry  4 }

atmPvcEpStatusCause OBJECT-TYPE
        SYNTAX  INTEGER { noCause (1),
                          underModification (2),
                          missingParameters (3),
                          invalidParameters (4),
                          uncompatibleParameters (5),
                          internalFailure (6),
                          pvcFailure (7),
                          unavailableResource (8),
                          remoteBusy (9),
                          retrying (10)
                          }
        ACCESS  read-only
        STATUS  mandatory
        DESCRIPTION
                "A detailed cause for the current PVC status."
        ::= { atmPvcEpEntry 5 }

atmPvcEpRemAddress OBJECT-TYPE
        SYNTAX  NetPrefix
        ACCESS  read-write
        STATUS  mandatory
        DESCRIPTION
                "The ATM address of the remote ATM switch where the PVC
                 ends.
                 If none is specified, the ATM address of the target
                 switch (local) is used and the PVC is confined to the
                 target switch (local switch)."
        ::= { atmPvcEpEntry 6 }

atmPvcEpRemIndex OBJECT-TYPE
        SYNTAX  INTEGER
        ACCESS  read-write
        STATUS  mandatory
        DESCRIPTION
                "The ifindex value used at the remote end to identify the
                 interface where the PVC ends.
                 This entry will remain in the notReady state until this
                 attribute is set (and the atmPvcRowStatus is set to active)."
        ::= { atmPvcEpEntry 7 }

atmPvcEpRemVpi OBJECT-TYPE
        SYNTAX  INTEGER (0..65536)
        ACCESS  read-write
        STATUS  mandatory
        DESCRIPTION
                "The VPI value assigned to this PVC at the destination
                 (remote end).
                 If left at 65536  (default value), one value is
                 automatically allocated by the agent."
        DEFVAL { 65536 }
        ::= { atmPvcEpEntry 8 }

atmPvcEpRemVci OBJECT-TYPE
        SYNTAX  INTEGER (0..65536)
        ACCESS  read-write
        STATUS  mandatory
        DESCRIPTION
                "The VCI value assigned to this PVC at the destination.
                 For VP-type PVC, this value is not applicable and is
                 set to 0.
                 If left at 65536 (default value), one value is
                 automatically allocated by the agent (for VC only)."
        DEFVAL { 65536 }
        ::= { atmPvcEpEntry  9 }

atmPvcEpLastActive OBJECT-TYPE
        SYNTAX  DateAndTime
        ACCESS  read-only
        STATUS  mandatory
        DESCRIPTION
                "The date and time of the latest PVC activation."
        ::= { atmPvcEpEntry  10}

atmPvcEpQ2931Cause OBJECT-TYPE
        SYNTAX  INTEGER
        ACCESS  read-only
        STATUS  mandatory
        DESCRIPTION
                "The cause of the failure as defined by Q2931."
        ::= { atmPvcEpEntry  11}

atmPvcEpFailures OBJECT-TYPE
        SYNTAX  Counter
        ACCESS  read-only
        STATUS  mandatory
        DESCRIPTION
                "The number of times this PVC failed."
        ::= { atmPvcEpEntry 12 }

atmPvcEpAtmAddress OBJECT-TYPE
        SYNTAX  AtmAddress
        ACCESS  read-write
        STATUS  mandatory
        DESCRIPTION
                "The ATM address of the remote ATM switch where the PVC
                 ends.
                 If none is specified, the ATM address of the target
                 switch (local) is used and the PVC is confined to the
                 target switch (local switch)."
        ::= { atmPvcEpEntry 13 }


-- The group atmLanEmulation defines the specific support for
-- the lan emulation resources in the atm node

lanEmulation OBJECT IDENTIFIER ::= { node 11 }

lanEmulationServer OBJECT IDENTIFIER ::= { lanEmulation 1 }

lesConfTable  OBJECT-TYPE
        SYNTAX  SEQUENCE OF LesConfEntry
        ACCESS  not-accessible
        STATUS  mandatory
        DESCRIPTION
                "This table contains the specific configuration
                 parameters of the embedded LAN emulation servers."
        ::= {lanEmulationServer  1}

lesConfEntry OBJECT-TYPE
        SYNTAX  LesConfEntry
        ACCESS  not-accessible
        STATUS  mandatory
        DESCRIPTION
                "Entries of the lesConfTable. Each entry corresponds to
                 a Lan emulation server embedded in the atm control point."
        INDEX { lesIndex }
        ::= { lesConfTable 1 }

LesConfEntry ::= SEQUENCE {
        lesIndex
              INTEGER,
        lesMaxNumberOfClients
              INTEGER,
        lesLecLastChange
              INTEGER,
        lesMaxLecId
              INTEGER,
        lesMinLecId
              INTEGER}

lesIndex OBJECT-TYPE
    SYNTAX  INTEGER
    ACCESS  not-accessible
    STATUS  mandatory
    DESCRIPTION
           "A value which uniquely identifies a
                  lan emulation server in the lesConfTable."
    ::= { lesConfEntry  1 }

lesMaxNumberOfClients OBJECT-TYPE
    SYNTAX  INTEGER
    ACCESS  read-write
    STATUS  mandatory
    DESCRIPTION
           "The maximum number of clients supported by
            this lan emulation server.
            The maximum number of clients cannot be set
            if the associated LES is started.
            The total number of clients on all the embedded
            lan emulation servers in one node must not exceed 128."
    ::= { lesConfEntry  2 }

lesLecTableLastChange OBJECT-TYPE
    SYNTAX  TimeTicks
    ACCESS  read-only
    STATUS  mandatory
    DESCRIPTION
           "The value of the sysUpTime the last time a change was detected
            in a lesLecEntry associated to the given lesIndex.
            The lesLecEntry is defined in the lesMIB."
    ::= { lesConfEntry  3 }

lesMaxLecId OBJECT-TYPE
    SYNTAX  INTEGER
    ACCESS  read-write
    STATUS  mandatory
    DESCRIPTION
           "The maximum LecId assigned by the LES.
            The maximum LecId cannot be set
            if the associated LES is started.
            (lesMaxLecId-lesMinLecId +1) of this LES
            +(lesMaxLecId-lesMinLecId +1) of colocated LES
            must not exceed 128.
            This variable must obey the following rules:
            1<= lesMaxLecId <= 65279.
            lesMinLecId <= lesMaxLecId."
    ::= { lesConfEntry  4 }

lesMinLecId OBJECT-TYPE
    SYNTAX  INTEGER
    ACCESS  read-write
    STATUS  mandatory
    DESCRIPTION
           "The minimum LecId assigned by the LES.
            The minimum LecId cannot be set
            if the associated LES is started.
            This variable must obey the following rules:
            1<= lesMinLecId <= 65279.
            lesMinLecId <= lesMaxLecId."
    ::= { lesConfEntry  5 }


-- atmSecurity

atmSecurity OBJECT IDENTIFIER ::= { node 12 }

-- Base Group

secBase OBJECT IDENTIFIER ::= { atmSecurity 1 }

mode OBJECT-TYPE
        SYNTAX  INTEGER { no-security (1),
                          access-control (2)
                        }
        ACCESS  read-write
        STATUS  mandatory
        DESCRIPTION

             "When set to access-control, the access control mechanism
             is enabled. The access to the ATM network is granted
             based on the value of the ATM address exchanged by the ILMI
             protocol.
             The control can apply to:
             - The ESI part of the ATM address.
             - The network prefix and the ESI parts of the ATM address.
             The address is controlled on a per-interface basis.

             When set to no-security, no control is performed, any
             address can register to the network."
                 ::= { secBase  1 }

bootSource OBJECT-TYPE
        SYNTAX  INTEGER { local-storage (1),
                          remote-file (2)
                        }
        ACCESS  read-only
        STATUS  mandatory
        DESCRIPTION

             "This value is depending on hardware model/version.
             When the ATM switch is reset, the list of the
             authorized ATM addresses is
             automatically retrieved, depending on the security boot
             source configuration:
             - From local storage (Non Volatile RAM).
             - Through TFTP, from a dedicated TFTP server."
                 ::= { secBase  2 }

transferLastResult OBJECT-TYPE
        SYNTAX  INTEGER { not-initialized (1),
                          transfer-successful (2),
                          upload-in-progress (3),
                          download-in-progress (4),
                          generic-error (5),
                          no-response-from-host (6),
                          connection-lost (7),
                          file-not-found (8),
                          file-empty (9),
                          file-too-big (10),
                          access-rights-violation (11),
                          invalid-file-header (12),
                          checksum-error (13),
                          transfer-error (14),
                          hardware-error (15)
                          }
        ACCESS  read-only
        STATUS  mandatory
        DESCRIPTION
                "The result of the last transfer of the security file.
                 If no security file has been transfered,
                 transferLastResult is equal to not-initialized.
                 When one of the TFTP security variables is modified,
                 transferLastResult is reset to not-initialized.
                 When a security file is downloaded,
                 the content of the file is checked.
                 If a line in the security file is not valid
                 the line is ignored."
                 ::= { secBase  3 }

secInterfaces OBJECT IDENTIFIER ::= { atmSecurity 2 }

secIfTable OBJECT-TYPE
        SYNTAX  SEQUENCE OF SecIfEntry
        ACCESS  not-accessible
        STATUS  mandatory
        DESCRIPTION
                "For each ATM physical interface, this table gives
                 the information on the last security violation."
        ::= { secInterfaces 1}

secIfEntry OBJECT-TYPE
        SYNTAX  SecIfEntry
        ACCESS  not-accessible
        STATUS  mandatory
        DESCRIPTION
                "Entries of the secIfTable."
        INDEX { secIfIndex }
        ::= { secIfTable 1 }

SecIfEntry ::= SEQUENCE {
        secIfIndex
              INTEGER,
        violationTime
              DateAndTime,
        atmAddressFailed
              AtmAddress
        }

secIfIndex OBJECT-TYPE
        SYNTAX  INTEGER
        ACCESS  read-only
        STATUS  mandatory
        DESCRIPTION
                "The interface number of the port represented by this entry.
                 This is the same number as the index used to represent this
                 interface in the MIB-II interface table."
        ::= { secIfEntry 1 }

violationTime OBJECT-TYPE
        SYNTAX  DateAndTime
        ACCESS  read-only
        STATUS  mandatory
        DESCRIPTION
                "The date and time of the last ATM address violation
                 detected on this interface ."
        ::= { secIfEntry 2 }

atmAddressFailed OBJECT-TYPE
        SYNTAX  AtmAddress
        ACCESS  read-only
        STATUS  mandatory
        DESCRIPTION
                "The ATM address which caused the last violation on this
                 interface."
        ::= { secIfEntry 3 }

-- ====================================================================
-- Traps
-- ====================================================================

hello TRAP-TYPE
      ENTERPRISE node
      VARIABLES { sysObjectID, ifPhysAddress }
      DESCRIPTION
      " A hello trap is sent:
        - when the system re-initializes: it is sent every minutes until
          an SNMP request is received or until 255 minutes have passed.
        - when one of the following parameters is changed:
          -- agent IP address(es)
          -- agent subnet mask(s)
          -- ATM address of the IP ARP server
          -- IP address of the default gateway
        The value of ifPhysAddress is the ATM address of the hub.
        The hello trap may be disabled."
      ::= 1

lock TRAP-TYPE
     ENTERPRISE node
     VARIABLES { moduleSlotIndex }
     DESCRIPTION
     " A lock trap is sent when a set request is rejected because it is
       suspected that this may cause to break the link between the agent
       and the manager. This may occur when:
       - isolating a slot
       - disabling a port
       if the request is received through this specific port/module/slot."
     ::= 2

change TRAP-TYPE
       ENTERPRISE node
       VARIABLES { moduleSlotIndex, ifIndex }
       DESCRIPTION
       " A change trap is sent when one of the following MIB variables or
         group of variables is changed:
         - Date and Time reset
         - System Parameters (name, contact, location) changed
         - Interface changed:
           -- Administrative State (enabled/disabled)
         - Module changed:
           -- Administrative State (isolate/attach)
         When one of this variable is changed, the lastChange MIB object is
         also updated with the current date and time.
         When the Date and Time or the System Parameters changed,
         the interface number of the hub virtual interface is returned.
         This trap may be disabled."
       ::= 3

pvcFailure TRAP-TYPE
           ENTERPRISE node
           VARIABLES { atmPvcIndex, atmPvcIdentifier, atmPvcEpQ2931Cause }
           DESCRIPTION
           " A PVC failure trap is sent when a PVC becomes inoperational."
           ::= 4

-- node.5 intentionnally left unused

callLoggingOverflow TRAP-TYPE
          ENTERPRISE node
          DESCRIPTION
          " A callLoggingOverflow trap is sent when the call logging table
           is about to wrap."
          ::= 6

moduleInstalled TRAP-TYPE
          ENTERPRISE node
          VARIABLES { moduleSlotIndex }
          DESCRIPTION
          " An ATM module has been detected in the hub."
          ::= 7

moduleRemoved TRAP-TYPE
            ENTERPRISE node
            VARIABLES { moduleSlotIndex }
            DESCRIPTION
            " An ATM module is no longer detected in the hub."
            ::= 8

lesMaxClientsReached TRAP-TYPE
            ENTERPRISE node
            VARIABLES { lesIndex }
            DESCRIPTION
            "The maximum number of lan emulation
            clients has been connected to the given lan emulation
            server."
            ::= 9

lesMaxClientsThresholdDown TRAP-TYPE
            ENTERPRISE node
            VARIABLES { lesIndex }
            DESCRIPTION
            "The number of operational clients of the given emulated
            lan is now equal to lesMaxNumberOfClients - 10.
            This trap is sent only if  the
            trap lesMaxClientsReached has been sent previously.
            lesIndex is the index of the lesConfTable defined above"
            ::= 10

-- Expansion Description

expansion OBJECT IDENTIFIER ::= { atmSw 4 }

expansionHardwareVersion OBJECT-TYPE
        SYNTAX  DisplayString
        ACCESS  read-only
        STATUS  mandatory
        DESCRIPTION
                "The Part Number (P/N) and Engineering Change (EC) level
                 and Plant Location for this module."
        ::= { expansion 1 }


-- Chassis management

chassis         OBJECT IDENTIFIER ::= { atmSw 5 }


--
-- Hub Chassis Groups
--

chassisAgents   OBJECT IDENTIFIER ::= { chassis   1 }
conc            OBJECT IDENTIFIER ::= { chassis   2 }
env             OBJECT IDENTIFIER ::= { chassis   3 }
modules         OBJECT IDENTIFIER ::= { chassis   4 }
ocPower         OBJECT IDENTIFIER ::= { chassis   8 }
ocInventory     OBJECT IDENTIFIER ::= { chassis   9 }

ocPowerControl  OBJECT IDENTIFIER ::= { ocPower  1 }
ocInvHub        OBJECT IDENTIFIER ::= { ocInventory 1 }
ocInvMods       OBJECT IDENTIFIER ::= { ocInventory 2 }



agentsMySlot OBJECT-TYPE
        SYNTAX INTEGER
        ACCESS read-only
        STATUS mandatory
        DESCRIPTION
                "The slot id of this agent."
        ::= { chassisAgents 1 }

agentsMasterReset OBJECT-TYPE
        SYNTAX  INTEGER {
                noReset(1)
                }
        ACCESS read-only
        STATUS mandatory
        DESCRIPTION
                "The agent mastership cannot be reset.
                noReset is always returned."
        ::= { chassisAgents 2 }

agentsTable OBJECT-TYPE
        SYNTAX  SEQUENCE OF AgentsEntry
        ACCESS  not-accessible
        STATUS  mandatory
        DESCRIPTION
                "A table of agents in the concentrator as seen by
                this agent.  A master will see all the agents; a slave
                will only see itself."
        ::= { chassisAgents 3 }

agentsEntry OBJECT-TYPE
        SYNTAX  AgentsEntry
        ACCESS  not-accessible
        STATUS  mandatory
        DESCRIPTION
                "A profile of an agent within the concentrator."
        INDEX   { agentsSlotIndex }
        ::= { agentsTable 1 }

AgentsEntry ::=
        SEQUENCE {
                agentsSlotIndex
                        INTEGER,
                agentsStationAddr
                        OCTET STRING,
                agentsIpAddress
                        IpAddress,
                agentsMasterStatus
                        INTEGER,
                agentsMasterPriority
                        INTEGER,
                ocAgentsSubSlot
                        INTEGER
                }

agentsSlotIndex OBJECT-TYPE
        SYNTAX  INTEGER
        ACCESS  read-only
        STATUS  mandatory
        DESCRIPTION
                "The slot number that identifies the referenced agent."
        ::= { agentsEntry 1 }

agentsStationAddr OBJECT-TYPE
        SYNTAX  OCTET STRING (SIZE(6))
        ACCESS  read-only
        STATUS  mandatory
        DESCRIPTION
                "The unique identifier for this agent.  Often this
                is the value of ifPhysAddress for the first interface."
        ::= { agentsEntry 2 }

agentsIpAddress OBJECT-TYPE
        SYNTAX  IpAddress
        ACCESS  read-only
        STATUS  mandatory
        DESCRIPTION
                "An IP Address that can be used to communicate to
                this agent.  Note, this object's value may change
                as the agent switches to different sub-networks."
        ::= { agentsEntry 3 }

agentsMasterStatus OBJECT-TYPE
        SYNTAX INTEGER {
                master(1),
                non-master(2), -- slave
                electing(3)
                }
        ACCESS read-only
        STATUS mandatory
        DESCRIPTION
                "The mastership status of this agent."
        ::= { agentsEntry 4 }

agentsMasterPriority OBJECT-TYPE
        SYNTAX INTEGER {
                one(1),         -- lowest
                two(2),
                three(3),
                four(4),
                five(5),
                six(6),
                seven(7),
                eight(8),
                nine(9),
                ten(10),        -- highest
                never(11)
                }
        ACCESS read-only
        STATUS mandatory
        DESCRIPTION
                "The mastership priority of this agent.  Ten is the
                highest and one is the lowest.  Never means will not
                be able become master. MasterPriority is only used
                when an election occurs. Mastership is not pre-emptive."
        ::= { agentsEntry 5 }

ocAgentsSubSlot OBJECT-TYPE
        SYNTAX INTEGER
        ACCESS read-only
        STATUS mandatory
        DESCRIPTION
                "The subslot index for this agent.  For agents not located
                in the IBM 8260 system, this object will always
                return 1 for this object value."
        ::= { agentsEntry 6 }


-- The conc Group:

-- This group is mandatory for all devices that are acting as a concentrator
-- master.
--
-- The conc group contains information and control relative to concentrator.
--

concType OBJECT-TYPE
        SYNTAX INTEGER {
                hub-8285-00X(1),        -- 8285 model 00B or 00P,
                hub-8285-02X(2),        -- 8285 model 02B or 02P,
                hub-8260-017-A(6),      -- 17-slot with ring backplane
                hub-8260-010-A(10)      -- 10-slot with ring backplane
        }
        ACCESS read-only
        STATUS mandatory
        DESCRIPTION
                "This object identifies the type of concentrator represented
                by this agent."
        ::= { conc 1 }

concReset OBJECT-TYPE
        SYNTAX INTEGER {
                noReset(1),
                reset(2)
                }
        ACCESS read-write
        STATUS mandatory
        DESCRIPTION
                "Writing a reset(2) will reset every module in the stack
                without changing the current configuration and will zero
                all counters."
        ::= { conc 2 }

concNumSlots OBJECT-TYPE
        SYNTAX INTEGER
        ACCESS read-only
        STATUS mandatory
        DESCRIPTION
                "The number of slots in this concentrator.  This value is
                the sum total of all payload slots plus any slots reserved
                for controller modules.  For example, for an IBM 8260 agent
                operating in a 17-slot IBM 8260 hub, this object will have
                the value 19 (17 payload slots plus 2 controller slots)."
        ::= { conc 3 }

concProfile OBJECT-TYPE
        SYNTAX OCTET STRING (SIZE(1..3))
        ACCESS read-only
        STATUS mandatory
        DESCRIPTION
                "A bit string containing always 00 00 00."
        ::= { conc 4 }

concDescr OBJECT-TYPE
        SYNTAX DisplayString (SIZE(1..128))
        ACCESS read-only
        STATUS mandatory
        DESCRIPTION
                "A textual string containing information about the hub type."
        ::= { conc 5 }



-- The env Group

-- This group represents the concentrator's environment.  It is available
-- from agents that are acting as a concentrator master.

envTempStatus OBJECT-TYPE
        SYNTAX INTEGER {
                okay(1),
                extremeTemp(2),
                warning(3)
                }
        ACCESS read-only
        STATUS mandatory
        DESCRIPTION
                "The overall temperature status for this concentrator.
                This object's value is an aggregate of all the temperature
                probes in the concentrator, such that, when at least one probe
                reports extreme temperature, this object will have the value
                extremeTemp(2).  This object will have the value warning(3)
                prior to reporting the value extremeTemp(2) as a means of
                warning of a possible hub overheat condition."
    ::= { env 1 }

envPSCapacity OBJECT-TYPE
        SYNTAX INTEGER
        ACCESS read-only
        STATUS mandatory
        DESCRIPTION
                "The total capacity of power supplies for this concentrator."
        ::= { env 2 }

envPSTable OBJECT-TYPE
        SYNTAX SEQUENCE OF EnvPSEntry
        ACCESS not-accessible
        STATUS mandatory
        DESCRIPTION
                "A table that contains information about each potential
                power supply in the concentrator."
        ::= { env 3 }


envPSEntry OBJECT-TYPE
        SYNTAX EnvPSEntry
        ACCESS not-accessible
        STATUS mandatory
        DESCRIPTION
                "A list of information for each power supply in the
                concentrator."
        INDEX { envPSIndex }
        ::= { envPSTable 1 }

EnvPSEntry ::=
        SEQUENCE {
                envPSIndex
                        INTEGER,
                envPSAdminState
                        INTEGER,
                envPSOperStatus
                        INTEGER
                }

envPSIndex OBJECT-TYPE
        SYNTAX INTEGER
        ACCESS read-only
        STATUS mandatory
        DESCRIPTION
                "Identifies the power supply for which this entry contains
                power supply information. "
        ::= { envPSEntry 1 }

envPSAdminState OBJECT-TYPE
        SYNTAX INTEGER {
                activate(1)
                }
        ACCESS read-only
        STATUS mandatory
        DESCRIPTION
                "The current desired state of the power supply.
                activate is the only adminState reported."
        ::= { envPSEntry 2 }

envPSOperStatus OBJECT-TYPE
        SYNTAX INTEGER {
                active(1),
                standby(2),
                faulty(3),
                not-installed(4)
                }
        ACCESS read-only
        STATUS mandatory
        DESCRIPTION
                "The current operational state of the power supply.  A power
                supply in standby does not provide power to the concentrator."
        ::= { envPSEntry 3 }

envFanStatus OBJECT-TYPE
        SYNTAX INTEGER {
                okay(1),
                faulty(2),
                not-installed(4),
                unknown(5)
                }
        ACCESS read-only
        STATUS mandatory
        DESCRIPTION
                "The overall status of the fan(s).  When fan operational
                status is known, this object's value is an aggregate of
                all fan status in the concentrator such that, when at
                least one fan unit is faulty, this object will have the
                value faulty(2)."
        ::= { env 4 }



--
-- Static Summaries
--

staticSummary OBJECT IDENTIFIER ::= { modules 12 }

staticSummaryTable OBJECT-TYPE
        SYNTAX  SEQUENCE OF StaticSummaryEntry
        ACCESS  not-accessible
        STATUS  mandatory
        DESCRIPTION
                "A table for retrieving predefined collections
                of MIB objects as a single field of octets.  This
                table is read-only:  all the entries are created
                by the agent.

                The purpose of this table is to replace the
                modSummaryTable.  It can support changes in
                the MIB structure and new types of variables as
                they are added in the future.  This is accomplished
                by returning the OID of each item included in the
                summary, along with the summarized values.

                Each entry in this table summarizes important
                information concerning the configuration and status
                of a slot/subslot. This information is a summary of
                the objects in the modules branch.

                No entry in this table exists for an empty slot."
        ::= { staticSummary 1 }

staticSummaryEntry OBJECT-TYPE
        SYNTAX  StaticSummaryEntry
        ACCESS  not-accessible
        STATUS  mandatory
        DESCRIPTION
                "A predefined collection of MIB objects whose
                values can be retrieved as a single field."
        INDEX   { ssSlotIndex, ssSubSlotIndex }
        ::= { staticSummaryTable 1 }

StaticSummaryEntry ::=
        SEQUENCE {
                ssSlotIndex            INTEGER,
                ssSubSlotIndex         INTEGER,
                ssValues               OCTET STRING
                }

ssSlotIndex OBJECT-TYPE
        SYNTAX  INTEGER
        ACCESS  read-only
        STATUS  mandatory
        DESCRIPTION
                "The slot number of the slot to which this
                entry pertains."
        ::= { staticSummaryEntry 1 }

ssSubSlotIndex OBJECT-TYPE
        SYNTAX  INTEGER
        ACCESS  read-only
        STATUS  mandatory
        DESCRIPTION
                "The subslot number to which this entry pertains.
                It is associated with a slot number. Motherboards are
                always located in subslot one, (e.g. <slot>.1). However,
                daughter cards can reside on any subslot within the range
                (2 ... 8), (e.g. <slot>.<2 .. 8>)."
        ::= { staticSummaryEntry 2 }

ssValues OBJECT-TYPE
        SYNTAX  OCTET STRING
        ACCESS  read-only
        STATUS  mandatory
        DESCRIPTION
                "The OIDs and values of the objects to be summarized,
                given as an octet string in the 'New Summary' format.

                        NEW_SUMMARY DEFINITION ::= BEGIN

                        IMPORTS TimeTicks FROM RFC1155-SMI;

                        Message ::= CHOICE OF {
                                Message_0
                        }

                        Message_0 ::= [0] IMPLICIT SEQUENCE {
                                timeStamp TimeTicks,
                                containments   CONTAINMENTS
                        }

                        CONTAINMENTS ::= SEQUENCE OF CONTAINMENT

                        CONTAINMENT ::= SEQUENCE {
                                prefix         OID,             -- Base OID
                                blocks         BLOCKS
                        }

                        BLOCKS ::= SEQUENCE OF BLOCK

                        BLOCK ::= SEQUENCE {
                                suffix  SUFFIX,
                                values  VALUES
                        }

                        SUFFIX ::= CHOICE OF {
                                SEQUENCE OF INTEGER, -- Indicies (i.e. slot.port)
                                NULL
                        }

                        VALUES ::= SEQUENCE OF VALUE

                        VALUE ::= SEQUENCE {
                                attribute       INTEGER,
                                data      DATA
                        }

                        DATA ::= CHOICE OF {
                                INTEGER,
                                OCTET STRING,
                                TimeTicks
                        }

                        END"
        ::= { staticSummaryEntry 3 }

ssLastChangedTable OBJECT-TYPE
        SYNTAX  SEQUENCE OF SsLastChangedEntry
        ACCESS  not-accessible
        STATUS  mandatory
        DESCRIPTION
                "A table of timestamps each indicating the change
                state of the corresponding information contained
                in the staticSummaryTable.

                This table contains a fixed number
                of entries, one for each possible subslot in
                each possible slot in the concentrator, regardless
                of whether the slot or subslot is occupied.  For
                example, for an IBM 8260 concentrator, this table
                has 19 x 8 entries; for an Hub concentrator, which
                has no subslots, this table has either 5 or 17 entries,
                and the subslot index of each entry is 1.

                (Note that the number of subslot entries in this table
                is determined by the type of concentrator, not the type
                of module; for an Hub module in an IBM 8260
                concentrator, there will still be 8 subslot entries.)"
        ::= { staticSummary 2 }

ssLastChangedEntry OBJECT-TYPE
        SYNTAX  SsLastChangedEntry
        ACCESS  not-accessible
        STATUS  mandatory
        DESCRIPTION
                "An entry for a particular slot/subslot address in
                the concentrator, indicating the value of SysUpTime
                at the time of the last detected change to any of
                the information included in the corresponding
                staticSummaryEntry instance."
        INDEX   { ssTlcSlotIndex, ssTlcSubSlotIndex }
        ::= { ssLastChangedTable 1 }

SsLastChangedEntry ::=
        SEQUENCE {
                ssTlcSlotIndex          INTEGER,
                ssTlcSubSlotIndex       INTEGER,
                ssTlcCurrentlyOccupied  INTEGER,
                ssTimeLastChanged       TimeTicks
                }

ssTlcSlotIndex OBJECT-TYPE
        SYNTAX  INTEGER
        ACCESS  read-only
        STATUS  mandatory
        DESCRIPTION
                "The number of the slot to which this entry pertains."
        ::= { ssLastChangedEntry 1 }

ssTlcSubSlotIndex OBJECT-TYPE
        SYNTAX  INTEGER
        ACCESS  read-only
        STATUS  mandatory
        DESCRIPTION
                "The subslot number to which this entry pertains.
                For Hub concentrators, there is a single entry
                for each slot, with a subslot number of 1.
                For IBM 8260 concentrators, the number 1 indicates
                the motherboard, and daughterboards are numbered
                beginning with subslot 2."
        ::= { ssLastChangedEntry 2 }

ssTlcCurrentlyOccupied OBJECT-TYPE
        SYNTAX  INTEGER {
            empty(1),
            occupied(2)
            }
        ACCESS  read-only
        STATUS  mandatory
        DESCRIPTION
                "The current configuration state of this slot/
                subslot.  Whether occupied or not, the
                ssTimeLastChanged field is still valid:  if a
                slot/subslot is unoccupied, the timestamp indicates
                the time that the module was removed.  If no module
                has occupied this slot/subslot since the last
                restart of the agent, the value of ssTimeLastChanged
                for this entry is zero."
        ::= { ssLastChangedEntry 3 }

ssTimeLastChanged OBJECT-TYPE
        SYNTAX  TimeTicks
        ACCESS  read-only
        STATUS  mandatory
        DESCRIPTION
                "The value of SysUpTime at the time that the
                last change was detected to any of the information
                included in the summary table entry for this slot
                and subslot.  A change in the value of this object
                signals the management station to re-get the
                corresponding summary information."
        ::= { ssLastChangedEntry 4 }

ssLastChangedSummary OBJECT-TYPE
        SYNTAX OCTET STRING
        ACCESS read-only
        STATUS mandatory
        DESCRIPTION
                "This object contains the value of ssTimeLastChanged for
                each slot/subslot in the concentrator. The first two
                octets contain the version of this object. The data
                following the version begins with the first slot and
                all of its sub-slots before continuing with the next slot."
        ::= { staticSummary 3 }


--
-- IBM 8260 Power Group
--
-- This group is used for managing the
-- power in the IBM 8260 hub.

--
-- Hub power mode
--
ocPowerModeAdminStatus OBJECT-TYPE
        SYNTAX INTEGER {
                fault-tolerant(1),
                not-fault-tolerant(2)
                }
        ACCESS read-write
        STATUS mandatory
        DESCRIPTION
                "The current desired state of hub power fault-tolerant
                mode.  Setting this object to fault-tolerant(1) will
                reserve one power supply's worth of power from the power
                budget for fault-tolerant operation, provided sufficient
                power is available.  Setting this object to
                not-fault-tolerant(2) returns the reserved power to the
                power budget."
        ::= { ocPowerControl 1 }

ocPowerModeOperStatus OBJECT-TYPE
        SYNTAX INTEGER {
                fault-tolerant(1),
                not-fault-tolerant(2)
                }
        ACCESS read-only
        STATUS mandatory
        DESCRIPTION
                "The current operational status of hub power fault-tolerant
                mode."
        ::= { ocPowerControl 2 }

ocPowerOverheatPowerDownMode OBJECT-TYPE
        SYNTAX INTEGER {
                enable(1),
                disable(2)
                }
        ACCESS read-only
        STATUS mandatory
        DESCRIPTION
                "The current desired state of hub overheat automatic power-
                down mode. The value enable(1) causes slots containing IBM 8260
                modules to be automatically power-disabled during a hub
                overheat condition. The value disable(2) causes no action
                to be taken when a hub overheat condition occurs."
        ::= { ocPowerControl 3 }

--
--  Hub backplane power
--
ocPowerOutputTable OBJECT-TYPE
        SYNTAX SEQUENCE OF OcPowerOutputEntry
        ACCESS not-accessible
        STATUS mandatory
        DESCRIPTION
                "A table that contains information about the hub power
                budget.  This table is indexed by voltage line type, each
                of which is supplied by the operational power supplies."
        ::= { ocPower 2 }

ocPowerOutputEntry OBJECT-TYPE
        SYNTAX OcPowerOutputEntry
        ACCESS not-accessible
        STATUS mandatory
        DESCRIPTION
                "A list of information about the hub power budget."
        INDEX { ocPowerOutputType }
        ::= { ocPowerOutputTable 1 }

OcPowerOutputEntry ::=
        SEQUENCE {
                ocPowerOutputType
                        INTEGER,
                ocPowerOutputVoltageLevel
                        Gauge,
                ocPowerOutputWattageCapacity
                        Gauge,
                ocPowerOutputWattageConsumed
                        Gauge,
                ocPowerOutputWattageAvailable
                        Gauge,
                ocPowerOutputUnmanagedWattageAlloc
                        Gauge
                }

ocPowerOutputType OBJECT-TYPE
        SYNTAX INTEGER {
                plusFiveVolt(1),        -- + 5 Volt
                minusFiveVolt(2),       -- - 5 Volt
                plusTwelveVolt(3),      -- +12 Volt
                minusTwelveVolt(4),     -- -12 Volt
                plusTwoVolt(5)          -- + 2 Volt
                }
        ACCESS  read-only
        STATUS  mandatory
        DESCRIPTION
                "Identifies the power (voltage) line type for which this
                entry contains power budget information."
        ::= { ocPowerOutputEntry 1 }

ocPowerOutputVoltageLevel OBJECT-TYPE
        SYNTAX Gauge
        ACCESS read-only
        STATUS mandatory
        DESCRIPTION
                "In millivolts (1/1000 Volt), the actual voltage level
                for this voltage type as sensed on the backplane.  This
                voltage is supplied by all operational power supplies."
        ::= { ocPowerOutputEntry 2 }

ocPowerOutputWattageCapacity OBJECT-TYPE
        SYNTAX Gauge
        ACCESS read-only
        STATUS mandatory
        DESCRIPTION
                "In hundredths of a Watt (1/100 Watt), the maximum
                wattage for the voltage line that is output by all
                operational power supplies combined."
        ::= { ocPowerOutputEntry 3 }

ocPowerOutputWattageConsumed OBJECT-TYPE
        SYNTAX Gauge
        ACCESS read-only
        STATUS mandatory
        DESCRIPTION
                "In hundredths of a Watt (1/100 Watt), the wattage
                consumed by all hub modules.  For a given voltage line,
                this object's value is the sum total of the power
                consumed by the hub itself, the Controller Modules
                and all power-enabled slots containing IBM 8260 modules.
                If power fault-tolerant mode is enabled (when it was
                previously disabled), this object's value is increased
                by the amount of power reserved for the voltage line.
                If power fault-tolerant mode is disabled (when it was
                previously enabled), this object's value is decreased
                by the amount of power that is returned to the available
                power budget for the voltage line."
        ::= { ocPowerOutputEntry 4 }

ocPowerOutputWattageAvailable OBJECT-TYPE
        SYNTAX Gauge
        ACCESS read-only
        STATUS mandatory
        DESCRIPTION
                "In hundredths of a Watt (1/100 Watt), the wattage
                available to power-up modules.  If power fault-tolerant
                mode is enabled (when it was previously disabled), this
                object's value is decreased by the amount of power reserved
                for the voltage line.  If power fault-tolerant mode is
                disabled (when it was previously enabled), this object's
                value is increased by the amount of power that is returned
                to the available power budget for the voltage line."
        ::= { ocPowerOutputEntry 5 }

ocPowerOutputUnmanagedWattageAlloc OBJECT-TYPE
        SYNTAX Gauge
        ACCESS read-only
        STATUS mandatory
        DESCRIPTION
                "In hundredths of a Watt (1/100 Watt), the wattage
                reserved for modules that are not power-manageable.
                This value 0 is always returned."
        ::= { ocPowerOutputEntry 6 }

--
-- Module power configuration
--
ocPowerSlotTable OBJECT-TYPE
        SYNTAX SEQUENCE OF OcPowerSlotEntry
        ACCESS not-accessible
        STATUS mandatory
        DESCRIPTION
                "A table that contains power management information
                for each non-empty, payload slot in the hub.  Note
                that for multi-slot IBM 8260 modules, there is one point
                of power management contact and control.  Hence, only
                the leftmost slot is represented in this table."
        ::= { ocPower 3  }

ocPowerSlotEntry OBJECT-TYPE
        SYNTAX OcPowerSlotEntry
        ACCESS not-accessible
        STATUS mandatory
        DESCRIPTION
                "A list of power management information for each
                payload slot in the hub containing an 8260 module."
        INDEX { ocPowerSlotIndex }
        ::= { ocPowerSlotTable 1 }

OcPowerSlotEntry ::=
        SEQUENCE {
                 ocPowerSlotIndex
                        INTEGER,
                 ocPowerSlotClass
                        INTEGER,
                 ocPowerSlotAdminStatus
                        INTEGER,
                 ocPowerSlotOperStatus
                        INTEGER
                 }

ocPowerSlotIndex OBJECT-TYPE
        SYNTAX INTEGER
        ACCESS read-only
        STATUS mandatory
        DESCRIPTION
                "The unique slot number that identifies the module
                associated with this power entry."
        ::= { ocPowerSlotEntry 1 }

ocPowerSlotClass OBJECT-TYPE
        SYNTAX INTEGER {
                one(1),
                two(2),
                three(3),
                four(4),
                five(5),
                six(6),
                seven(7),
                eight(8),
                nine(9),
                ten(10)
                }
        ACCESS read-write
        STATUS mandatory
        DESCRIPTION
                "The current slot power class.  For a slot containing
                an IBM 8260 module, this object's value ranges from 1 to
                10, where 1 is the lowest power class and 10 is the
                highest power class.  Slots assigned higher power classes
                will be power-enabled before slots assigned lower power
                classes.  Similarly, slots assigned lower power classes
                will be power-disabled before slots assigned higher power
                classes. Power class can be used to establish an
                IBM 8260 module power-up and power-down priority scheme.
                Combined with slot location, slot power class defines the
                order in which slots containing IBM 8260 modules will be
                power-enabled and power-disabled.  For a given power class,
                slots are power-enabled from lowest payload slot to highest
                payload slot and power-disabled from highest payload slot
                to lowest payload slot.  Slot power class is not pre-emptive;
                changing a slot's power class will not affect the power
                state of other slots.  It will take effect during a slot
                power-up or power-down event (e.g., the failure or recovery
                of a power supply)."
        ::= { ocPowerSlotEntry 2 }

ocPowerSlotAdminStatus OBJECT-TYPE
        SYNTAX  INTEGER {
                enable(1),  -- enable slot power
                disable(2)  -- disable slot power
                }
        ACCESS read-only
        STATUS mandatory
        DESCRIPTION
                "The current desired slot power state.  For a slot
                containing an IBM 8260 module, the value enable(1) causes the
                module to be power-enabled, provided sufficient power is
                available. The value disable(2) causes the module to be
                power-disabled and is not allowed for a slot containing the
                IBM 8260 agent, to prevent the user from losing hub
                manageability. The slot will not receive power untill this
                object is set to the the value enable(1)."
        ::= { ocPowerSlotEntry 3 }

ocPowerSlotOperStatus OBJECT-TYPE
        SYNTAX INTEGER {
                enabled(1),             -- Slot power is enabled
                disabled(2),            -- Slot power is disabled
                insufficient-power(3),  -- Slot power up not possible
                enabled-always(4)       -- Slot power is enabled always
                }
        ACCESS read-only
        STATUS mandatory
        DESCRIPTION
                "The current operational slot power status.  This object
                will have the value enabled(1), if the slot contains an
                IBM 8260 module and is actually power-enabled.  This object
                will have the value disabled(2), if the slot contains an
                IBM 8260 module and is actually power-disabled.  In this case,
                the slot is ineligible for power until ocPowerSlotAdminStatus
                for the slot is set to enable(1).  This object will have
                the value insufficient-power(3), if the slot is eligible to
                receive power but, due to power constraints, is not
                power-enabled.  When sufficient power becomes available, the
                slot will become power-enabled, and this object will then have
                the value enabled(1).  This object will have the value
                enabled-always(4) for a slot containing the IBM 8260 agent.
                For the slot containing the IBM 8260 agent, ocPowerSlotAdminStatus
                cannot be set to the value disable(2).  However, in the event of
                an environmental change such as a power supply failure, the slot
                containing the IBM 8260 agent may be automatically power-disabled,
                and this object will then have the value insufficient-power(3).
                This is based on the value of ocPowerSlotClass for the slot."
        ::= { ocPowerSlotEntry 4 }

--
-- IBM 8260 Inventory Group
--
-- This group reflects inventory information about
-- components in the IBM 8260 hub.
--

--
-- Hub chassis information
--
ocInvHubType OBJECT-TYPE
        SYNTAX DisplayString (SIZE(1..32))
        ACCESS read-only
        STATUS mandatory
        DESCRIPTION
                "The hub type (i.e. model number) of the hub.  An instance
                for which information is not valid will return 'invalid
                EEPROM!'."
        ::= { ocInvHub 1 }

ocInvHubSerialNo OBJECT-TYPE
        SYNTAX DisplayString (SIZE(1..32))
        ACCESS read-only
        STATUS mandatory
        DESCRIPTION
                "The serial number of the hub.  An instance for which
                information is not valid will return 'invalid EEPROM!'."
        ::= { ocInvHub 2 }

ocInvHubHWVer OBJECT-TYPE
        SYNTAX DisplayString (SIZE(1..32))
        ACCESS read-only
        STATUS mandatory
        DESCRIPTION
                "The revision number of the hardware of the hub.  An instance
                for which information is not valid will return 'invalid
                EEPROM!'."
        ::= { ocInvHub 3 }

ocInvHubMfr OBJECT-TYPE
        SYNTAX DisplayString (SIZE(1..32))
        ACCESS read-only
        STATUS mandatory
        DESCRIPTION
                "The company name that manufactured this hub.  An instance
                for which information is not valid will return 'invalid
                EEPROM!."
        ::= { ocInvHub 4 }

ocInvHubMfrDate OBJECT-TYPE
        SYNTAX DisplayString (SIZE(6))
        ACCESS read-only
        STATUS mandatory
        DESCRIPTION
                "The date in yymmdd format that this unit was manufactured.
                An instance for which information is not valid will return
                'invalid EEPROM!'."
        ::= { ocInvHub 5 }

ocInvHubNotePad OBJECT-TYPE
        SYNTAX DisplayString (SIZE(0..256))
        ACCESS read-only
        STATUS mandatory
        DESCRIPTION
                "Note pad area reserved for the hub.  This area
                contains information pertaining to the hub such as
                service or hardware upgrade information.  An instance
                for which information is not valid will return 'invalid
                EEPROM!'."
        ::= { ocInvHub 6 }


--
-- IBM 8260 Modules inventory information
--
-- Contains information about the hub modules. The modules
-- information are organized as a base-one matrix. That is, a module,
-- motherboard or daughter card, can be located by a pair of primitives:
-- slot index and subslot index (i.e. <slot>.<subslot>)
--
-- ocInvModTable
--
ocInvModTable OBJECT-TYPE
        SYNTAX SEQUENCE OF OcInvModEntry
        ACCESS not-accessible
        STATUS mandatory
        DESCRIPTION
                "A list of inventory information related to a module,
                indexed with respect to slot and subslot location numbers."
        ::= { ocInvMods 1 }

ocInvModEntry OBJECT-TYPE
        SYNTAX OcInvModEntry
        ACCESS not-accessible
        STATUS mandatory
        DESCRIPTION
                "Values to describe a module inventory items."
        INDEX { ocInvModSlotIndex, ocInvModSubSlotIndex }
        ::= { ocInvModTable 1 }

OcInvModEntry ::=
        SEQUENCE {
                ocInvModSlotIndex
                        INTEGER,
                ocInvModSubSlotIndex
                        INTEGER,
                ocInvModModel
                        DisplayString,
                ocInvModSerialNo
                        DisplayString,
                ocInvModHWVer
                        DisplayString,
                ocInvModSWVer
                        DisplayString,
                ocInvModSWBootVer
                        DisplayString,
                ocInvModMfr
                        DisplayString,
                ocInvModMfrDate
                        DisplayString,
                ocInvModNotePad
                        DisplayString
                }

ocInvModSlotIndex OBJECT-TYPE
        SYNTAX INTEGER
        ACCESS read-only
        STATUS mandatory
        DESCRIPTION
                "The slot number where this Module is located."
        ::= { ocInvModEntry 1 }

ocInvModSubSlotIndex OBJECT-TYPE
        SYNTAX INTEGER
        ACCESS read-only
        STATUS mandatory
        DESCRIPTION
                "The subslot number where this Module is located.
                It is associated with a slot number. Motherboards are
                always located in subslot one, (e.g. <slot>.1). However,
                daughter cards can reside on any subslot within the range
                (2 ... 8), (e.g. <slot>.<2 .. 8>)."
        ::= { ocInvModEntry 2 }

ocInvModModel OBJECT-TYPE
        SYNTAX DisplayString (SIZE(1..32))
        ACCESS read-only
        STATUS mandatory
        DESCRIPTION
                "This Module model number.
                If the instance value is unknown, Hub will be returned."
        ::= { ocInvModEntry 3 }

ocInvModSerialNo OBJECT-TYPE
        SYNTAX DisplayString (SIZE(1..32))
        ACCESS read-only
        STATUS mandatory
        DESCRIPTION
                "This Module serial number.
                If the instance value is unknown, N/A will be returned."
        ::= { ocInvModEntry 4 }

ocInvModHWVer OBJECT-TYPE
        SYNTAX DisplayString (SIZE(1..32))
        ACCESS read-only
        STATUS mandatory
        DESCRIPTION
                "The revision number of the hardware on this module.
                If the instance value is unknown, N/A will be returned."
        ::= { ocInvModEntry 5 }

ocInvModSWVer OBJECT-TYPE
        SYNTAX DisplayString (SIZE(1..32))
        ACCESS read-only
        STATUS mandatory
        DESCRIPTION
                "The revision number of the software on this module.
                If the instance value is unknown, N/A will be returned."
        ::= { ocInvModEntry 6 }

ocInvModSWBootVer OBJECT-TYPE
        SYNTAX DisplayString (SIZE(1..32))
        ACCESS read-only
        STATUS mandatory
        DESCRIPTION
                "The revision number of the boot software on this module.
                If the instance value is unknown, N/A will be returned."
        ::= { ocInvModEntry 7 }

ocInvModMfr OBJECT-TYPE
        SYNTAX DisplayString (SIZE(1..32))
        ACCESS read-only
        STATUS mandatory
        DESCRIPTION
                "The company name that manufactured this module.
                If the instance value is unknown, N/A will be returned."
        ::= { ocInvModEntry 8 }

ocInvModMfrDate OBJECT-TYPE
        SYNTAX DisplayString (SIZE(0..6))
        ACCESS read-only
        STATUS mandatory
        DESCRIPTION
                "The date in yymmdd format that this module was manufactured.
                If the instance value is unknown, N/A will be returned."
        ::= { ocInvModEntry 9 }

ocInvModNotePad OBJECT-TYPE
        SYNTAX DisplayString (SIZE(0..256))
        ACCESS read-only
        STATUS mandatory
        DESCRIPTION
                "Note pad area reserved for the module.  This area
                contains information pertaining to the module such as
                service or hardware upgrade information.  If the instance
                value is unknown, N/A will be returned."
        ::= { ocInvModEntry 10 }


-- Chassis related Traps sent by the 8260 ATM agent.

-- Traps are defined using the conventions in RFC 1215.

chassisSlotDown TRAP-TYPE
        ENTERPRISE      node
        DESCRIPTION
                "This trap indicates that a module is down.
                Usually, this trap is sent when the module
                has been removed.

                Sometimes, this trap is sent when management communications
                with this module have been broken.  In this case, it may not
                be possible to distinguish between a removed and a failed
                module."
        ::= 102

chassisSlotUp TRAP-TYPE
        ENTERPRISE      node
        DESCRIPTION
                "This trap indicates that a module is up.
                Usually, this trap is sent when the module is
                inserted into the hub.

                Sometimes, this trap is sent when management communications
                have been restored to a module where they had previously
                been broken."
        ::= 103

chassisEnvironment TRAP-TYPE
        ENTERPRISE      node
        DESCRIPTION
                "A chassisEnvironment trap indicates a change in the
                concentrator's environment has occurred.  The variables
                supplied indicate what exactly changed."
        ::= 104

chassisChange TRAP-TYPE
        ENTERPRISE      node
        DESCRIPTION
                "A chassisChange trap is used to indicate that a configuration
                change has occurred.  The actual variables that changed
                are included in the variables section of the PDU."
        ::= 107

chassisModuleDown TRAP-TYPE
        ENTERPRISE      node
        DESCRIPTION
                "A chassisModuleDown trap indicates that management communications
                with a slot has been
                broken.  This event usually occurs when a module has been
                physically removed from the concentrator.  However, it
                is possible for this event to occur when the particular
                module fails."
        ::= 116

chassisModuleUp TRAP-TYPE
        ENTERPRISE      node
        DESCRIPTION
                "A chassisModuleUp trap indicates that management communications
                with a slot has been
                established.  This event usually occurs when a module has
                physically been inserted into the concentrator.  The
                variable chipModType indicates the module type inserted."
        ::= 117


--
--  Proxy management
--
proxy OBJECT IDENTIFIER ::= { atmSw 6 }

--
-- Ports of the device managed by the atm subsystem proxy
-- agent
--
proxyPortTable OBJECT-TYPE
        SYNTAX  SEQUENCE OF ProxyPortEntry
        ACCESS  not-accessible
        STATUS  mandatory
        DESCRIPTION
                "The table of the ports of the attached device.
                 There is one entry per port in the attached device
                 managed by the proxy agent in the atm subsystem."
        ::= { proxy 1}

proxyPortEntry OBJECT-TYPE
        SYNTAX  ProxyPortEntry
        ACCESS  not-accessible
        STATUS  mandatory
        DESCRIPTION
                "Entries of the proxyPortTable.
                 Each entry corresponds to a port that belongs
                 to the attached device."
        INDEX { proxyId, portNumber }
        ::= { proxyPortTable 1 }

ProxyPortEntry ::= SEQUENCE {
        proxyId
              INTEGER,
        portNumber
              INTEGER,
        portOperState
              INTEGER,
        portPhysAddress
            MacAddress
        }

proxyId OBJECT-TYPE
        SYNTAX  INTEGER
        ACCESS  read-only
        STATUS  mandatory
        DESCRIPTION
                "The identifier of the proxy agent in the atm subsystem
                 managing this attached device and its ports."
        ::= { proxyPortEntry 1 }

portNumber OBJECT-TYPE
        SYNTAX  INTEGER
        ACCESS  read-only
        STATUS  mandatory
        DESCRIPTION
                "The identifier of the port in the attached device."
        ::= { proxyPortEntry 2 }

portOperState OBJECT-TYPE
        SYNTAX  INTEGER { normal (0),
                          transientError (1),
                          fatalError (2)
                        }

        ACCESS  read-only
        STATUS  mandatory
        DESCRIPTION
                "The operational state of the port in the attached
                 device."
        ::= { proxyPortEntry 3 }


portPhysAddress OBJECT-TYPE
    SYNTAX  MacAddress
    ACCESS  read-only
    STATUS  mandatory
    DESCRIPTION
           "The physical address associated to this
            port."
    ::= { proxyPortEntry 4 }


--
--  Experimental group
--   This group is dedicated to the management of the ressources
--   not yet standardized.
--
experimental OBJECT IDENTIFIER ::= { atmSw 7 }

   -- ****************************************************
   -- ATM Interface Signalling Table
   --
   -- This table contains signalling entity configuration
   --       from atommib-atm1ng-01.txt ietf draft
   -- ****************************************************


atmSigTable       OBJECT-TYPE
        SYNTAX       SEQUENCE OF AtmSigEntry
        ACCESS       not-accessible
        STATUS       mandatory
        DESCRIPTION
         "This table contains ATM local interface
          configuration parameters, one entry per ATM
          signalling interface."
        ::= { experimental   1 }

atmSigEntry         OBJECT-TYPE
        SYNTAX         AtmSigEntry
        ACCESS         not-accessible
        STATUS         mandatory
        DESCRIPTION
         "This list contains signalling configuration
          parameters and state variables."
        INDEX { ifIndex }
        ::= { atmSigTable  1}

AtmSigEntry    ::= SEQUENCE  {
        atmConfigSigType            AtmSignallingType,
        atmActualSigType            AtmSignallingType,
        atmConfigSigSide            INTEGER,
        atmActualSigSide            INTEGER
             }

atmConfigSigType     OBJECT-TYPE
       SYNTAX  INTEGER  {
                 other(1),
                 autoConfig(2),
                 ituDss2(3),
                 atmfUni3Dot0(4),
                 atmfUni3Dot1(5),
                 atmfUni4Dot0(6),
                 atmfIispUni3Dot0(7),
                 atmfIispUni3Dot1(8),
                 atmfIispUni4Dot0 (9),
                 atmfPnni1Dot0(10),
                 atmfBici2Dot0(11)  }
        ACCESS        read-write
        STATUS        mandatory
        DESCRIPTION
          "The type of signalling that is configured for the
          interface.  Setting this variable to a value of
          'other' is not allowed."
       DEFVAL { autoConfig }
       ::= { atmSigEntry 1 }

atmActualSigType     OBJECT-TYPE
       SYNTAX  INTEGER  {
                 other(1),
                 autoConfig(2),
                 ituDss2(3),
                 atmfUni3Dot0(4),
                 atmfUni3Dot1(5),
                 atmfUni4Dot0(6),
                 atmfIispUni3Dot0(7),
                 atmfIispUni3Dot1(8),
                 atmfIispUni4Dot0 (9),
                 atmfPnni1Dot0(10),
                 atmfBici2Dot0(11)  }
       ACCESS          read-only
       STATUS          mandatory
       DESCRIPTION
         "The type of signalling that is currently being used
         on the interface.  This may reflect a manually
         configured value for the signalling type, or may be
         determined by other means such as auto-configuration.
         A value of `autoConfig' indicates that auto-
         configuration was requested but has not yet been
         completed."
      ::= { atmSigEntry 2 }

atmConfigSigSide     OBJECT-TYPE
      SYNTAX       INTEGER  {
                   other(1),
                   user(2),
                   network(3) }
      ACCESS       read-write
      STATUS       mandatory
      DESCRIPTION
        "The role of this signalling entity.  This value
        does not apply when atmConfigSigType is set
        to `autoConfig', `atmfPnni1Dot0', or
        `atmfBici2Dot0'."
     ::= { atmSigEntry 3}

atmActualSigSide     OBJECT-TYPE
     SYNTAX       INTEGER  {
                  other(1),
                  user(2),
                  network(3),
                  symmetric(4) }
     ACCESS       read-only
     STATUS       mandatory
     DESCRIPTION
       "The actual role of this signalling entity."
     ::= { atmSigEntry 4}

END
