-- MIB created 4/01/98 13:02:38, by
--   SMIC (the next generation) version 1.6.29, November 22, 1994.

FECLIENT827x-MIB DEFINITIONS ::= BEGIN

-- From file: "ibmMSSClient.mi2"
-- Compile options "G A T M"

IMPORTS
    Counter32, Integer32, IpAddress
            FROM SNMPv2-SMI-v1
    OBJECT-TYPE
            FROM RFC-1212
    TRAP-TYPE
            FROM RFC-1215
    proElsSubSysEventMsg
            FROM PROTEON-MIB
    ifIndex
            FROM RFC1213-MIB
    enterprises
            FROM RFC1155-SMI;

ibmMSSClientMIB OBJECT IDENTIFIER ::= { nwaysMSS 4 }
-- MODULE-IDENTITY
--  LastUpdated
--    9804011200Z
--  OrgName
--    IBM Corporation
--  ContactInfo
--     Florian K Kandefer
--       Postal:  IBM Corporation
--                800 Park Offices Drive
--                Research Triangle Park, NC 27709
--                US
--       Tel:     +1 919 254 0685
--       Fax:     +1 919 254 0391
--       E-mail:  kandefer@vnet.ibm.com     
--  Descr
--    
--    This MIB defines the enterprise specific management objects
--    for the IBM MSS Client and MSS Domain Client.
--  RevDate
--    9804011200Z
--  RevDescr
--    
--    The  creation

ibm             OBJECT IDENTIFIER ::= { enterprises 2 }
ibmProd         OBJECT IDENTIFIER ::= { ibm 6 }
nwaysMSS        OBJECT IDENTIFIER ::= { ibmProd 118 }
fe827xNotificationGroup OBJECT IDENTIFIER ::= { ibmMSSClientMIB 0 }
fe827xMIBObjectGroup OBJECT IDENTIFIER ::= { ibmMSSClientMIB 1 }
fe827xMIBConformanceGroup OBJECT IDENTIFIER ::= { ibmMSSClientMIB 2 }
fe827xProdGroup OBJECT IDENTIFIER ::= { fe827xMIBObjectGroup 1 }
fe827xPCIAdapterGroup OBJECT IDENTIFIER ::= { fe827xMIBObjectGroup 2 }
fe827xStatGroup OBJECT IDENTIFIER ::= { fe827xMIBObjectGroup 3 }
fe827xSwitchGroup OBJECT IDENTIFIER ::= { fe827xMIBObjectGroup 4 }
feMIBGroups     OBJECT IDENTIFIER ::= { fe827xMIBConformanceGroup 1 }
feMIBCompliances OBJECT IDENTIFIER ::= { fe827xMIBConformanceGroup 2 }

fe827xResetFlag OBJECT-TYPE
    SYNTAX INTEGER {
        noreset(1),
        reboot(2)
        }
    ACCESS read-write
    STATUS mandatory
    DESCRIPTION
        "The flag that controls the reset process in this blade.
         This variable shall assume a value of noreset(1) in
        the absence of a request for a reset from the management
        application. This variable shall assume a value of reboot(2)
        if the management application requests that this blade
        execute a complete hardware reboot which reloads the code
        load from storage."
    DEFVAL { noreset }
    ::= { fe827xProdGroup 1 }

fe827xDRAMInstalled OBJECT-TYPE
    SYNTAX Integer32
    ACCESS read-only
    STATUS mandatory
    DESCRIPTION
        "The total amount of dynamic RAM installed on this
        blade. The amount is in units of megabytes."
    ::= { fe827xProdGroup 2 }

fe827xCacheInstalled OBJECT-TYPE
    SYNTAX Integer32
    ACCESS read-only
    STATUS mandatory
    DESCRIPTION
        "The total amount of Cache memory installed on this
        blade. The amount is in units of Kbytes. This value
        is obtained from the card version level. Version 1
        cards will have 256 Kbytes."
    ::= { fe827xProdGroup 3 }

fe827xFlashInstalled OBJECT-TYPE
    SYNTAX Integer32
    ACCESS read-only
    STATUS mandatory
    DESCRIPTION
        "The total amount of Flash memory installed on this blade.
         The amount is in units of Mbytes. This value
        is obtained from the Generic Status Register."
    ::= { fe827xProdGroup 4 }

fe827xSRAMInstalled OBJECT-TYPE
    SYNTAX Integer32
    ACCESS read-only
    STATUS mandatory
    DESCRIPTION
        "The total amount of SRAM installed on this blade. The
         amount is in units of Mbytes. This value is obtained
         indirectly by reading MIMIC adapter version in the UFIC
         adapter ID register. Version 1 will have 1 Mbytes."
    ::= { fe827xProdGroup 5 }

fe827xNotifyStatus OBJECT-TYPE
    SYNTAX INTEGER {
        enabled(1),
        disabled(2)
        }
    ACCESS read-write
    STATUS mandatory
    DESCRIPTION
        "The status of the trap reporting service in this MSS Client or
        MSS Domain Client variable shall assume a value of enabled(1)
        if this MSS Client or MSS Domain Client is permitted to send traps.
        This variable shall assume a value of disabled(2) if this
        MSS Client or MSS Domain Client is prohibited from sending traps."
    DEFVAL { enabled }
    ::= { fe827xProdGroup 6 }

fe827xSwitchIPAddr OBJECT-TYPE
    SYNTAX IpAddress
    ACCESS read-only
    STATUS mandatory
    DESCRIPTION
        "
        This is the IP address of the switch that the MSS Client or
        MSS Domain Client is plugged into."
    ::= { fe827xProdGroup 7 }

fe827xSwitchSlotNum OBJECT-TYPE
    SYNTAX Integer32
    ACCESS read-only
    STATUS mandatory
    DESCRIPTION
        "
        This is the slot number of the switch that the MSS Client or
        MSS Domain Client is plugged into."
    ::= { fe827xProdGroup 8 }

fe827xSwitchPortNum OBJECT-TYPE
    SYNTAX Integer32
    ACCESS read-only
    STATUS mandatory
    DESCRIPTION
        "
        This is the switch port number that the MSS Client or
        MSS Domain Client is associated with."
    ::= { fe827xProdGroup 9 }

fe827xPCINumSlot OBJECT-TYPE
    SYNTAX Integer32
    ACCESS read-only
    STATUS mandatory
    DESCRIPTION
        "The number of PCI adapter slots available for this blade.
         At present this would assume a value 1, since there can
         be only one PCI adapter for the MSS Client. This value is zero for
         the MSS Domain Client since it does not support PCI adapters."
    ::= { fe827xPCIAdapterGroup 1 }

fe827xPCIAdapTable OBJECT-TYPE
    SYNTAX SEQUENCE OF Fe827xPCIAdapEntry
    ACCESS not-accessible
    STATUS mandatory
    DESCRIPTION
        "A table of PCI adapters entries. The number of entries is
        given by the value of fe827xPCINumSlot. At present only
        one PCI adapter is supported by the MSS Client."
    ::= { fe827xPCIAdapterGroup 2 }

fe827xPCIAdapEntry OBJECT-TYPE
    SYNTAX Fe827xPCIAdapEntry
    ACCESS not-accessible
    STATUS mandatory
    DESCRIPTION
        "A PCI adapter entry containing objects to describe the
        operational aspects of the PCI adapter on this blade."
    INDEX { fe827xPCIAdapSlotNum }
    ::= { fe827xPCIAdapTable 1 }

Fe827xPCIAdapEntry ::= SEQUENCE {
    fe827xPCIAdapSlotNum Integer32,
    fe827xPCIAdapType INTEGER,
    fe827xPCIAdapConfigType INTEGER,
    fe827xPCIAdapATMMediaType INTEGER,
    fe827xPCIAdapOperStatus INTEGER,
    fe827xPCIAdapDiagStatus INTEGER,
    fe827xPCIAdapNetworkStatus INTEGER,
    fe827xPCIAdapFaultStatus INTEGER
    }

fe827xPCIAdapSlotNum OBJECT-TYPE
    SYNTAX Integer32
    ACCESS not-accessible
    STATUS mandatory
    DESCRIPTION
        "The relative slot location at which the adapter is attached to
        this blade.  At present slot is numbered as 1. This variable
        serves as the index for the 827xPCIAdapTable."
    ::= { fe827xPCIAdapEntry 1 }

fe827xPCIAdapType OBJECT-TYPE
    SYNTAX INTEGER {
        unknown(1),
        atm(2)
        }
    ACCESS read-only
    STATUS mandatory
    DESCRIPTION
        "The type of PCI adapter that is inserted into this slot.
        This variable shall assume a value of unknown(1) if the
        fe827xPCIAdapConfigType is notConfigured(1) or if the
        fe827xPCIAdapConfigType is atm(2) and the fe827xPCIAdapOperStatus
        has a value of unknown(1), notConfigured(2), notPresent(3),
        unavailable(4), does-not_apply(5) or missConfigured (10).
        The variable shall assume a value of atm(2) if the
        fe827xPCIAdapConfigType has a value of atm(2) and the
        fe827xPCIAdapOperStatus has a value of enabled-pending(6),
        enabled(7), disabled-pending(8) or disabled(9)."
    ::= { fe827xPCIAdapEntry 2 }

fe827xPCIAdapConfigType OBJECT-TYPE
    SYNTAX INTEGER {
        notConfigured(1),
        atm(2)
        }
    ACCESS read-only
    STATUS mandatory
    DESCRIPTION
        "The router configuration type for this slot. The variable
         shall assume a value of notConfigured(1) if no configuration
         exist for this slot. The variable shall assume a value of
         atm(2) if the slot is configured for an ATM adapter."
    ::= { fe827xPCIAdapEntry 3 }

fe827xPCIAdapATMMediaType OBJECT-TYPE
    SYNTAX INTEGER {
        unknown(1),
        smf(2),
        mmf(3)
        }
    ACCESS read-only
    STATUS mandatory
    DESCRIPTION
        "The type of fiber used by the ATM short PCI cards. The values
         for the media type could be Gemini or Multi-Mode Fiber mmf(2) and
         Meercat or Single Mode Fiber smf(3)."
    ::= { fe827xPCIAdapEntry 4 }

fe827xPCIAdapOperStatus OBJECT-TYPE
    SYNTAX INTEGER {
        unknown(1),
        notConfigured(2),
        notPresent(3),
        unavailable(4),
        doesNotApply(5),
        enablePending(6),
        enabled(7),
        disablePending(8),
        disabled(9),
        missConfigured(10)
        }
    ACCESS read-only
    STATUS mandatory
    DESCRIPTION
        "The operational status of this PCI adapter for the balde.
         The variable shall assume a value of unknown(1)
        if the adapter inserted in the slot cannot be recognized. The
        variable shall assume a value of notConfigured(2) if the adapter
        inserted in the slot is recognized but no router configuration
        exists. The variable shall assume a value of notPresent(3) if
        the adapter is not inserted in the slot but the router
        configuration exists. The variable shall assume a value of
        unavailable(4) if adapter inserted in the slot can not be used
        nor made ready to be used; for example, a hardware error. The
        variable shall assume a value of doesNotApply(5) if this adapter
        does not contain an operational state. The variable shall assume
        a value of enablePending(6) if commands have been issued to enable
        the adapter but have not been completed. The variable shall assume
        a value of enabled(7) if commands have been successfully issued
        to enable the adapter. The variable shall assume a value of
        disablePending(8) if commands have been issued to disable the
        adapter but have not been completed. The variable shall assume
        a value of disabled(9) if commands have been successfully issued
        to disable the adapter. The variable shall assume a value of
        missConfigured(10) if the adapter is inserted in the slot
        but the router configuration is of a different type. This object
        would also drive the Unit LED's."
    ::= { fe827xPCIAdapEntry 5 }

fe827xPCIAdapDiagStatus OBJECT-TYPE
    SYNTAX INTEGER {
        auto(1),
        inactive(2),
        idle(3),
        active(4)
        }
    ACCESS read-only
    STATUS mandatory
    DESCRIPTION
        "The diagnostic status of this PCI adapter for the blade.
         The variable shall assume a value of auto(1) if
        commands have been issued by the system to determine the status
        of the adapter; for example, at initialization. The variable shall
        assume a value of inactive(2) if the adapter is not currently
        running any diagnostics. The variable shall assume a value
        of idle(3) if the adapter is in the disabled operational state
        ready to run the diagnostics. The variable shall assume a value
        of active(4) if commands have been issued by the user to
        run the diagnostics."
    ::= { fe827xPCIAdapEntry 6 }

fe827xPCIAdapNetworkStatus OBJECT-TYPE
    SYNTAX INTEGER {
        unknown(1),
        up(2),
        down(3),
        testing(4),
        doesNotApply(5)
        }
    ACCESS read-only
    STATUS mandatory
    DESCRIPTION
        "The network status of this PCI adapter in this blade
         The variable shall assume a value of up(1) if the adapter
        is connected to the network. The variable shall assume a value
        of down(3) if the adapter can not verify a network connection.
        The variable shall assume a value of testing(4) if the
        adapter is running tests for the network connection. The
        variable shall assume a value of unknown(1) if network status
        can not be determined. The variable shall assume a value of
        doesNotApply(5) if the adapter does not contain a network
        state."
    ::= { fe827xPCIAdapEntry 7 }

fe827xPCIAdapFaultStatus OBJECT-TYPE
    SYNTAX INTEGER {
        unknown(1),
        noFault(2),
        isolated(3),
        nonIsolated(4)
        }
    ACCESS read-only
    STATUS mandatory
    DESCRIPTION
        "The fault status of this PCI adapter in this blade.
        The variable shall assume a value of noFault(2)
        if no fault that is associated with this adapter has been
        detected. The variable shall assume a value of isolated(3) if this
        fault that can be isolated on the adapter itself. The variable
        shall assume a value of nonIsolated(4) if the fault
        can not isolated on the adapter or in the network.
        The variable shall assume a value of unknown(1) if the
        fault status has not been determined; for example, at
        initialization. This object would drive the port LED's also.
        status noFault(2) indicates LED green other values indicate
        port LED yellow."
    ::= { fe827xPCIAdapEntry 8 }

fe827xStatTable OBJECT-TYPE
    SYNTAX SEQUENCE OF Fe827xStatEntry
    ACCESS not-accessible
    STATUS mandatory
    DESCRIPTION
        "A table of the statistics for each queue on the MSS Client or
        MSS Domain Client."
    ::= { fe827xStatGroup 1 }

fe827xStatEntry OBJECT-TYPE
    SYNTAX Fe827xStatEntry
    ACCESS not-accessible
    STATUS mandatory
    DESCRIPTION
        "A statistic entry containing objects to describe the
         aspects of the queue's on the MSS Client or MSS Domain Client."
    INDEX { fe827xStatQueueNum }
    ::= { fe827xStatTable 1 }

Fe827xStatEntry ::= SEQUENCE {
    fe827xStatQueueNum Integer32,
    fe827xStatFramesSent Counter32,
    fe827xStatFramesReceived Counter32
    }

fe827xStatQueueNum OBJECT-TYPE
    SYNTAX Integer32
    ACCESS not-accessible
    STATUS mandatory
    DESCRIPTION
        "The queue number on the Forwarding Engine. This variable
        serves as the index for the fe827xStatTable."
    ::= { fe827xStatEntry 1 }

fe827xStatFramesSent OBJECT-TYPE
    SYNTAX Counter32
    ACCESS read-only
    STATUS mandatory
    DESCRIPTION
        "A count of frames sent on the queue."
    ::= { fe827xStatEntry 2 }

fe827xStatFramesReceived OBJECT-TYPE
    SYNTAX Counter32
    ACCESS read-only
    STATUS mandatory
    DESCRIPTION
        "A count of frames received on the queue."
    ::= { fe827xStatEntry 3 }

fe827xDomainIfTable OBJECT-TYPE
    SYNTAX SEQUENCE OF Fe827xDomainIfEntry
    ACCESS not-accessible
    STATUS mandatory
    DESCRIPTION
        "A table for mapping MSS Client or MSS Domain Client interface numbers
        
        to Switch Domain numbers."
    ::= { fe827xSwitchGroup 1 }

fe827xDomainIfEntry OBJECT-TYPE
    SYNTAX Fe827xDomainIfEntry
    ACCESS not-accessible
    STATUS mandatory
    DESCRIPTION
        "Each entry maps a single MSS Client or MSS Domain Client
        interface number to a single Switch
        Domain numbers."
    INDEX { ifIndex }
    ::= { fe827xDomainIfTable 1 }

Fe827xDomainIfEntry ::= SEQUENCE {
    fe827xSwitchDomainNum Integer32
    }

fe827xSwitchDomainNum OBJECT-TYPE
    SYNTAX Integer32
    ACCESS read-only
    STATUS mandatory
    DESCRIPTION
        "
        Switches Domain Number associated with this MSS Client or
        MSS Domain Client Interface Number."
    ::= { fe827xDomainIfEntry 1 }

fe827xPCIAdapStatusChg TRAP-TYPE
-- Reverse mappable trap
    ENTERPRISE ibmMSSClientMIB
    VARIABLES {
        fe827xPCIAdapConfigType, fe827xPCIAdapOperStatus, 
        fe827xPCIAdapDiagStatus, fe827xPCIAdapNetworkStatus, 
        fe827xPCIAdapFaultStatus }
--  Status
--    mandatory
    DESCRIPTION
        "The trap announces a change in the status of the PCI adapter.
        It shall be sent if the value of either fe827xPCIAdapOperType,
        fe827xPCIAdapDiagStatus, fe827xPCIAdapNetworkStatus,
        or fe827xPCIAdapFaultStatus changes and fe827xNotifyStatus
        has a value of enabled(1)."
    ::= 1

feGroup OBJECT IDENTIFIER ::= { feMIBGroups 1 }
-- OBJECT-GROUP
--  Status
--    mandatory
--  Descr
--    
--    These are all the MSS Client or MSS Domain Client MIB objects
--  objects
--    fe827xResetFlag, fe827xDRAMInstalled, fe827xCacheInstalled, 
--    fe827xFlashInstalled, fe827xSRAMInstalled, fe827xPCIAdapType, 
--    fe827xPCIAdapConfigType, fe827xPCIAdapATMMediaType, 
--    fe827xPCIAdapOperStatus, fe827xPCIAdapDiagStatus, 
--    fe827xPCIAdapNetworkStatus, fe827xPCIAdapFaultStatus, 
--    fe827xStatQueueNum, fe827xStatFramesSent, 
--    fe827xStatFramesReceived

feMIBCompliance OBJECT IDENTIFIER ::= { feMIBCompliances 1 }
-- MODULE-COMPLIANCE
--  Status
--    mandatory
--  Descr
--    The compliance statement for MSS Client or MSS Domain Client 
--  Module
--    >>current<<
--   OptGroup
--    feGroup


END
