RMONitor-MIB DEFINITIONS ::= BEGIN

        IMPORTS

                DisplayString        FROM RFC1158-MIB
                enterprises          FROM RFC1155;

                  -- textual conventions

                  OwnerString ::= DisplayString
                  -- This data type is used to model an administratively
                  -- assigned name of the owner of a resource. This
                  -- information is taken from the ASCII character set.
                  -- It is suggested that this name contain one or more
                  -- of the following:
                  -- IP address, management station name, network manager's
                  -- name, location, or phone number.
                  -- In some cases the agent itself will be the owner of
                  -- an entry.  In these cases, this string shall be set
                  -- to a string starting with 'monitor'.
                  -- SNMP access control is articulated entirely in terms of
                  -- the contents of MIB views; access to a particular SNMP
                  -- object instance depends only upon its presence or
                  -- absence in a particular MIB view and never upon its
                  -- value or the value of related object instances. Thus,
                  -- objects of this type afford resolution of resource
                  -- contention only among cooperating managers; they
                  -- realize no access control function with respect
                  -- to uncooperative parties.
                  --
                  -- By convention, objects with this syntax are declared
                  -- as having
                  --
                  --      SIZE (0..127)

                EntryStatus ::= INTEGER
                {
                        valid(1),
                        createRequest(2),
                        underCreation(3),
                        invalid(4)
                }


                ibm                   OBJECT IDENTIFIER ::= { enterprises 2 }
                mib-2           OBJECT IDENTIFIER ::= { iso(1) org(3) dod(6) internet(1) mgmt(2) 1 }
                ibmProd         OBJECT IDENTIFIER ::= { ibm 6 }
                rmonitor            OBJECT IDENTIFIER ::= { ibmProd 45 }
                security                OBJECT IDENTIFIER ::= { rmonitor 1 }
                protocols               OBJECT IDENTIFIER ::= { rmonitor 2 }


                -- The Security Group
                --
                -- The Security group provides the authentication scheme for the
                -- IBM RMONitor Agent for OS/2 product.

                -- The authTable includes entries describing the communities
                -- accepted by the agent.       Each community can be granted one
                -- access-modes to their corresponding MIB view.
                -- Please note, 'monitor' access allows users read-only access whereas
                -- 'primary' access allows users both read-only and read-write mib access.



                authTable OBJECT-TYPE
                        SYNTAX SEQUENCE OF AuthEntry
                        ACCESS not-accessible
                        STATUS mandatory
                        DESCRIPTION
                                "The entries for the authentication table."
                        ::= { security 1 }

                authEntry OBJECT-TYPE
                        SYNTAX AuthEntry
                        ACCESS not-accessible
                        STATUS mandatory
                        DESCRIPTION
                                "The entries for authentication table."
                        INDEX { authCommunity }
                        ::= { authTable 1 }

                AuthEntry ::= SEQUENCE {
                        authCommunity           OCTET STRING,
                        authTypeAccess          INTEGER,
                        authActions                     INTEGER
                        }

                authCommunity OBJECT-TYPE
                        SYNTAX OCTET STRING
                        ACCESS read-write
                        STATUS mandatory
                        DESCRIPTION
                                "The community string identifying an authentic/authorized
                                manager."
                        ::= { authEntry 1 }

                authTypeAccess OBJECT-TYPE
                        SYNTAX INTEGER {
                                not-applicable(1),
                                monitor(2),
                                not-applicable(3),
                                primary(4)
                                }
                        ACCESS read-write
                        STATUS mandatory
                        DESCRIPTION
                                "The type of access allowed for the community string
                                identifying an authentic/authorized manager."
                        ::= { authEntry 2 }

                authActions OBJECT-TYPE
                        SYNTAX INTEGER {
                                not-applicable(1),
                                add(2),
                                delete(3)
                                }
                        ACCESS read-write
                        STATUS mandatory
                        DESCRIPTION
                                "The action on a row of the authentication table."
                        ::= { authEntry 3 }

                -- The Subscription table is used to specify the managers
                -- that wish to receive traps generated by the IBM RMONiter Agent for OS/2
                -- product.  When an event calls for a trap PDU, the agent sends
                -- a trap to each IP address found in the subscriptTable, using
                -- the community specified in the table.

                subscriptTable OBJECT-TYPE
                        SYNTAX SEQUENCE OF SubscriptEntry
                        ACCESS read-write
                        STATUS mandatory
                        DESCRIPTION
                                "The entries for the subscription table."
                        ::= { security 2 }

                subscriptEntry OBJECT-TYPE
                        SYNTAX SubscriptEntry
                        ACCESS read-write
                        STATUS mandatory
                        DESCRIPTION
                                "The entries for subscription table."
                        INDEX { subscriptIpAddress }
                        ::= { subscriptTable 1 }

                SubscriptEntry ::= SEQUENCE {
                        subscriptIpAddress              IpAddress,
                        subscriptCommunity              DisplayString,
                        subscriptActions                INTEGER
                        }

                subscriptIpAddress OBJECT-TYPE
                        SYNTAX IpAddress
                        ACCESS read-write
                        STATUS mandatory
                        DESCRIPTION
                                "The IP address of the manager subscribing to traps."
                        ::= { subscriptEntry 1 }

                subscriptCommunity OBJECT-TYPE
                        SYNTAX DisplayString
                        ACCESS read-write
                        STATUS mandatory
                        DESCRIPTION
                                "The community string to be used in trap PDUs sent
                                to the subscribing manager."
                        ::= { subscriptEntry 2 }

                subscriptActions OBJECT-TYPE
                        SYNTAX INTEGER {
                                not-applicable(1),
                                add(2),
                                delete(3)
                                }
                        ACCESS read-write
                        STATUS mandatory
                        DESCRIPTION
                                "The action on a row of the subscription table."
                        ::= { subscriptEntry 3 }

                -- The Authentication Failure table is used to report
                -- authentication failures at the agent.  When the agent
                -- receives a SNMP request that is not allowed by the Authentication
                -- table, an entry is added to the authFailTable to record
                -- the IP address and community of the manager issuing the request.

                authFailTable OBJECT-TYPE
                        SYNTAX SEQUENCE OF AuthFailEntry
                        ACCESS read-write
                        STATUS mandatory
                        DESCRIPTION
                                "The entries for the authentication failure table."
                        ::= { security 3 }

                authFailEntry OBJECT-TYPE
                        SYNTAX AuthFailEntry
                        ACCESS read-write
                        STATUS mandatory
                        DESCRIPTION
                                "The entries for authentication failure table."
                        INDEX { authFailIndex }
                        ::= { authFailTable 1 }

                AuthFailEntry ::= SEQUENCE {
                        authFailIndex                   INTEGER,
                        authFailIPAddress               IpAddress,
                        authFailCommunity               DisplayString
                        }

                authFailIndex OBJECT-TYPE
                        SYNTAX INTEGER
                        ACCESS read-only
                        STATUS mandatory
                        DESCRIPTION
                                "The index for this entry in the authentication
                                failure table."
                        ::= { authFailEntry 1 }

                authFailIPAddress OBJECT-TYPE
                        SYNTAX IpAddress
                        ACCESS read-only
                        STATUS mandatory
                        DESCRIPTION
                                "The IP address of the manager that sent the SNMP request
                                that caused the authentication failure."
                        ::= { authFailEntry 2 }

                authFailCommunity OBJECT-TYPE
                        SYNTAX DisplayString
                        ACCESS read-only
                        STATUS mandatory
                        DESCRIPTION
                                "The community string used in the SNMP request that
                                caused the authentication failure."
                        ::= { authFailEntry 3 }


                -- The Protocols Group
                --
                -- The Protocols group includes MIB data collection based on protocols
                -- seen in the packets observed by the agent.

                -- The Protocol Distribution Group examines the protocols identified in
                -- the "ethertype" field found in DIX Ethernet frames, the SNAP protocol
                -- on IEEE 802 networks, or the DSAP field of the LLC protocol, also found
                -- on IEEE 802 networks.

                protocolDistControlTable OBJECT-TYPE
                        SYNTAX SEQUENCE OF ProtocolDistControlEntry
                        ACCESS not-accessible
                        STATUS mandatory
                        DESCRIPTION
                                ""
                        ::= { protocols 1 }

                protocolDistControlEntry OBJECT-TYPE
                        SYNTAX ProtocolDistControlEntry
                        ACCESS not-accessible
                        STATUS mandatory
                        DESCRIPTION
                                ""
                        INDEX { protocolDistControlIndex }
                        ::= { protocolDistControlTable 1 }

                ProtocolDistControlEntry ::= SEQUENCE {
                        protocolDistControlIndex                INTEGER,
                        protocolDistControlDataSource   OBJECT IDENTIFIER,
                        protocolDistControlLastDeleteTime       TimeTicks,
                        protocolDistControlOwner                OwnerString,
                        protocolDistControlStatus               EntryStatus
                }

                protocolDistControlIndex OBJECT-TYPE
                        SYNTAX INTEGER
                        ACCESS read-only
                        STATUS mandatory
                        DESCRIPTION
                                ""
                        ::= { protocolDistControlEntry 1 }

                protocolDistControlDataSource OBJECT-TYPE
                        SYNTAX OBJECT IDENTIFIER
                        ACCESS read-write
                        STATUS mandatory
                        DESCRIPTION
                                "This object identifies the source of the data for
                                which protocol distribution data is collected. This
                                source can be any interface on this device.  In order
                                to identify a particular interface, this object shall identify
                                the instance of the ifIndex object, for the desired
                                interface.  For example, if an entry were to receive
                                data from interface #1, this object would be set to
                                ifIndex.1.

                                This object may not be modified if the associated
                                protocolDistControlStatus object is equal to valid(1)."
                        ::= { protocolDistControlEntry 2 }

                protocolDistControlLastDeleteTime OBJECT-TYPE
                        SYNTAX TimeTicks
                        ACCESS read-only
                        STATUS mandatory
                        DESCRIPTION
                                ""
                        ::= { protocolDistControlEntry 3 }

                protocolDistControlOwner OBJECT-TYPE
                        SYNTAX OwnerString
                        ACCESS read-write
                        STATUS mandatory
                        DESCRIPTION
                                "The entity that created this entry in the protocol
                                distribution control table, and is therefore using the
                                resources associated with it."
                        ::= { protocolDistControlEntry  4 }

                protocolDistControlStatus OBJECT-TYPE
                        SYNTAX EntryStatus
                        ACCESS read-write
                        STATUS mandatory
                        DESCRIPTION
                                "The status of this protocol distribution control entry."
                        ::= { protocolDistControlEntry  5 }

                protocolDistTable OBJECT-TYPE
                        SYNTAX SEQUENCE OF ProtocolDistEntry
                        ACCESS not-accessible
                        STATUS mandatory
                        DESCRIPTION
                                "A table of protocol types and associated counts
                                including entries for each different protocol seen
                                by the monitor.  Note that protocols are identified by
                                examining the 'ethertype' field of DIX Ethernet frames,
                                the SNAP protocol on IEEE 802 network frames, or the
                                DSAP field of the LLC protocol, also found on IEEE 802
                                networks."
                        ::= { protocols 2 }

                protocolDistEntry OBJECT-TYPE
                        SYNTAX ProtocolDistEntry
                        ACCESS not-accessible
                        STATUS mandatory
                        DESCRIPTION
                                "A set of counts maintained for each different protocol
                                seen by the agent."
                        INDEX { protocolDistIndex, protocolDistEthertype }
                        ::= { protocolDistTable 1 }

                ProtocolDistEntry ::= SEQUENCE {
                        protocolDistIndex               INTEGER,
                        protocolDistEthertype           OCTET STRING (SIZE (2)),
                        protocolDistPkts                Counter,
                        protocolDistOctets              Counter
                }

                protocolDistIndex OBJECT-TYPE
                        SYNTAX INTEGER
                        ACCESS read-only
                        STATUS mandatory
                        DESCRIPTION
                                "A value uniquely identifying this protocol distribution
                                control table entry."
                        ::= { protocolDistEntry 1 }

                protocolDistEthertype OBJECT-TYPE
                        SYNTAX OCTET STRING (SIZE (2))
                        ACCESS read-only
                        STATUS mandatory
                        DESCRIPTION
                                "A protocol type identified by the 'ethertype' field found
                                in DIX Ethernet, or in the SNAP protocol on IEEE 802
                                networks or  the DSAP protocol on 802.5 networks."
                        ::= { protocolDistEntry 2 }

                protocolDistPkts OBJECT-TYPE
                        SYNTAX Counter
                        ACCESS read-only
                        STATUS mandatory
                        DESCRIPTION
                                "A count of the number of packets seen using the protocol
                                identified by the corresponding protocolDistEthertype."
                        ::= { protocolDistEntry 3 }

                protocolDistOctets OBJECT-TYPE
                        SYNTAX Counter
                        ACCESS read-only
                        STATUS mandatory
                        DESCRIPTION
                                "A count of the number of octets in packets seen using
                                the protocol identified by the corresponding
                                protocolDistEthertype."
                        ::= { protocolDistEntry 4 }



END
