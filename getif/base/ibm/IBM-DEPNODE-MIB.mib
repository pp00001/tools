-- Licensed Materials - Property of IBM    
--                                        
-- 5765-529                              
--                                      
-- (C) Copyright IBM Corp. 1996 All Rights Reserved.                     
--                                                                       
-- US Government Users Restricted Rights - Use, duplication or disclosure
-- restricted by GSA ADP Schedule Contract with IBM Corp.               
--                                                                        
-- Script Name:  depnode.my                                                  
--                                                                      
-- Description:                                                        
--      definition of the depnode mib.
--                                                                      
-- "%Z%%M%   %I%   %W% %G% %U%"

DEPNODE-MIB  DEFINITIONS ::= BEGIN

IMPORTS
        Counter, Gauge, TimeTicks, IpAddress, DisplayString, enterprises
		FROM RFC1155-SMI
	TRAP-TYPE
		FROM RFC1215;

ibm           	OBJECT IDENTIFIER ::= { enterprises 2 }

ibmProd		OBJECT IDENTIFIER ::= { ibm 6 }

ibmSP		OBJECT IDENTIFIER ::= { ibmProd 117 }

------------------------------------------------------------------
--

--              IBM NODEDEP MIB

--
ibmSPDepNode       OBJECT IDENTIFIER ::= { ibmSP 4 }

ibmSPDepNodeTable OBJECT-TYPE
      SYNTAX  SEQUENCE OF IbmSPDepNodeEntry
      ACCESS  not-accessible
      STATUS  mandatory
      DESCRIPTION
              "This entity's table of dependent secondary nodes
               attached to IBM SP switch networks."
      ::= { ibmSPDepNode 1 }

ibmSPDepNodeEntry OBJECT-TYPE
      SYNTAX  IbmSPDepNodeEntry
      ACCESS  not-accessible
      STATUS  mandatory
      DESCRIPTION
              "Configuration information for a dependent
               secondary node on SP switch network."
      INDEX { ibmSPDepNodeName }
      ::= { ibmSPDepNodeTable 1 }

IbmSPDepNodeEntry ::=
       SEQUENCE {
       ibmSPDepNodeName
          DisplayString, 
       ibmSPDepNodeNumber
          INTEGER, 
       ibmSPDepSwToken
          OCTET STRING,
       ibmSPDepSwARP
          INTEGER,
       ibmSPDepSwNodeNumber
          INTEGER, 
       ibmSPDepIPaddr
          IpAddress,
       ibmSPDepNetMask
          IpAddress,
       ibmSPDepIPMaxLinkPkt
          INTEGER,
       ibmSPDepIPHostOffset
          INTEGER,
       ibmSPDepConfigState
          INTEGER,
       ibmSPDepSysName
          DisplayString,
       ibmSPDepNodeState
          INTEGER,
       ibmSPDepSwChipLink
          INTEGER,
       ibmSPDepNodeDelay
          INTEGER,
       ibmSPDepAdminStatus
	  INTEGER
       }

ibmSPDepNodeName OBJECT-TYPE
      SYNTAX  DisplayString
      ACCESS  read-only
      STATUS  mandatory
      DESCRIPTION
              "Identifier assigned to this node in its
               system's administrative environment."
      ::= { ibmSPDepNodeEntry 1 }
 
ibmSPDepNodeNumber OBJECT-TYPE
      SYNTAX  INTEGER 
      ACCESS  read-write
      STATUS  mandatory
      DESCRIPTION
              "Relative node number assigned to this node in the SP system.
               Note that this is distinct from switch node number."
      ::= { ibmSPDepNodeEntry 2 }

ibmSPDepSwToken OBJECT-TYPE
      SYNTAX  OCTET STRING (SIZE(10))
      ACCESS  read-write
      STATUS  mandatory
      DESCRIPTION
              "Opaque correlator assigned in the SP system
               for this node's switch connection."
      ::= { ibmSPDepNodeEntry 3 }

ibmSPDepSwARP OBJECT-TYPE
      SYNTAX  INTEGER {
                  disabled(1),
                  enabled(2)
              }
      ACCESS  read-write
      STATUS  mandatory
      DESCRIPTION
              "Indicates whether ARP is enabled for the partition
               of the switch network that contains the associated
               dependent secondary node.
               NOTE: An SNMP Agent may be responsible for switch
               nodes in several SP system partitions, and ARP 
               may be enabled in none, some, or all of the partitions.

               A value of disabled(1) indicates that ARP is
               not to be used to resolve network protocol
               addresses to switch node numbers for the switch
               network.  Instead, the mapping of IP addresses
               to switch node numbers is determined via the
               algorithm in the description of ibmSPDepIPHostOffset.

               A value of enabled(2) indicates that ARP is
               to be used to resolve network protocol
               addresses to switch node numbers for the switch
               network."
      ::= { ibmSPDepNodeEntry 4 }

ibmSPDepSwNodeNumber OBJECT-TYPE
      SYNTAX  INTEGER (0..65535)
      ACCESS  read-write
      STATUS  mandatory
      DESCRIPTION
              "The switch node number of the associated SP switch
               interface.  In common networking terminology,
               this is the physical address for the interface
               on the SP switch network, and is also called
               the Node Device ID in the SP dependent node
               architecture."
      ::= { ibmSPDepNodeEntry 5 }

ibmSPDepIPaddr OBJECT-TYPE
      SYNTAX  IpAddress
      ACCESS  read-write
      STATUS  mandatory
      DESCRIPTION
              "The IP address for the associated SP switch interface."
      ::= { ibmSPDepNodeEntry 6 }

ibmSPDepNetMask OBJECT-TYPE
      SYNTAX  IpAddress
      ACCESS  read-write
      STATUS  mandatory
      DESCRIPTION
               "The subnet mask associated with the IP address of
                this entry.  The value of the mask is an IP
                address with all the network bits set to 1 and all
                the host bits set to 0."
      ::= { ibmSPDepNodeEntry 7 }

ibmSPDepIPMaxLinkPkt OBJECT-TYPE
      SYNTAX  INTEGER
      ACCESS  read-write
      STATUS  mandatory
      DESCRIPTION
              "The maximum number of bytes in the data portion of
               link-layer packets for IP datagrams on the
               SP switch network."
      ::= { ibmSPDepNodeEntry 8 }

ibmSPDepIPHostOffset OBJECT-TYPE
      SYNTAX  INTEGER
      ACCESS  read-write
      STATUS  mandatory
      DESCRIPTION
              "This value is the difference between switch node
               numbers and the host portion of the corresponding
               IP addresses when ARP is disabled on the SP switch
               network.  It is the value to subtract from the
               host portion of an IP address to calculate the
               corresponding switch node number."
      ::= { ibmSPDepNodeEntry 9 }

ibmSPDepConfigState OBJECT-TYPE
      SYNTAX  INTEGER {
                  notConfigured(1),
                  firmwareLoadFailed(2),
                  driverLoadFailed(3),
                  diagnosticFailed(4),
                  microcodeLoadFailed(5),
                  fullyConfigured(6)
              }
      ACCESS  read-only
      STATUS  mandatory
      DESCRIPTION
              "This value indicates the final configuration state
               of the corresponding SP switch interface."
      ::= { ibmSPDepNodeEntry 10 }

ibmSPDepSysName OBJECT-TYPE
      SYNTAX  DisplayString
      ACCESS  read-write
      STATUS  mandatory
      DESCRIPTION
              "The fully-qualified domain name of the SP system 
               partition that contains this dependent node. This
               name is administratively assigned in the SP system."
      ::= { ibmSPDepNodeEntry 11 }

ibmSPDepNodeState OBJECT-TYPE
      SYNTAX  INTEGER {
                  nodeUp(1),
                  nodeDown(2)
              }
      ACCESS  read-only
      STATUS  mandatory
      DESCRIPTION
              "This value indicates the state of the dependent
               node with respect to its capability to handle
               Switch Manager protocol via its SP switch interface.

               A value of nodeUp(1) indicates that the node has
               been reinitialized or reconfigured sufficiently
               to handle the Switch Manager protocol to unfence
               the node if it were previously fenced from the
               SP switch network.

               A value of nodeDown(2) indicates that the node is
               no longer able to handle Switch Manager protocol
               messages on the SP switch network."
      ::= { ibmSPDepNodeEntry 12 }

ibmSPDepSwChipLink OBJECT-TYPE
      SYNTAX  INTEGER 
      ACCESS  read-write
      STATUS  mandatory
      DESCRIPTION
              "The send port number for packets from the
               adjacent switch chip to the dependent node.
               The dependent node needs this value to build
               the packet that it sends to the adjacent
               switch chip to trigger that chip to reply
               with a clock synchronization packet."
      ::= { ibmSPDepNodeEntry 13 }

ibmSPDepNodeDelay OBJECT-TYPE
      SYNTAX  INTEGER
      ACCESS  read-write
      STATUS  mandatory
      DESCRIPTION
              "This value is an estimate of how many clock
               cycles elapse before a clock synchronization packet
               sent from the adjacent switch chip to the dependent node
               results in loading of the switch time-of-day register
               for the node.

               The dependent node needs this value to build
               the packet that it sends to the adjacent
               switch chip to trigger that chip to reply with
               a clock synchronization packet."
      ::= { ibmSPDepNodeEntry 14 }

ibmSPDepAdminStatus OBJECT-TYPE
	SYNTAX  INTEGER {
		    up(1),
		    down(2),
		    reconfigure(3)
		}
	ACCESS  read-write
	STATUS	mandatory
	DESCRIPTION
		"This value indicates the desired state of the dependent
		node with respect to its capability to handle
		Switch Manager protocol via its SP switch interface.
		If the dependent node is not in the desired state,
		then the SNMP Agent triggers actions to change its state
		to the desired state.
	
		A value of up(1) indicates that the node should be 
		initialized and configured sufficiently
		to handle the Switch Manager protocol.

		A value of down(2) indicates that the node should be
		reset such that it is not able to receive and handle
		Switch Manager protocol messages on the SP switch
		network.
	
		A value of reconfigure(3) indicates that the SNMP Agent
		must send the switchInfoNeeded trap to request new SP 
		switch configuration information for the dependent
		node.  This causes the SNMP Manager to send the
		new configuration information for the dependent node
		MIB objects via set-request PDU(s).
		Once the new values are set by the SNMP Manager,
		the SNMP Agent reinitializes and reconfigures the dependent
		node sufficiently to handle the Switch Manager protocol."
	::= { ibmSPDepNodeEntry 15 }


-- IBM enterprise-specific traps dependent secondary nodes on SP switch:

switchInfoNeeded TRAP-TYPE
      ENTERPRISE  ibmSPDepNode
      VARIABLES   { ibmSPDepNodeName }
      DESCRIPTION
              "A switchInfoNeeded trap signifies that the sending
               protocol entity needs SP switch configuration
               information for a dependent secondary node within
               the sender's configuration."
      ::= 1
 
switchConfigState TRAP-TYPE
      ENTERPRISE  ibmSPDepNode
      VARIABLES   { ibmSPDepConfigState }
      DESCRIPTION
              "A switchConfigState trap indicates the final
               configuration state of a dependent secondary node's
               SP switch interface."
      ::= 2
 
switchNodeUp TRAP-TYPE
      ENTERPRISE  ibmSPDepNode
      VARIABLES   { ibmSPDepNodeName }
      DESCRIPTION
              "A switchNodeUp trap indicates that a dependent
               secondary node in the sender's configuration has
               just been reinitialized or reconfigured and is able
               to handle SP Switch Manager protocol messages."
      ::= 3
 
switchNodeDown TRAP-TYPE
      ENTERPRISE  ibmSPDepNode
      VARIABLES   { ibmSPDepNodeName }
      DESCRIPTION
              "A switchNodeDown trap indicates that a dependent
               secondary node in the sender's configuration
               is no longer able to handle Switch Manager protocol
               messages on the switch network."
      ::= 4
 
END
