-- ********************************************************************

--  UnitransMib-MS-alarm.mib

--  Copyright (c) 2008 ZTE CORPORATION.All rights reserved.

--  Description: ZTE Unitrans alamrs definition

--  Version     v1.0

--  Modification Record: 

--********************************************************************
UnitransMib-MS-alarm
DEFINITIONS ::= BEGIN
IMPORTS
    MODULE-IDENTITY, OBJECT-TYPE, NOTIFICATION-TYPE,
    enterprises, Integer32, Unsigned32, IpAddress
        FROM SNMPv2-SMI
    TEXTUAL-CONVENTION, DisplayString, TimeStamp, DateAndTime
        FROM SNMPv2-TC  
    MODULE-COMPLIANCE, OBJECT-GROUP, NOTIFICATION-GROUP
        FROM SNMPv2-CONF
     zteUnitransMS
	FROM 
	UnitransMib-MS-root   
        BOOL-TC,Time-TC,Unit-TC,       
        ObjectNVSList-T,NamingAttributes-T,LayerRate-TC,LayerRate-TC
        FROM 
        UnitransMib-MS-common      
        
        PMParameterName-TC,PMLocation-TC,PMValue-TC,Granularity-TC,PMThresholdType-TC,PMValue-TC
        FROM 
        UnitransMib-MS-performance
        
        ;

 zteuAlmObjects MODULE-IDENTITY
        LAST-UPDATED   "0602130000Z"
        ORGANIZATION   "ZTE"
        CONTACT-INFO   "
           ZTE Corporation
           
           Postal:   518057    
           
           via the WEB:  http://www.zte.com.cn                           
            
           via phone:    86-755-26773000"
   DESCRIPTION
      "The module describing ZTE Unitrans MIB."
::= { zteUnitransMS 8 }       
-- ********************************************************************
-- the MIB module for the ZTE unitrans objects
-- ********************************************************************
--      zteuAlmObjects           OBJECT IDENTIFIER  ::=  { zteUnitrans 3 } 
-- ********************************************************************

   
    PerceivedSeverity-TC ::= TEXTUAL-CONVENTION
    STATUS current
        DESCRIPTION "
        This textual convention presents alarm serverity:
                ps-INDETERMINATE,   Indeterminate Alarm
                ps-CRITICAL,        Critical Alarm
                ps-MAJOR            Major Alarm
                ps-MINOR,           Minor Alarm
                ps-WARNING,         Warning Alarm
                ps-CLEARED          Cleared Alarm 

        "
        SYNTAX INTEGER 
        {                
                ps-CRITICAL(1),
                ps-MAJOR(2),
                ps-MINOR(3),
                ps-WARNING(4),
                ps-INDETERMINATE(5),
                ps-CLEARED(6)
        }
        
        AlarmID-TC
        ::= TEXTUAL-CONVENTION
        STATUS current
        DESCRIPTION "
        This textual convention presents alarm identifier
        "
        SYNTAX OCTET STRING 
        
        AlarmType-TC ::= TEXTUAL-CONVENTION
        STATUS current
        DESCRIPTION "
        This textual convention presents alarm type:
                at-COMMUNICATIONSALARM	Communication Alarm
                at-QOSALARM           	Quality of service Alarm
                at-EQUIPMENTALARM	     Device Alarm
                at-PROCESSINGERRORALARM	Processing Failure Alarm
                at-ENVIRONMENTALALARM	  Environmental Alarm
		at-VENDORDEFINEDEVENT    Application related event
        "
        SYNTAX INTEGER 
        {
                at-COMMUNICATIONSALARM (1),
                at-QOSALARM (2),
                at-EQUIPMENTALARM (3),
                at-PROCESSINGERRORALARM(4),
                at-ENVIRONMENTALALARM(5),
				at-VENDORDEFINEDEVENT(6) 
        }  
        
	
	ServiceAffecting-TC ::= TEXTUAL-CONVENTION
        STATUS current
        DESCRIPTION "
        This textual convention presents whether alarm affect service or not:
            sa-UNKNOWN(1),          Unknown
        sa-SERVICE-AFFECTING(2),    Affecting
        sa-NON-SERVICE-AFFECTING(3) No Affecting
        "
        SYNTAX INTEGER
        {
            sa-UNKNOWN(1),
            sa-SERVICE-AFFECTING(2),
            sa-NON-SERVICE-AFFECTING(3)
        } 

		ProbableCause-TC ::= TEXTUAL-CONVENTION
        STATUS current
        DESCRIPTION        
                "The possible alarm causes are more detailed than
                 the alarmType. "
        SYNTAX INTEGER {
                -- The following values are defined in M.3100 (1995)
                m3100Indeterminate(0),
                m3100AlarmIndicationSignal(1),
                m3100CallSetupFailure(2),
                m3100DegradedSignal(3),
                m3100FarEndReceiverFailure(4),
                m3100FramingError(5),
                m3100LossOfFrame(6),
                m3100LossOfPointer(7),
                m3100LossOfSignal(8),
                m3100PayloadTypeMismatch(9),
                m3100TransmissionError(10),
                m3100RemoteAlarmInterface(11),
                m3100ExcessiveBitErrorRate(12),
                m3100PathTraceMismatch(13),
                m3100Unavailable(14),
                m3100SignalLabelMismatch(15),
                m3100LossOfMultiFrame(16),
                m3100CommunicationsReceiveFailure(17),
                m3100CommunicationsTransmitFailure(18),
                m3100ModulationFailure(19),
                m3100DemodulationFailure(20),
				m3100BroadcastChannelFailure(21),
				m3100ConnectionEstablishmentError(22),
				m3100InvalidMessageReceived(23),
				m3100RoutingFailure(26),

                m3100BackPlaneFailure(51),
                m3100DataSetProblem(52),
                m3100EquipmentIdentifierDuplication(53),
                m3100ExternalIfDeviceProblem(54),
                m3100LineCardProblem(55),
                m3100MultiplexerProblem(56),
                m3100NeIdentifierDuplication(57),
                m3100PowerProblem(58),
                m3100ProcessorProblem(59),
                m3100ProtectionPathFailure(60),
                m3100ReceiverFailure(61),
                m3100ReplaceableUnitMissing(62),
                m3100ReplaceableUnitTypeMismatch(63),
                m3100SynchronisationSourceMismatch(64),
                m3100TerminalProblem(65),
                m3100TimingProblem(66),
                m3100TransmitterFailure(67),
                m3100TrunkCardProblem(68),
                m3100ReplaceableUnitProblem(69),
                m3100RealTimeClockFailure(70),
				m3100DiskFailure(73),
				m3100FrequencyHoppingFailure(74),
				m3100LossOfSynchronisation(76),
				m3100LossOfRedundancy(77),
				m3100PowerSupplyFailure(78),
				m3100SignalQualityEvaluationFailure(79),
                m3100ProtectionMechanismFailure(81),
                m3100ProtectingResourceFailure(82),
                m3100AirCompressorFailure(101),
                m3100AirConditioningFailure(102),
                m3100AirDryerFailure(103),
                m3100BatteryDischarging(104),
                m3100BatteryFailure(105),
                m3100CommercialPowerFailure(106),
                m3100CoolingFanFailure(107),
                m3100EngineFailure(108),
                m3100FireDetectorFailure(109),
                m3100FuseFailure(110),
                m3100GeneratorFailure(111),
                m3100LowBatteryThreshold(112),
                m3100PumpFailure(113),
                m3100RectifierFailure(114),
                m3100RectifierHighVoltage(115),
                m3100RectifierLowVoltage(116),
                m3100VentilationSystemFailure(117),
                m3100EnclosureDoorOpen(118),
                m3100ExplosiveGas(119),
                m3100Fire(120),
                m3100Flood(121),
                m3100HighHumidity(122),
                m3100HighTemperature(123),
                m3100HighWind(124),
                m3100IceBuildUp(125),
                m3100IntrusionDetection(126),
                m3100LowFuel(127),
                m3100LowHumidity(128),
                m3100LowCablePressure(129),
                m3100LowTemperature(130),
                m3100LowWater(131),
                m3100Smoke(132),
                m3100ToxicGas(133),
                m3100ExternalPointFailure(136),
                m3100StorageCapacityProblem(151),
                m3100MemoryMismatch(152),
                m3100CorruptData(153),
                m3100OutOfCPUCycles(154),
                m3100SoftwareEnvironmentProblem(155),
                m3100SoftwareDownloadFailure(156),
                m3100LossOfRealTime(157),
                m3100Reinitialized(158),
				m3100DatabaseInconsistency(161),
				m3100TimeoutExpired(165),
                m3100ExcessiveErrorRate(203),
				m3100ReducedLoggingCapability(206),
				m3100SystemResourcesOverload(207),
                --
                -- The following values are defined in X.733 (1992)
                x733AdapterError(301),
                x733ApplicationSubsystemFailure(302),
                x733BandwidthReduced(303),
                -- x733CallEstablishmentError (use M.3100 value)
                x733CommunicationsProtocolError(305),
                x733CommunicationsSubsystemFailure(306),
                x733ConfigurationOrCustomizationError(307),
                x733Congestion(308),
                -- x733CorruptData (use M.3100 value)
                x733CpuCyclesLimitExceeded(310),
                x733DataSetOrModemError(311),
                -- x733DegradedSignal (use M.3100 value)
                x733DTEDCEInterfaceError(313),
                -- x733EnclosureDoorOpen (use M.3100 value)
                x733EquipmentMalfunction(315),
                x733ExcessiveVibration(316),
                x733FileError(317),
                -- x733FireDetected (use M.3100 value)
                -- x733FloodDetected (use M.3100 value)
                -- x733FramingError  (use M.3100 value)
                x733HeatingOrVentilationOrCoolingSystemProblem(321),
                x733HumidityUnacceptable(322),
                x733InputOutputDeviceError(323),
                x733InputDeviceError(324),
                x733LANError(325),
                x733LeakDetected(326),
                x733LocalNodeTransmissionError(327),
                -- x733LossOfFrame (use M.3100 value)
                -- x733LossOfSignal (use M.3100 value)
                x733MaterialSupplyExhausted(330),
                -- x733MultiplexerProblem (use M.3100 value)
                x733OutOfMemory(332),
                x733OuputDeviceError(333),
                x733PerformanceDegraded(334),
                -- x733PowerProblem (use M.3100 value)
                x733PressureUnacceptable(336),
                -- x733ProcessorProblem (use M.3100 value)
                -- x733PumpFailure (use M.3100 value)
                x733QueueSizeExceeded(339),
                x733ReceiveFailure(340),
                -- x733ReceiverFailure (use M.3100 value)
                x733RemoteNodeTransmissionError(342),
                x733ResourceAtOrNearingCapacity(343),
                x733ResponseTimeExcessive(344),
                x733RetransmissionRateExcessive(345),
                x733SoftwareError(346),
                x733SoftwareProgramAbnormallyTerminated(347),
                x733SoftwareProgramError(348),
                -- x733StorageCapacityProblem (use M.3100 value)
                x733TemperatureUnacceptable(350),
                x733ThresholdCrossed(351),
                -- x733TimingProblem (use M.3100 value)
                x733ToxicLeakDetected(353),
                x733TransmitFailure(354),
                -- x733TransmitterFailure (use M.3100 value)
                x733UnderlyingResourceUnavailable(356),
                x733VersionMismatch(357),
                   
                
                -- The following values are defined in X.736 (1992)
                x736AuthenticationFailure(701),
                x736BreachOfConfidentiality(702),
                x736CableTamper(703),
                x736DelayedInformation(704),
                x736DenialOfService(705),
                x736DuplicateInformation(706),
                x736InformationMissing(707),
                x736InformationModificationDetected(708),
                x736InformationOutOfSequence(709),
                x736IntrusionDetection(710),
                x736KeyExpired(711),
                x736NonRepudiationFailure(712),
                x736OutOfHoursActivity(713),
                x736OutOfService(714),
                x736ProceduralError(715),
                x736UnauthorizedAccessAttempt(716),
                x736UnexpectedInformation(717),
                x736UnspecifiedReason(718),
                
                zte-payloadERDI(100002),
                zte-connectionERDI(100004),
								zte-serviceERDI(100005),
								zte-extendSignalIdMissmatch(100010),
								zte-SInterfaceError(100011),
								zte-contPdu(100013),
								zte-signalLabelMismatch(100015),
								zte-sdhOOFStatusInd(100027),
								zte-sdhLIDIStatus(100028),
								zte-sdhPRDIStatus(100029),
								zte-sdhLAISStatus(100030),
								zte-sdhPAISStatus(100031),
								zte-m4IMsgLocationLost(100032),
								zte-msgMarkLose(100036),
								zte-etpieUnlink(100037),
								zte-rai(100038),
								zte-YAS(100039),
								zte-slip(100040),
								zte-dccConnectionFailure(100042),
								zte-protectionSwitchEvent(100044),
								zte-k2Mismatch(100045),
								zte-k1k2Mismatch(100046),
								zte-inputPowerHigh(100047),
								zte-unequiped(100049),
								zte-receivePower-TCA(100050),
								zte-vcgLos-1B(100051),
								zte-missmatchedUPI-1B(100053),
								zte-clientSignalFailed-1B(100054),
								zte-LaserBackPower-TCA(100068),
								zte-sendRefClockLoseLock(100081),
								zte-recvDataRecoverClockLoseLock(100082),
								zte-recvRefClockLoseLock(100083),
								zte-ocd(100088),
								zte-eccStyleMismatch(100089),
								zte-unAuthenLaserModule(100101),
								zte-recvGFPUserDataFrames-1B-TCA(100103),
								zte-recvGFPIdleFrames-1B-TCA(100104),
								zte-recvGFPClientManagementFrames-1B-TCA(100105),
								zte-transGFPDataFrames-1B-TCA(100106),
								zte-engineFailure(100108),
								zte-recvGFPTypeHECCheckFailure-1B-TCA(100109),
								zte-recvGFPbadFCSFrames-1B-TCA(100110),
								zte-loseOfAlignment(100139),
								zte-externalWarn1(100140),
								zte-externalWarn2(100141),
								zte-externalWarn3(100142),
								zte-externalWarn4(100143),
								zte-externalWarn5(100144),
								zte-externalWarn6(100145),
								zte-externalWarn7(100146),
								zte-LaserOutPower-TCA(100147),
								zte-LaserCoolingCurr-TCA(100148),
								zte-ModuleTemp-TCA(100149),
								zte-outOfControl(100150),
								zte-interfaceBoardSick(100168),
								zte-sendCollisionCnt-TCA(100170),
								zte-recvFragErrFrameCnt-TCA(100171),
								zte-recvAlignErrFrameCnt-TCA(100172),
								zte-recvSmallFrameCnt-TCA(100173),
								zte-recvExcLengthFrameCnt-TCA(100174),
								zte-recvCrcErrFrameCnt-TCA(100175),
								zte-recvDropFrameCnt-TCA(100176),
								zte-sendDelayExcFrameCnt-TCA(100177),
								zte-sendDelayColliFrameCnt-TCA(100178),
								zte-recvFrameFilterCnt-TCA(100179),
								zte-sendErrByteCntExc-TCA(100180),
								zte-recvByteFilterCnt-TCA(100181),
								zte-recvSFrameFilterCnt-TCA(100182),
								zte-sendErrFrameCnt-TCA(100183),
								zte-recvMFrameFilterCnt-TCA(100184),
								zte-recvBFrameFilterCntExc-TCA(100185),
								zte-sendCrcErrFrameCnt-TCA(100186),
								zte-sendDropFrame4MACCnt-TCA(100187),
								zte-sendFlagErrCntExc-TCA(100188),
								zte-sendOFRErrCnt-TCA(100189),
								zte-recvErrByteCnt-TCA(100190),
								zte-recvDropFrame4MACCnt-TCA(100191),
								zte-recvSysErrFrameCnt-TCA(100192),
								zte-recvErrFrameCnt-TCA(100193),
								zte-recvErrSFrameCnt-TCA(100194),
								zte-recvErrMFrameCnt-TCA(100195),
								zte-sendJabberFrameCnt-TCA(100196),
								zte-recvErrBFrameCnt-TCA(100197),
								zte-initializeFailure(100200),
								zte-BBE-TCA(100221),
								zte-ES-TCA(100222),
								zte-SES-TCA(100223),
								zte-UAS-TCA(100224),
								zte-PJCH-TCA(100225),
								zte-OFS-TCA(100226),
								zte-PSC(100227),
								zte-PSD(100228),
								zte-PJCL-TCA(100229),
								zte-NegPSlipCnt-TCA(100230),
								zte-FEUAS-TCA(100235),
								zte-FEBBE-TCA(100236),
								zte-FEES-TCA(100237),
								zte-FESES-TCA(100238),
								zte-LsrBiasCurr-TCA(100239),
								zte-LsrTemp-TCA(100240),
								zte-OptPowerOut-TCA(100241),
								zte-CV-TCA(100242),
								zte-laserWaveLength(100243),
								zte-laserBackPower(100244),
								zte-detectTemp(100245),
								zte-fanSpeed(100246),
								zte-NZBTER-TCA(100247),
								zte-NOBTER-TCA(100248),
								zte-NBYTER-TCA(100249),
								zte-NERROV-TCA(100250),
								zte-tributeClockSlipHigh-TCA(100253),
								zte-correctHCS-TCA(100306),
								zte-RxCell-TCA(100307),
								zte-TxCell-TCA(100308),
								zte-atmfM4TCProtoCurrDiscardHECViol-TCA(100309),
								zte-atmfM4UpcNpcCurrDiscardedCells-TCA(100310),
								zte-atmfM4UpcNpcCurrPassedCells-TCA(100311),
								zte-H-atmfM4UpcNpcCurrDisCells-TCA(100312),
								zte-H-atmfM4UpcNpcCurrPassedCells-TCA(100313),
								zte-ASON-VC4-SPC-MAX-NUM-TCA(100500),
								zte-ASON-VC4-SPC-MIN-NUM-TCA(100501),
								zte-ASON-VC4-SPC-AVG-NUM-TCA(100502),
								zte-ASON-EPL-SPC-MAX-NUM-TCA(100503),
								zte-ASON-EPL-SPC-MIN-NUM-TCA(100504),
								zte-ASON-EPL-SPC-AVG-NUM-TCA(100505),
								zte-ASON-VC4-SPC-CRT-SUCC-COUNT-TCA(100506),
								zte-ASON-EPL-SPC-CRT-SUCC-COUNT-TCA(100507),
								zte-ASON-VC4-SPC-CRT-FAIL-COUNT-TCA(100508),
								zte-ASON-EPL-SPC-CRT-FAIL-COUNT-TCA(100509),
								zte-ASON-VC4-SPC-CRANK-BACK-COUNT-TCA(100510),
								zte-ASON-VC4-SPC-CRANK-BACK-COUNT-PER-TRA-TCA(100511),
								zte-ASON-VC4-SPC-SWITCH-RECOV-COUNT-TCA(100512),
								zte-opticalFibreError(100602),
								zte-lockPhaseRingError(100603),
								zte-inputPowerLow(100604),
								zte-outClockFailure(100605),
								zte-coderFailer(100606),
								zte-clocksOL1I(100607),
								zte-clocksE1I(100608),
								zte-ocxo(100610),
								zte-lockPhaseRingLost(100611),
								zte-EthPortHalfDuxLnk(100617),
								zte-incorrectBoardState(100618),
								zte-backupBrdNotReady(100620),
								zte-LoopAtten-TCA(100622),
								zte-SignalNoiseRat-TCA(100625),
								zte-NoOptIn-TCA(100628),
								zte-LowOptIn(100629),
								zte-NoOptOut-TCA(100630),
								zte-LowOptOut(100631),
								zte-E-Mod-notCert(100633),
								zte-eptModuleRateMismatch(100634),
								zte-OCI(100635),
								zte-BDI(100636),
								zte-CB-ext-shelf(100638),
								zte-ABN-ShelfFan-1(100640),
								zte-ABN-ShelfFan-2(100641),
								zte-ABN-ShelfFan-3(100642),
								zte-ABN-ShelfFan-4(100643),
								zte-ABN-ShelfFan-5(100644),
								zte-ABN-ShelfFan-6(100645),
								zte-ABN-BoxA-Fan0(100646),
								zte-ABN-BoxA-Fan1(100647),
								zte-ABN-BoxA-Fan2(100648),
								zte-ABN-BoxA-Fan3(100649),
								zte-ABN-BoxA-Fan4(100650),
								zte-ABN-BoxA-Fan5(100651),
								zte-ABN-BoxA-Fan6(100652),
								zte-ABN-BoxA-Fan7(100653),
								zte-ABN-BoxB-Fan0(100654),
								zte-ABN-BoxB-Fan1(100655),
								zte-ABN-BoxB-Fan2(100656),
								zte-ABN-BoxB-Fan3(100657),
								zte-ABN-BoxB-Fan4(100658),
								zte-ABN-BoxB-Fan5(100659),
								zte-ABN-BoxB-Fan6(100660),
								zte-ABN-BoxB-Fan7(100661),
								zte-SP-CPU-TEMP-common(100662),
								zte-SP-CPU-TEMP-critical(100663),
								zte-SP-880m-TEMP-common(100664),
								zte-SP-880m-TEMP-critical(100665),
								zte-SP-880s-TEMP-common(100666),
								zte-SP-880s-TEMP-critical(100667),
								zte-SP-880m-ABN(100668),
								zte-SP-880s-ABN(100669),
								zte-SP-870m-TEMP-common(100670),
								zte-SP-870m-TEMP-critical(100671),
								zte-SP-870s-TEMP-common(100672),
								zte-SP-FGPA-TEMP-common(100673),
								zte-SP-FPGA-TEMP-critical(100674),
								zte-SP-VSC870-OOS(100675),
								zte-Brd-Inn-Link-SW-ABN(100676),
								zte-Both-SFC-Offline(100678),
								zte-SP-870s-TEMP-critical(100679),
								zte-Brd-Type-ABN(100680),
								zte-SFC880-OOS(100681),
								zte-If-Brd-Err(100683),
								zte-IF-Brd-Type-Err(100684),
								zte-no-clock-output-msf(100685),
								zte-concat58-removed(100686),
								zte-port-down(100687),
								zte-Sys-P-OL(100688),
								zte-PortTypeMismatch(100689),
								zte-LO1PPS(100691),
								zte-EEOT(100692),
								zte-LnkFlt(100693),
								zte-timeSW(100694),
								zte-AlmChg(100695),
								zte-externalWarn8(100700),
								zte-externalWarn9(100709),
								zte-externalWarn10(100710),
								zte-externalWarn11(100711),
								zte-externalWarn12(100712),
								zte-externalWarn13(100713),
								zte-externalWarn14(100714),
								zte-externalWarn15(100715),
								zte-externalWarn16(100716),
								zte-AbNorm-Infrare(100717),
								zte-Ltn-Rod-OOO(100718),
								zte-Wrng-Frq-AC-Inpt(100719),
								zte-Rctfr-1-OOO(100720),
								zte-Rctfr-2-OOO(100721),
								zte-Rctfr-3-OOO(100722),
								zte-AC-Flow-12-5A(100723),
								zte-Lack-AC-FlowInfo(100724),
								zte-DC-Flow-50A(100725),
								zte-Lack-DC-FlowInfo(100726),
								zte-Lack-TempInfo(100727),
								zte-Lack-HumiInfo(100728),
								zte-Lack-SmokeInfo(100729),
								zte-Lack-InfareInfo(100730),
								zte-Lack-PowerInfo(100731),
								zte-Lack-FanInfo(100732),
								zte-BB-Sock1-LC(100733),
								zte-BB-Sock2-LC(100734),
								zte-BB-Sock3-LC(100735),
								zte-AC-Low(100736),
								zte-AC-High(100737),
								zte-AC-Freq-Low(100738),
								zte-AC-Freq-High(100739),
								zte-Fuse-Brk(100740),
								zte-Ltn-Rod-Brk(100741),
								zte-DC-Volt-Low(100742),
								zte-DC-Volt-High(100743),
								zte-DC-Fuse1-Brk(100744),
								zte-DC-Fuse2-Brk(100745),
								zte-Rack-Temp-Thrshd1(100748),
								zte-Rack-Temp-Thrshd2(100750),
								zte-Rack-Temp-LowThrshd(100751),
								zte-Rack-Temp-CThrshd(100752),
								zte-Avg-In-V-TCA(100754),
								zte-P-In-V-High(100755),
								zte-P-In-V-Lo(100756),
								zte-Avg-5V-In-TCA(100757),
								zte-Avg-3-3V-In-TCA(100760),
								zte-Avg-2-5V-In-TCA(100763),
								zte-Avg-1-8V-In-TCA(100766),
								zte-Avg-1-2V-In-TCA(100769),
								zte-Avg-1V-In-TCA(100772),
								zte-Avg-0-9V-In-TCA(100775),
								zte-Avg-1-5V-TCA(100778),
								zte-prtSettingUnconsist(100800),
								zte-nodeMACDuplicated(100801),
								zte-topoUnconsist(100802),
								zte-neighbourUnconsist(100803),
								zte-hasNoFreeBandLeft(100804),
								zte-spanPortBandwidthMissmatch(100805),
								zte-lspEstablishUnsuccess(100806),
								zte-HD-DBS-overload(100807),
								zte-CPU-APP-overload(100808),
								zte-RAM-APP-overload(100809),
								zte-HD-APP-overload(100810),
								zte-DIR-Sz-Exc(100811),
								zte-LNK-Office-Brk(100812),
								zte-DB-Space-Low(100813),
								zte-EMS-Disconnected(100814),
								zte-ME-Ver-Mismatch(100815),
								zte-Loss-of-Cont(100838),
								zte-Unexp-MEG-Level(100839),
								zte-Mismerge(100840),
								zte-Unexp-MEP(100841),
								zte-Unexp-Period(100842),
								zte-Port-Agg-Succ(100843),
								zte-Port-Q-Agg-Fail(100844),
								zte-port-0(100845),
								zte-alarmSuppressTask(100846),
								zte-PeriodSaveFail(100848),
								zte-CCM-los(100850),
								zte-lMEP-Msg-Err(100851),
								zte-lMEP-Msg-MD-Err(100852),
								zte-OAMLB-Set-Fail(100854),
								zte-OAMLB-Cncl-Fail(100855),
								zte-lossKeepalive(100900),
								zte-lossOfConection(100901),
								zte-missmatchedUPI(100902),
								zte-clientSignalFailed(100903),
								zte-RSD(100904),
								zte-ER1-10E3(100906),
								zte-ts16RecvAIS(100907),
								zte-RCRC4(100908),
								zte-ensureBWexcTotalBW(100909),
								zte-ensureBWexcHalfTotalBW(100910),
								zte-vcgLos(100911),
								zte-tsf(100912),
								zte-LFD(100913),
								zte-GFP-OOF(100914),
								zte-PPP-HDLC-OOF(100915),
								zte-IrrUserConfDestAddr(100916),
								zte-TC-RDI(100917),
								zte-ODI(100918),
								zte-TC-IAIS(100919),
								zte-LTC(100920),
								zte-TC-IEC-TCA(100921),
								zte-TC-OEI-TCA(100922),
								zte-TC-REI-TCA(100923),
								zte-dLoCV-sink(100925),
								zte-dTTSI-mismatch-sink(100926),
								zte-dTTSI-mismerge-sink(100927),
								zte-dExcess-sink(100928),
								zte-dServer-sink(100929),
								zte-dLoCV-sinkForw(100930),
								zte-dTTSI-mismatch-sinkForw(100931),
								zte-dTTSI-mismerge-sinkForw(100932),
								zte-dExcess-sinkForw(100933),
								zte-dServer-sinkForw(100934),
								zte-dLoCV-srcBack(100935),
								zte-dTTSI-mismatch-srcBack(100936),
								zte-dTTSI-mismerge-srcBack(100937),
								zte-dExcess-srcBack(100938),
								zte-dServer-srcBack(100939),
								zte-vcgPortTermLoop(100940),
								zte-vcgCapacityLessThanRequired(100942),
								zte-vcgSourceSthNotDeleted(100943),
								zte-LOSW(100944),
								zte-LOSWS-TCA(100945),
								zte-LOL(100946),
								zte-Nego-Mode-Miss(100947),
								zte-IAE-TCA(100957),
								zte-BIAE-TCA(100958),
								zte-LOFLOM(100959),
								zte-MSIM(100960),
								zte-Cell-Starv-TCA(100961),
								zte-Err-Cell-Head-TCA(100962),
								zte-No-Violation-TCA(100963),
								zte-SSF(100964),
								zte-LOC(100965),
								zte-MMG(100966),
								zte-UNM(100967),
								zte-UNP(100968),
								zte-UNPhb(100969),
								zte-LCK(100970),
								zte-OOM(100971),
								zte-Port-Flow-Over(100972),
								zte-recvByteDropInStreamTCx-TCA(101025),
								zte-recvTtlOuttimePKG-TCA(101026),
								zte-recvHeadCrcPKG-TCA(101027),
								zte-recvCrcPKG-TCA(101028),
								zte-recvSrcIsLocalPKG-TCA(101029),
								zte-recvUnknownPKG-TCA(101030),
								zte-recvPkgDrop-TCA(101031),
								zte-notKeepAlive(101032),
								zte-recvPkgInStream-TCA(101033),
								zte-recvByteInStream-TCA(101034),
								zte-recvSigleByte-TCA(101036),
								zte-recvNonSiglePkg-TCA(101037),
								zte-recvNonSigleByte(101038),
								zte-sendSigleByte-TCA(101040),
								zte-sendNonSiglePkg-TCA(101041),
								zte-sendNonSigleByte-TCA(101042),
								zte-sendFailedPKG-TCA(101045),
								zte-recvIdleFrame-TCA(101046),
								zte-recvIdleFrameByte-TCA(101047),
								zte-recvCtrlFrame-TCA(101048),
								zte-recvCtrlFrameByte-TCA(101049),
								zte-recvFareFrame-TCA(101050),
								zte-recvFareFrameByte-TCA(101051),
								zte-recvTTLErrFrameByte-TCA(101052),
								zte-recvLenErrFrame-TCA(101053),
								zte-recvLenErrFrameByte-TCA(101054),
								zte-excNode(101056),
								zte-recvPMDErrFrame-TCA(101055),
								zte-redirSingleFrame-TCA(101057),
								zte-redirSingleByte-TCA(101058),
								zte-redirNonSingleFrame-TCA(101059),
								zte-redirNonSingleByte-TCA(101060),
								zte-sendDropByPMDFrame-TCA(101061),
								zte-recvGFPCtrlFrames-TCA(101062),
								zte-recvGFPDrpCtrlFrames-TCA(101063),
								zte-recvGFPCoreHECError-TCA(101064),
								zte-recvGFPTypeHECCheckFailure-TCA(101065),
								zte-recvGFPextHECCheckFailure-TCA(101066),
								zte-recvGFPMisTypeError-TCA(101067),
								zte-recvGFPMisUPIError-TCA(101068),
								zte-recvGFPbadFCSFrames-TCA(101069),
								zte-recvGFPBytes-TCA(101070),
								zte-recvGFPUserDataFrames-TCA(101071),
								zte-recvGFPUsrDataNullExtHeaderFrames-TCA(101072),
								zte-recvGFPUsrDataLinearFrames-TCA(101073),
								zte-recvGFPUsrDataRingFrames-TCA(101074),
								zte-recvGFPUsrDataFramesWith1FCS-TCA(101075),
								zte-recvGFPIdleFrames-TCA(101076),
								zte-recvGFPClientManagementFrames-TCA(101077),
								zte-recvGFPClientMgmntFramesWithFCS-TCA(101078),
								zte-recvGFPTypeFilterDropped-TCA(101079),
								zte-recvGFPSingleCorrected-cHEC-TCA(101080),
								zte-recvGFPMultiCorrected-cHEC(101081),
								zte-recvGFPSingleCorrected-tHEC-TCA(101082),
								zte-recvGFPMultiCorrected-tHEC(101083),
								zte-transGFPDataFrames-TCA(101084),
								zte-transGFPIdleFrames-TCA(101085),
								zte-transGFPClientDataFrames-TCA(101086),
								zte-transGFPClientMgmntFrames-TCA(101087),
								zte-transGFPBytes-TCA(101088),
								zte-agcv-TCA(101089),
								zte-LDID-TCA(101090),
								zte-OOF-TCA(101091),
								zte-FEBC-TCA(101092),
								zte-NDF-TCA(101093),
								zte-HDB3EER-TCA(101094),
								zte-BDEG-TCA(101096),
								zte-BEXC-TCA(101097),
								zte-SBPinTAR-TCA(101099),
								zte-SBBinTAR-TCA(101100),
								zte-nonSBPinTAR-TCA(101101),
								zte-nonSBBinTAR-TCA(101102),
								zte-SBPinTDR-TCA(101103),
								zte-SBBinTDR-TCA(101104),
								zte-nonSBPinTDR-TCA(101105),
								zte-nonSBBinTDR-TCA(101106),
								zte-recvLostByte-TCA(101107),
								zte-recvGFPDropFrame-TCA(101108),
								zte-sendGFPDropFrame-TCA(101109),
								zte-recvPPPHDLCFrame-TCA(101110),
								zte-recvPPPHDLCByte-TCA(101111),
								zte-recvPPPHDLCDropFrame-TCA(101112),
								zte-recvPPPHDLCUnkownTypeFrame-TCA(101113),
								zte-recvPPPHDLCFCSErrorFrame-TCA(101114),
								zte-recvPPPHDLCSourceDropFrame-TCA(101115),
								zte-sendPPPHDLCFrame-TCA(101116),
								zte-sendPPPHDLCByte-TCA(101117),
								zte-sendPPPHDLCDropFrame-TCA(101118),
								zte-ring0uploadByte-TCA(101119),
								zte-ring0downloadByte-TCA(101120),
								zte-ring0redirByte-TCA(101121),
								zte-ring1uploadByte-TCA(101122),
								zte-ring1downloadByte-TCA(101123),
								zte-ring1redirByte-TCA(101124),
								zte-recvMPLSFrame-TCA(101127),
								zte-recvMPLSTotalFrameTCA(101128),
								zte-recvMPLSCtrlFrame-TCA(101129),
								zte-sendMPLSFrame-TCA(101130),
								zte-sendMPLSTotalFrame-TCA(101131),
								zte-sendMPLSCtrlFrame-TCA(101132),
								zte-ActualMemInVCG-TCA(101134),
								zte-FailedMemInVCG-TCA(101135),
								zte-provisionedMemInVCG-TCA(101136),
								zte-recvJabberFrame-TCA(101137),
								zte-portForceLinkdown(101138),
								zte-InClp0DropCells-TCA(101140),
								zte-InClp1DropCells-TCA(101141),
								zte-InEPDDropCells-TCA(101142),
								zte-InEPDDropFrames-TCA(101143),
								zte-InUPCTaggingCells-TCA(101144),
								zte-InUPCDropCells-TCA(101145),
								zte-EgClp0DropCells-TCA(101146),
								zte-EgClp1DropCells-TCA(101147),
								zte-EgEPDDropCells-TCA(101148),
								zte-EgEPDDropFrames-TCA(101149),
								zte-Uncorrecthcs-TCA(101150),
								zte-STP-FCC(101151),
								zte-pause-FCC(101152),
								zte-LACP-FCC(101153),
								zte-InconsistJUMBO-supported(101154),
								zte-InconsistJUMBO-nonsupported(101155),
								zte-misTRUNKGroup-PortAcess(101156),
								zte-misTRUNKGroup-VB(101157),
								zte-CSF-LCCSynch(101158),
								zte-CSF-unknownCS(101159),
								zte-PLCT(101160),
								zte-TLCT(101161),
								zte-PLCR(101162),
								zte-TLCR(101163),
								zte-VCGP-CCTL(101164),
								zte-RecvStuffSymbls-TCA(101165),
								zte-RecvSupperBlocks-TCA(101166),
								zte-RecvCrcSupperBlocks-TCA(101167),
								zte-Recv10BErrSymbols-TCA(101168),
								zte-SendStuffSymbols-TCA(101169),
								zte-SendSupperBlocks-TCA(101170),
								zte-Send10BErrSymbols-TCA(101171),
								zte-RecvStartOf10BSymbol-TCA(101172),
								zte-Recv10BInvalidSymbols-TCA(101173),
								zte-SendStartOf10BSymbol-TCA(101174),
								zte-Send10BInvalidSymbols-TCA(101175),
								zte-SendIns10BIdleSymble-TCA(101176),
								zte-SendDel10BIdleSymble-TCA(101177),
								zte-Recv-IP-B-TCA(101178),
								zte-Recv-IP-Fr-TCA(101179),
								zte-Recv-SNMP-B-TCA(101180),
								zte-Recv-SNMP-Fr-TCA(101181),
								zte-Recv-ARP-B-TCA(101182),
								zte-Recv-ARP-Fr-TCA(101183),
								zte-Recv-RARP-B-TCA(101184),
								zte-Recv-RARP-Fr-TCA(101185),
								zte-Recv-UDP-B-TCA(101186),
								zte-Recv-UDP-Fr-TCA(101187),
								zte-Recv-TCP-B-TCA(101188),
								zte-Recv-TCP-Fr-TCA(101189),
								zte-Recv-ICMP-B-TCA(101190),
								zte-Recv-ICMP-Fr-TCA(101191),
								zte-Recv-IGMP-B-TCA(101192),
								zte-Recv-IGMP-Fr-TCA(101193),
								zte-Recv-PIM-B-TCA(101194),
								zte-Recv-PIM-Fr-TCA(101195),
								zte-Recv-EGP-B-TCA(101196),
								zte-Recv-EGP-Fr-TCA(101197),
								zte-Recv-OSPFIGP-B-TCA(101198),
								zte-Recv-OSPFIGP-Fr-TCA(101199),
								zte-Recv-STP-B-TCA(101200),
								zte-Recv-STP-Fr-TCA(101201),
								zte-Recv-LACP-B-TCA(101202),
								zte-Recv-LACP-Fr-TCA(101203),
								zte-Recv-802-1X-B-TCA(101204),
								zte-Recv-802-1X-Fr-TCA(101205),
								zte-Recv-frm-bps-TCA(101206),
								zte-Recv-fps-TCA(101207),
								zte-Send-bps-TCA(101208),
								zte-Send-fps-TCA(101209),
								zte-Trns-UC-fps-to-Rnlt-TCA(101210),
								zte-Trns-UC-bps-to-Rnlt-TCA(101211),
								zte-Trns-non-UC-fps-to-Rnlt-TCA(101212),
								zte-Trns-non-UC-bps-to-Rnlt-TCA(101213),
								zte-Add-UC-fps-to-Rnlt-TCA(101214),
								zte-Add-UC-bps-to-Rnlt-TCA(101215),
								zte-Add-non-UC-fps-to-Rnlt-TCA(101216),
								zte-Add-non-UC-bps-to-Rnlt-TCA(101217),
								zte-Drop-UC-fps-from-Rnlt-TCA(101218),
								zte-Drop-UC-bps-from-Rnlt-TCA(101219),
								zte-Drop-non-UC-fps-from-Rnlt-TCA(101220),
								zte-Drop-non-UC-bps-from-Rnlt-TCA(101221),
								zte-Recv-IP-bps-TCA(101222),
								zte-Recv-IP-fps-TCA(101223),
								zte-Recv-SNMP-bps-TCA(101224),
								zte-Recv-SNMP-fps-TCA(101225),
								zte-Recv-ARP-bps-TCA(101226),
								zte-Recv-ARP-fps-TCA(101227),
								zte-Recv-RARP-bps-TCA(101228),
								zte-Recv-RARP-fps-TCA(101229),
								zte-Recv-UDP-bps-TCA(101230),
								zte-Recv-UDP-fps-TCA(101231),
								zte-Recv-TCP-bps-TCA(101232),
								zte-Recv-TCP-fps-TCA(101233),
								zte-Recv-ICMP-bps-TCA(101234),
								zte-Recv-ICMP-fps-TCA(101235),
								zte-Recv-IGMP-bps-TCA(101236),
								zte-Recv-IGMP-fps-TCA(101237),
								zte-Recv-PIM-bps-TCA(101238),
								zte-Recv-PIM-fps-TCA(101239),
								zte-Recv-EGP-bps-TCA(101240),
								zte-Recv-EGP-fps-TCA(101241),
								zte-Recv-OSPFIGP-bps-TCA(101242),
								zte-Recv-OSPFIGP-fps-TCA(101243),
								zte-Recv-STP-bps-TCA(101244),
								zte-Recv-STP-fps-TCA(101245),
								zte-Recv-LACP-bps-TCA(101246),
								zte-Recv-LACP-fps-TCA(101247),
								zte-Recv-802-1X-bps-TCA(101248),
								zte-Recv-802-1X-fps-TCA(101249),
								zte-Send-req-OAM-Fr-TCA(101382),
								zte-Send-rsp-OAM-Fr-TCA(101383),
								zte-Recv-req-OAM-Fr-TCA(101384),
								zte-Recv-rsp-OAM-Fr-TCA(101385),
								zte-NE-send-clt-data-Fr-TCA(101386),
								zte-NE-DCDF-TCA(101387),
								zte-FE-DCDF-TCA(101389),
								zte-Recv-GSF-TCA(101390),
								zte-Recv-GSB-TCA(101391),
								zte-Recv-YSF-TCA(101392),
								zte-Recv-YSB-TCA(101393),
								zte-Recv-RSFD-TCA(101394),
								zte-Recv-RSBD-TCA(101395),
								zte-Send-GSF-TCA(101396),
								zte-Send-GSB-TCA(101397),
								zte-Send-YSF-TCA(101398),
								zte-Send-YSB-TCA(101399),
								zte-Send-GSFD-TCA(101400),
								zte-Send-GSBD-TCA(101401),
								zte-Send-YSFD-TCA(101402),
								zte-Send-YSBD-TCA(101403),
								zte-Drop-Cells-TCA(101404),
								zte-Wrong-Ins-Cells-TCA(101405),
								zte-SDTP-Check-Errs-TCA(101406),
								zte-N-FL-TCA(101407),
								zte-F-FL-TCA(101409),
								zte-F-DS-TCA(101411),
								zte-N-DS-TCA(101412),
								zte-Snd-DF-TCA(101413),
								zte-Rcv-FDR-TCA(101414),
								zte-Snd-FDR-TCA(101415),
								zte-NE-Drp-TCA(101440),
								zte-FE-Drp-TCA(101441),
								zte-MalForm-Pkt-TCA(101444),
								zte-Buff-OverRun-TCA(101445),
								zte-Pkt-Loss-TCA(101446),
								zte-R-Pkt-Loss-TCA(101447),
								zte-Exc-Pkt-Loss-Rate-TCA(101450),
								zte-IV-IMA-TCA(101451),
								zte-OIF-IMA-TCA(101452),
								zte-Tx-UUS-IMA-TCA(101453),
								zte-Rx-UUS-IMA-TCA(101454),
								zte-Tx-UUS-IMA-FE-TCA(101455),
								zte-Rx-UUS-IMA-FE-TCA(101456),
								zte-GR-FC-TCA(101457),
								zte-GR-FC-FE-TCA(101458),
								zte-Conn-Degrade(102001),
								zte-RSVP-Hello-Down(102002),
								zte-LMP-Hello-Down(102003),
								zte-NB-Dscv-Fail(102004),
								zte-UA-Sgn-req(102005),
								zte-Link-Property-Corr-Fail(102006),
								zte-Service-Dscv-Fail(102007),
								zte-Node-Parameter-not-Configured(102008),
								zte-Main-ctrl-Mod-Fail(102009),
								zte-conn-ctrl-Mod-Fail(102010),
								zte-Link-Res-Mgm-Mod-Fail(102011),
								zte-MS-Mod-Fail(102012),
								zte-Nbase-Entry-Mod-Fail(102013),
								zte-Nbase-Init-Mod-Fail(102014),
								zte-DB-Access-Fail(102015),
								zte-Data-Sync-Fail(102016),
								zte-Service-fails(102017),
								zte-ADAPTOR-fails(102018),
								zte-DA-fails(102019),
								zte-TRA-MGR-fails(102020),
								zte-DB-MGR-fails(102021),
								zte-CPA-MGR-fails(102022),
								zte-Ex-fails(102023),
								zte-TrnsP-Dscv-FAIL(102025),
								zte-MISconn(102026),
								zte-MISWIRE(102027),
								zte-Svc-DEG(102028),
								zte-Remn-conn(102029),
								zte-RESC-PRP-DISACCORD(102030),
								zte-Prss-Hangup(103000),
								zte-Adm-PASSWD-CHG(103002),
								zte-WR-DB-Fail(103003),
								zte-RD-DB-Fail(103004),
								zte-ALM-Buff-80PC(103005),
								zte-ALM-Buff-FULL(103006),
								zte-BK-BRD-CP-FILE-FAIL(103007),
								zte-BK-BRD-FTP-FILE-FAIL(103008),
								zte-Recur-Deep-Del-DB-ND(103009),
								zte-CPU-Usg-Lvl3(103010),
								zte-CPU-Usg-Lvl2(103011),
								zte-CPU-Usg-Lvl1(103012),
								zte-Detect-Flash-Fail(103013),
								zte-Flash-not-work(103014),
								zte-BK-BRD-WR-nvram-Fail(103015),
								zte-Dstr-SYS-Fail(103016),
								zte-APP-RAM-Fail-QOS(103017),
								zte-MSG-Lost-at-Wr(103018),
								zte-FTP-USR-Login(103020),
								zte-Term-Link-Brk-Cfg(103021),
								zte-Term-Link-Brk-Cpy(103022),
								zte-FTP-USR-Del-File(103023),
								zte-FTP-USR-Upload-File-to-Dev(103024),
								zte-FTP-USR-Cpy-File-from-Dev(103025),
								zte-FTP-SVR-Send-Msg-Fail(103026),
								zte-Port-State-CHG(103027),
								zte-VL-Port-State-CHG(103028),
								zte-NB-State-CHG(103029),
								zte-VNB-State-CHG(103030),
								zte-Port-Certify-Fail(103031),
								zte-VPort-Certify-Fail(103032),
								zte-Port-Recv-Err-Pkg(103033),
								zte-VPort-Recv-Err-Pkg(103034),
								zte-DB-Sz-Big(103035),
								zte-Port-Cfg-err(103036),
								zte-VPort-Cfg-err(103037),
								zte-RSnd-Port-Pkg(103038),
								zte-RSnd-VPort-Pkg(103039),
								zte-Snd-MD5-Fail(103040),
								zte-Rcv-Err-Pkg-Lnk-Brk(103042),
								zte-Rcv-DD-Pkg-Lnk-Brk(103043),
								zte-Rcv-Hello-Pkg-Lnk-Brk(103044),
								zte-Rcv-Hello-Pkg-TmOut-Lnk-Brk(103045),
								zte-Mgr-Down-Lnk-Brk(103046),
								zte-Port-Down-Lnk-Brk(103047),
								zte-Port-State-Chg-Lnk-Brk(103048),
								zte-TCP-Rd-DB-Init-Fail(103049),
								zte-TCP-Wait-Tmout(103050),
								zte-TCP-Err-Start-TCB(103051),
								zte-TCP-Too-Many-Lnk(103052),
								zte-TCP-Who-am-I(103053),
								zte-TCP-Port-In-Use(103054),
								zte-TCP-Pkg-Err-Ver(103055),
								zte-TCP-Pkg-Err-Checksum(103056),
								zte-TCP-Rcv-Silent-Time(103057),
								zte-TCP-Pkg-no-Lnk(103058),
								zte-TCP-Pkg-in-Adv(103059),
								zte-TCP-Pkg-Ack-Err(103060),
								zte-TCP-Pkg-Old-No(103061),
								zte-TCP-Pkg-Ack-not-Snd(103062),
								zte-TCP-Rcv-RSnd-Thshld(103063),
								zte-TCP-Pkg-Ack-Dup(103064),
								zte-TCP-Rcv-Window0-Pkg(103065),
								zte-TCP-Rcv-Saved-Pkg(103066),
								zte-TCP-Rcv-MD5-Fail-Pkg(103067),
								zte-TCP-Rcv-Pkg-err-head-len(103068),
								zte-TCP-Rcv-Pkg-err-offset(103069),
								zte-TCP-Rcv-Pkg-Secu-Fail(103070),
								zte-TCP-Rcv-Tmout-Pkg(103071),
								zte-TCP-Snd-Allct-Pkg-Err(103072),
								zte-TCP-Snd-Err-Ver-Pkg(103073),
								zte-No-License(102041),
								zte-TCP-Del-Err-State-Lnk(103075),
								zte-TCP-RSnd-Allct-Pkg-Err(103076),
								zte-TCP-Clr-Inexist-Lnk(103077),
								zte-TCP-Calc-Avai-Wndw-Err(103078),
								zte-TCP-Wrt-Err(103079),
								zte-Rcv-BGP-Pkg-Fail-Md5-Chk(103080),
								zte-Prtcl-Snd-Msg-App-Fail(103081),
								zte-UDP-MP-INIT-CLK(103082),
								zte-UDP-Req-RAM-Fail(103083),
								zte-UDP-Rcv-Pkg-Err-Head(103084),
								zte-UDP-Rcv-Pkg-Err-IP-Ver(103085),
								zte-UDP-Rcv-Pkg-Err-Chksum(103086),
								zte-UDP-Rcv-Pkg-Err-Port(103087),
								zte-UDP-Snd-Pkg-Err-IP-Ver(103088),
								zte-UDP-Snd-Pkg-Err-Port(103089),
								zte-ARP-Req-RAM-Fail-Init(103090),
								zte-ARP-Init-Rt-Fail(103091),
								zte-Sz-Rt-Limit(103092),
								zte-Init-Buff-Fail(103093),
								zte-Tra-Lnk-TypeMisMatch(102043),
								zte-Op-Dyn-Rt-If-Fail(103095),
								zte-Add-Static-Rt-Fail(103096),
								zte-Tra-route-diss-constr(102044),
								zte-Wrg-If-Type(103098),
								zte-IP-Cfg-Data-Lost-SW(103099),
								zte-Crt-Tmr-Fail(103100),
								zte-Spc-ACL-Chk-Not-Suff(103101),
								zte-If-Up(103102),
								zte-If-Down(103103),
								zte-Crt-DB-Nd-Fail-Crt-If(103104),
								zte-Rcv-Pkg-Len-Less-Mix-Len(103105),
								zte-Rcv-UN-Type-Pkg(103106),
								zte-Rcv-Pkg-IP-Hd-Too-Shrt(103107),
								zte-Rcv-Pkg-IP-Len-Err(103108),
								zte-Rcv-Pkg-IP-Ver-Err(103109),
								zte-Rcv-Pkg-IP-ChkSum-Err(103110),
								zte-Rcv-Pkg-IP-Invld-Src-Addr(103111),
								zte-Rcv-Pkg-IP-Invld-Dest-Addr(103112),
								zte-Rcv-Pkg-IP-UnRch-Dest-Addr(103113),
								zte-Rcv-Pkg-IP-UnKwn-Prtcl-Type(103114),
								zte-IP-Slc-Op-Fail(103115),
								zte-ReAssm-IP-Slc-Fail(103116),
								zte-ReAssm-IP-Slc-TmOut(103117),
								zte-Wrg-ICMP-Head-Len(103118),
								zte-ICMP-CRC-Err(103119),
								zte-Req-RAM-ICMP-Rsp-Fail(103120),
								zte-Snd-ICMP-Rsp-Fail(103121),
								zte-Chnnl-Mode-Chg(103122),
								zte-Rt-Map-Invld-On-Crd(103123),
								zte-Rt-Map-No-Take-Efft(103124),
								zte-Too-Much-Seq-Rt-Plcy(103125),
								zte-Too-Much-ACL-Tb-on-Card(103126),
								zte-Too-Much-ACL-Tb-on-Card-IN(103127),
								zte-Too-Much-ACL-Tb-on-Card-OUT(103128),
								zte-Too-Much-ACL-Rule-on-Card(103129),
								zte-NCP-ACL-Req-RAM-Fail(103130),
								zte-NCP-ACL-Wr-Buff-Exc-Cmplx-Lot(103131),
								zte-RP-ACL-Req-RAM-Fail(103132),
								zte-NCP-ACL-Prcss-Fail(103133),
								zte-Rt-Row-Exhaust(103134),
								zte-IGMP-Memb-Join(103136),
								zte-IGMP-Memb-leave(103137),
								zte-Rcv-OAM-Data-TmOut(103138),
								zte-Snd-Msg-OAM-Layer-Fail(103139),
								zte-Disp-Buff-Full(103140),
								zte-MAC-Chg-Dyn-ARP-Row(103141),
								zte-Exc-ARP-Prt-Row-Lmt(103142),
								zte-Rcv-ARP-Msg-Same-Src-Dst(103143),
								zte-Rcv-ARP-Msg-Addr-Cnflct-Lcl(103144),
								zte-Drop-Wrg-Usr-DHCP-Snooping-ARP(103145),
								zte-SUPERVLAN-IP-POOL-Filer-Rcv-ARP-Pkt-Not-In-IP-POOL-Seg-Drop(103146),
								zte-NB-Est-Adj-Relate(103147),
								zte-NB-Fail(103148),
								zte-Rcv-LSP-Pkt-From-Fail-NB(103149),
								zte-Rcv-SNP-Pkt-From-Fail-NB(103150),
								zte-Rcv-LSP-Pkt-From-Unkn-NB(103151),
								zte-Rcv-SNP-Pkt-From-Unkn-NB(103152),
								zte-NB-Auth-Fail(103153),
								zte-LSP-Pkg-Auth-Fail(103154),
								zte-SNP-Pkg-Auth-Fail(103155),
								zte-Rcv-Ill-Pkg(103156),
								zte-ISIS-Add-Rt-Fail(103157),
								zte-ISIS-Req-RAM-Fail(103158),
								zte-ISIS-no-or-Multi-LSP-rtId(103159),
								zte-ISIS-Start-Hot-Stby-Err(103160),
								zte-Cfg-ISIS-Agg-Info-Buff-Full(103161),
								zte-RMON-Grp-Err(103162),
								zte-RMON-Rcv-Msg-Head-Err(103163),
								zte-RMON-Rcv-Msg-Data-Err(103164),
								zte-RMON-Rcv-Msg-RspZ-Err(103165),
								zte-RMON-Rcv-Msg-Id-Err(103166),
								zte-RMON-Rcv-Cmd-Id-Err(103167),
								zte-RMON-Rcv-Cmd-Para-Err(103168),
								zte-RMON-Rcv-Cmd-Num-Para-Err(103169),
								zte-RMON-Grp-Idx-Err(103170),
								zte-RMON-Buff-Exhause(103171),
								zte-RMON-Inn-Cnflct(103172),
								zte-RMON-Del-Row-Err(103173),
								zte-RMON-Add-Row-Err(103174),
								zte-RMON-Cfg-Info-State-Tb-Un(103175),
								zte-RMON-Stat-Table-Empty(103176),
								zte-RMON-His-Table-Empty(103177),
								zte-RMON-Alm-Table-Empty(103178),
								zte-RMON-MM-Table-Empty(103179),
								zte-RMON-TN-MM-Table-Empty(103180),
								zte-RMON-Mtx-Table-Empty(103181),
								zte-RMON-Filter-Table-Empty(103182),
								zte-RMON-Catch-Table-Empty(103183),
								zte-RMON-Event-Table-Empty(103184),
								zte-RMON-Tmr-Err(103185),
								zte-RMON-Not-Start(103186),
								zte-NO-If-Start-RMON(103187),
								zte-RMON-RCV-Pkg-Err(103188),
								zte-RMON-Smpl-Type-Err(103189),
								zte-RMON-Alm-Grp-Adm-OID-Err(103190),
								zte-Rsrc-Not-Exist(103191),
								zte-Stat-Idx-to-Del-Not-Exist(103192),
								zte-His-Idx-to-Del-Not-Exist(103193),
								zte-Alm-Idx-to-Del-Not-Exist(103194),
								zte-MM-Idx-to-Del-Not-Exist(103195),
								zte-TN-MM-Idx-to-Del-Not-Exist(103196),
								zte-Mtx-Idx-to-Del-Not-Exist(103197),
								zte-Flt-Idx-to-Del-Not-Exist(103198),
								zte-Catch-Idx-to-Del-Not-Exist(103199),
								zte-Ev-Idx-to-Del-Not-Exist(103200),
								zte-Src-Rt-Chk-Fail-Alm(103201),
								zte-V-Sw-Row-Crt-Del-Ntif(103202),
								zte-ACL-Row-Bd-If-Ex-16-Mask(103203),
								zte-Aft-Updt-ACL-Row-Bd-If-Ex-16-Mask(103204),
								zte-Drv-Err-Bd-ACL-If-Too-Much-QOS(103205),
								zte-Drv-Err-Bd-ACL-If-QOS-Para(103206),
								zte-Drv-Err-Bd-ACL-If(103207),
								zte-Drv-Err-Bd-ACL-If-ACL-Ly2(103208),
								zte-Drv-Err-Bd-ACL-If-ACL-Spec(103209),
								zte-IP-Data-Pkg-ACL-Rule-LOG(103210),
								zte-Add-Msg-Chk-Fuc-Hi-Sw-Prtcl-Err(103211),
								zte-Card-Del-Bd-Nm-ACL-Rstart(103212),
								zte-VRRP-State-Chg(103213),
								zte-RIP-Req-RAM-Fail(103214),
								zte-RIP-Rele-RAM-Fail(103215),
								zte-RIP-Crt-Tmr-Fail(103216),
								zte-RIP-Rt-Tab-Full(103217),
								zte-RIP-NB-Not-In-SN-Or-BC(103218),
								zte-Simp-Cert-Not-to-Snd-Pkg(103219),
								zte-RIP-Ign-Ill-Pkg(103220),
								zte-RIP-NB-Fail(103221),
								zte-RIP-Port-Dn(103222),
								zte-RIP-Port-Up(103223),
								zte-Crt-BGP-Fail(103224),
								zte-Crt-Prtcl-Tmr-Fail(103225),
								zte-Crt-NB-Fail(103226),
								zte-Crt-NB-Tmr-Fail(103227),
								zte-BGP-N-TCB-Psv-Lst(103228),
								zte-BGP-N-TCB-Init-Crt-Lnk(103229),
								zte-BPG-Try-Lst-If-Bd-Lcl-Addr(103230),
								zte-BGP-Psv-Lst-If-TCB-Strt-Fail(103231),
								zte-BGP-Init-Crt-Lnk-If-TCB-Strt-Fail(103232),
								zte-NB-Lnk-Brk(103233),
								zte-NB-Psw-Chg(103234),
								zte-NB-Jn-Grp-Fail(103235),
								zte-Port-Dn-NB-Lnk-Brk(103236),
								zte-Port-Addr-Chg-NB-Lnk-Brk(103237),
								zte-Rd-Rcv-Buff-Err(103238),
								zte-NB-Rtry-TmOut(103239),
								zte-NB-HT-TmOut(103240),
								zte-NB-KA-TmOut(103241),
								zte-ST-Mach-Err(103242),
								zte-Rcv-Ntf-Lnk-Brk(103243),
								zte-Rcv-un-Rec-Pkg(103244),
								zte-Msg-Head-Err(103245),
								zte-Wrg-OPEN-Msg(103246),
								zte-Wrg-UPDATE-Msg(103247),
								zte-NB-Rcv-Upd-no-Rsrc(103248),
								zte-NB-Rcv-Upd-NLRI-Max-Pref(103249),
								zte-Rcv-Inv-Rt(103250),
								zte-NB-Rcv-Upd-RD-Not-0-Ign(103251),
								zte-Wrg-KA-Msg(103252),
								zte-Wrg-NTF-Msg(103253),
								zte-Snd-Msg-Fail(103254),
								zte-Snd-OPEN-Msg-Fail(103255),
								zte-Snd-KA-Msg-Fail(103256),
								zte-Snd-NTF-Msg-Fail(103257),
								zte-Snd-UPD-Reach-Msg-Fail(103258),
								zte-Snd-UPD-N-Reach-Msg-Fail(103259),
								zte-Try-Snd-Oth-Msg-SPOOL-Not-Empty(103260),
								zte-Crt-SPOOL-Fail(103261),
								zte-BGP-Req-RAM-Fail(103262),
								zte-Ins-Rt-Fail(103263),
								zte-Disp-Prtcl-RAM-Fail(103264),
								zte-ST-Chg(103265),
								zte-Get-NB-Idx-Fail-Crt-NB(103266),
								zte-Del-NB-Frm-Grp-Fail(103267),
								zte-Snd-Rfsh-Msg-Gails(103268),
								zte-Lcl-PPP-Port-Rcv-Peer-IPCP-RTR-Msg(103299),
								zte-ppp-add-route-failed(103300),
								zte-port-recv-virus-Pkg(103301),
								zte-mac-addr-reach-thred(103302),
								zte-mac-addr-less-port-thred(103303),
								zte-write-drv-mac-add-fail(103304),
								zte-En-Prot-Stat(103305),
								zte-Ex-Prot-Stat(103306),
								zte-MAC-Move-Port(103307),
								zte-STP-St-Change(103308),
								zte-MAC-OutInf-InLab-Change(103309),
								zte-Port-With-Loop(103310),
								zte-D-Con-User-OverThred(103311),
								zte-BP-Con-User-OverThred(103312),
								zte-Sys-Con-User-OverThred(103313),
								zte-DHCP-Usr-OnOffLine(103314),
								zte-MLD-McastUsr-Jion(103315),
								zte-MLD-McastUsr-Leave(103316),
								zte-No-BPDU-STPLOOP(103317),
								zte-Recv-BPDU-STPLOOP-LOOP(103318),
								zte-Recv-Better-BPDU-Root(103319),
								zte-Recv-Worse-BPDU-NoRoot(103320),
								zte-SVLAN-Write-Drv-Fail(103321),
								zte-VLAN-Fail-At-Start(103322),
								zte-THPort-Tuvlan-Over(103323),
								zte-PV-Conf-With-OtherS(103324),
								zte-Lacc-Mem-Over(103325),
								zte-Err-Comm-RADIUS(103326),
								zte-RDIUS-C-Not-Available(103327),
								zte-One-VFI-Two-PW(103328),
								zte-LDP-Sig-Err(103329),
								zte-LDP-notify(103330),
								zte-LDP-Neb-Down(103331),
								zte-LDP-Recv-U-TLV(103332),
								zte-LDP-GR-Enable(103333),
								zte-LDP-Std-Change(103334),
								zte-LDP-Clr-Mpls-Nei(103335),
								zte-LDP-S-Msg-TCP(103336),
								zte-LDP-DB-OP-Err(103337),
								zte-LDP-MEM-OP-Err(103338),
								zte-LDP-Req-Timer-Err(103339),
								zte-LDP-Label-Insuf(103340),
								zte-LDP-Label-FEC(103341),
								zte-LDP-RelMsg-Send-Err(103342),
								zte-LDP-IPC-Timeout(103343),
								zte-LDP-Neb-St-Down(103344),
								zte-AMAT-AT-Start(103345),
								zte-AMAT-AT-End(103346),
								zte-AMAT-M-AT(103347),
								zte-VPLS-MAC-Chg(103348),
								zte-L2VPN-UnTLV(103349),
								zte-L2VPN-EnGR(103350),
								zte-L2VPN-VC-Insuf(103351),
								zte-L2VPN-FEC-Insuf(103352),
								zte-L2VPN-OP-DB-Err(103353),
								zte-L2VPN-OP-Mem-Err(103354),
								zte-L2VPN-OP-Timer-Err(103355),
								zte-L2VPN-Label-Insuf(103356),
								zte-ZESR-D-to-U(103357),
								zte-ZESR-D-to-PU(103358),
								zte-ZESR-U-to-D-H(103359),
								zte-ZESR-U-to-D-L(103360),
								zte-ZESR-PU-to-D-H(103361),
								zte-ZESR-PU-to-D-L(103362),
								zte-ZESR-PU-to-U(103363),
								zte-ZESR-D-to-U-U(103364),
								zte-ZESR-U-to-D(103365),
								zte-Tacacs-Cus-Aue-Full(103366),
								zte-Tacacs-Cus-AQue-Full(103367),
								zte-Tacacs-Cus-ACQue-Full(103368),
								zte-Err-Recv-from-Tacacs-Svr(103369),
								zte-Tacacs-Not-Start(103370),
								zte-No-Av-Svr-In-Tacacs(103371),
								zte-Long-Tacacs-Req-Pkg(103372),
								zte-Err-Tacacs-Creq(103373),
								zte-Tacacs-Req-Timeout(103374),
								zte-No-Sup-CerType-Used(103375),
								zte-AcPkg-reach-high-thred(103376),
								zte-Send-AcPkg-to-Svr-Fail(103377),
								zte-Undef-AAA-Meth(103378),
								zte-Err-AAA-Meth-List(103379),
								zte-Not-TacacsG-of-Spec-SvrG(103380),
								zte-Undef-SvrG(103381),
								zte-No-Meb-in-SvrG(103382),
								zte-Unknown-Attr-by-NAS(103383),
								zte-Unknown-P-In-AAA-Apair(103384),
								zte-Unknown-S-In-AAA-Apair(103385),
								zte-START-From-NAS-To-Svr(103386),
								zte-UPDATE-From-NAS-To-Svr(103387),
								zte-STOP-From-NAS-To-Svr(103388),
								zte-AAA-Req-Mem-Err(103389),
								zte-Comm-Alarm-Occ-or-Clear(103390),
								zte-Alm-Occ-by-TCPsynf(103391),
								zte-Alm-Occ-by-TCPsynSC(103392),
								zte-Alm-Occ-by-TCPsynRe(103393),
								zte-SL-Req-BFD-Session(103394),
								zte-BFD-Session-Up(103395),
								zte-Session-Over-Thred-InCPU(103397),
								zte-HQosFRP-Over-Ptab(103398),
								zte-IPI-Ins-Crt-Fail(103399),
								zte-BGP-Ins-Crt-Fail(103400),
								zte-OSPF-Ins-Crt-Fail(103401),
								zte-RIP-Ins-Crt-Fail(103402),
								zte-IPI-Ins-En-Fail(103403),
								zte-IPI-Ins-Ren-Fail(103404),
								zte-IPI-Ins-Timer-Crt-Fail(103405),
								zte-IPI-Crt-OSPF-Ins-ByIrd(103406),
								zte-Pkg-Recv-OSPF-No-Start(103407),
								zte-No-IFG-M-OSPF(103408),
								zte-Dis-OSPF-IFB-Down(103409),
								zte-No-IFG-M-RIP(103410),
								zte-Dis-RIP-IFB-Down(103411),
								zte-IP-CT-Err(103412),
								zte-Mem-Alloc-Err(103413),
								zte-Ins-Route-Err(103414),
								zte-No-Exist-R-Del(103416),
								zte-Cold-start(103417),
								zte-Green-Msg-Tx-ABN(103418),
								zte-Loss-Pkt(103419),
								zte-LIF(103420),
								zte-LODS(103421),
								zte-Tx-Fault(103424),
								zte-Rx-Fault(103425),
								zte-Start-up-FE(103428),
								zte-Config-Aborted(103429),
								zte-Config-Aborted-FE(103430),
								zte-Insufficient-Links(103431),
								zte-Insufficient-Links-FE(103432),
								zte-Blocked-FE(103433),
								zte-GR-Timing-Mis-match(103434),
								zte-LCT-Login(103438),
								zte-PTP-Port-FAIL(103439),
								zte-Slaver-Port-Sw(103440),
								zte-PTP-Node-Fault(103441),
								zte-Loss-1PPS-TOD(103442),
								zte-TRAIM(103443),
								zte-3D-Alarm(103444),
								zte-Loss-Satellite-Sync(103445),
								zte-GPS-Mod-Miss(103446),
								zte-RemoteDiscoveryFail(103447),
								zte-Dying-Gasp(103448),
								zte-Critical-Event(103449),
								zte-OIF(103450),
								zte-Rmt-Dying-Gasp(103482),
								zte-Rmt-Crtcl-Ev(103483),
								zte-UnpPrd(103486),
								zte-UnpMEPId(103487),
								zte-MLPPPGrpFail(103488),
								zte-LCPNegtFail(103489),
								zte-MLPPPMembFail(103490),
								zte-UnExpMegLvl(103492),
								zte-MLPP-Grp-Memb-Dly(103500),
								zte-NCP-Nego-Fail(103501),
								zte-Nb-Dn(103502),
								zte-VNb-Dn(103503),
								zte-SmtGrpI-Fail(103504),
								zte-VLanI-Fail(103505),
								zte-Smtgrp-Mmb-Fail(103506),
								zte-Mac-addr-Msm(103507),
								zte-Rcv-Bding-Lnk(103508),
								zte-Rcv-Mpping-Lnk(103509),
								zte-VRRP-Grp-Chg(103510),
								zte-Tnnl-Dwn(103511),
								zte-VC-Sessn-dispear(103512),
								zte-VC-LDP-Sessn-Dn(103513),
								zte-VC-TE-Tnnl-Sessn-Dn(103514),
								zte-LDP-Nb-Status-Chg(103515),
								zte-Rch-Max-Num(103516),
								zte-BGP-Lnk-Dn(103517),
								zte-Num-Prefx-Alm(103518),
								zte-Num-Prefx-NB(103519),
								zte-NB-Lnk-Dn(103520),
								zte-Out-Tnnl-Fail(103521),
								zte-VPLS-MAC-Excrsn-Rate(103522),
								zte-VPLS-MAC-Lrn-Rate(103523),
								zte-BFD-Sssn-Sprss-Shake(103524),
								zte-CSPF-Calc-Rt-Fail(103525),
								zte-FRR-SW(103526),
								zte-Hot-standby-SW(103527),
								zte-Num-MAC-inPort(103528),
								zte-Num-MAC-inVLAN(103529),
								zte-Num-MAC-inGlobal(103530),
								zte-PW-Nego-Fail(103531),
								zte-SD-Card-Drawn(103532),
								zte-STP-Root-Prt(103533),
								zte-STP-Ring-Prt(103534),
								zte-VLAN-MAC-Excrsn-Rate(103535),
								zte-VLAN-MAC-Lrn-Rate(103536),
								zte-Port-Mac-Prt(103537),
								zte-If-MAC-Excrsn-Rate(103538),
								zte-If-MAC-Lrn-Rate(103539),
								zte-Rmv-FRR-Prt(103540),
								zte-Rmv-Ht-Stndby-Prt(103541),
								zte-NB-Del(103542),
								zte-Rmt-Accss-Ctrl-Fail(103543),
								zte-Nenough-BW-4-PW(103544),
								zte-Nenough-BW-4-Tnnl(103545),
								zte-BCP-Nego-Fail(103546),
								zte-IPCP-Nego-Fail(103547),
								zte-IPV6CP-Nego-Fail(103548),
								zte-MPLSCP-Nego-Fail(103549),
								zte-extAlm5128(105128),
								zte-extAlm5129(105129),
								zte-extAlm5130(105130),
								zte-extAlm5135(105135),
								zte-extAlm5139(105139),
								zte-extAlm5142(105142),
								zte-0x3000-0x3FFF(83617),
								zte-Ev-uplF(116641),
								zte-Ev-smgrRstt(116642),
								zte-Ev-smgrLogin(116643),
								zte-Ev-outOfMgr(116644),
								zte-Ev-nAsgnPort(116645),
								zte-Ev-assoBreak(116646),
								zte-Ev-assoEstab(116647),
								zte-Ev-smgrLost(116648),
								zte-Ev-CONN-SWITCH(116897),
								zte-Ev-TREv-RESTORING(116898),
								zte-Ev-TREv-RESTORE-SUCC(116899),
								zte-Ev-TREv-RESTORE-FAIL(116900),
								zte-Ev-TREv-RETURNING(116901),
								zte-Ev-TREv-RETURN-SUCC(116902),
								zte-Ev-TREv-RETURN-FAIL(116903),
								zte-Ev-TREv-ABNORMITY(116904),
								zte-Ev-TREv-PREMPTED(116905),
								zte-Ev-TREv-PREMPTED-END(116906),
								zte-Ev-CONN-CREATE-RETRY(116907),
								zte-Ev-CONN-RESTART-RECOVER(116908),
								zte-Ev-CFG-CROSS-ERR(116911),
								zte-Ev-SIMULATE-OPEN(116912),
								zte-Ev-SIMULATE-CLOSE(116913),
								zte-Ev-BRD-INFO-ERR(116914),
								zte-Ev-TREv-OPTM-REROUTE-START(116915),
								zte-Ev-TREv-OPTM-REROUTE-FAIL(116916),
								zte-Ev-TREv-OPTM-REROUTE-SUCC(116917),
								zte-Ev-TREv-OPTM-REROUTE-STOP-RECOV(116918),
								zte-Ev-TREv-RESTART-FAIL(116919),
								zte-Ev-CONN-SW-FAIL(116920),
								zte-Ev-SW-Failed(116921),
								zte-Ev-CONN-FORCE-TO-PC(116922),
								zte-Ev-CP-DEL-REMAIN-CONN(116923),
								zte-Ev-Conn-Back(116924),
								zte-OSPF-NB-Auth-Err(116925),
								zte-RSVP-NB-Auth-Err(116926),
								zte-Svc-Prmpt(116927),
								zte-Svc-Rstr-Prmpt(116928),
								zte-Ev-dbRestart(117665),
								zte-Ev-dbFull(117666),
								zte-Ev-dbEmpy(118177),
								zte-Ev-dbVs(118178),
								zte-Ev-ncpNorm(118179),
								zte-Ev-TSdata(118180),
								zte-Ev-NTPadjust(118181),
								zte-Ev-NTPserver(118182),
								zte-Ev-dataComparing(118183),
								zte-Ev-dataQComp(118184),
								zte-Ev-TxDataFail(118185),
								zte-Ev-logInOut(118186),
								zte-Ev-rptBrdType(118187),
								zte-Ev-rptBrdOnDeck(118188),
								zte-Ev-BrdRmtUpgrade(118189),
								zte-Ev-dbFileLogic(118192),
								zte-Ev-dbFileSys(118193),
								zte-Ev-freeRamLow(118194),
								zte-Ev-ncpDBCleared(118195),
								zte-Ev-tsAlgSW(118196),
								zte-Ev-tsSaveRB(118197),
								zte-Ev-telnetRstBrd(118198),
								zte-Ev-aClsLBF(118199),
								zte-Ev-insertBrdF(118200),
								zte-Ev-aStartLaserF(118201),
								zte-Ev-initTsModFail(118202),
								zte-Ev-RstrLastTsFail(118203),
								zte-Ev-PHEQ-TmOut-Fail(118204),
								zte-Ev-TSINITFAIL(118208),
								zte-Ev-TSRESTOREFAIL(118209),
								zte-Ev-MCUReset(118210),
								zte-Ev-UserDeleted(118256),
								zte-Ev-UserPasswordChanged(118257),
								zte-Ev-UserKickedOut(118258),
								zte-Ev-UserAttrModified(118259),
								zte-Ev-svtFailONF(118433),
								zte-Ev-buffHeadEmpty(118434),
								zte-Ev-unRTErr(118435),
								zte-Ev-noSuchObj(118436),
								zte-Ev-CorbaComm(118437),
								zte-Ev-getSvcF(118438),
								zte-Ev-getRltEmpt(118439),
								zte-Ev-CmdNotSupp(118440),
								zte-Ev-errSvcTOCmd(118441),
								zte-Ev-numSadpLmt(118442),
								zte-Ev-almFF(118443),
								zte-Ev-ftpHB(118444),
								zte-AlmFreq(118445),
								zte-AlmLastLong(118446),
								zte-AlmUnAckLong(118447),
								zte-DBSpaceUsg(118448),
								zte-SvrSynchTimeFail(118449),
								zte-AlmBox2OMCSvrLnkBrd(118450),
								zte-TbCollAutoBackupFail(118451),
								zte-LicExp(118452),
								zte-LicAbExp(118453),
								zte-Lnk2DevBrk(118454),
								zte-UsrPswContFail(118455),
								zte-NMSDisconn(118456),
								zte-DBAssignSpace(118457),
								zte-mcu-VCG(118688),
								zte-MS-PSE(118944),
								zte-SNCP-PSE(118945),
								zte-EQP1RatioN-PSE(118946),
								zte-EQP1-1-PSE(118947),
								zte-CLKS-SW(118948),
								zte-RPR-PSE(118949),
								zte-ATM-PSE(118950),
								zte-LSP-PSE(118951),
								zte-ODUk-PSE(118952),
								zte-RNet-PSE(118953),
								zte-PLL-PSE(118954),
								zte-EPS-PSE(118955),
								zte-PW-PSE(118956),
								zte-Clk-Dm-PSE(118958),
								zte-Father-Clk-PSE(118959),
								zte-GrpCst-VLAN-SW(118960),
								zte-Write-DB-Fail(119457),
								zte-Rollback-Fail(119456),
								zte-Dm-Rcvr-Clk-Fail(119458),
								zte-Curr-Ver-Cmmssn(119459),
								zte-Curr-Ver-isRollBack(119460),
								zte-Set-Upg-Flag-Fail(119461),
								zte-IP-Chg-MAC(119462),
								zte-If-MAC-Cnflct(119463),
								zte-If-IP-Cnflct(119464),
								zte-DHCP-inv-Usr-refuse(119465),
								zte-SUPERVLAN-inv-IP-Filtered(119466),
								zte-SUPERVLAN-usr-sameIP-diff-MAC(119467),
								zte-BGP-status-SW(119468),
								zte-NB-HOLDTIME-Timeout(119469),
								zte-Rcv-Head-Err-Msg(119470),
								zte-Rcv-Err-Open-Msg(119471),
								zte-Rcv-Err-Update-Pkg(119472),
								zte-Rcv-Nxt-Hop-NonZero-Rt(119474),
								zte-Rcv-Err-Ntf-Msg(119475),
								zte-Rcv-LSP-Pkg-Fail-NB(119476),
								zte-Rcv-SNP-Pkg-Fail-NB(119477),
								zte-Rcv-LSP-Pkg-Unkn-NB(119478),
								zte-Rcv-SNP-Pkg-Unkn-NB(119479),
								zte-Hello-Pkg-Athu-Fail(119480),
								zte-LSP-Pkg-Athu-Fail(119481),
								zte-SNP-Pkg-Athu-Fail(119482),
								zte-ISIS-Rcv-Ill-Pkg(119483),
								zte-ISIS-NB-Status-Chg(119484),
								zte-Rcv-MAC-Withdraw(119485),
								zte-MAC-Move(119486),
								zte-L2VPN-Prtl-Unkn-TLV(119487),
								zte-GR-Abnm(119488),
								zte-Lbl-Rsrc-Not-Enough(119489),
								zte-LDP-FEC-Rsrc-Not-Enough(119490),
								zte-MAC-Mv-Bt-Ports(119491),
								zte-Port-Status-Mv(119492),
								zte-VPort-Status-Mv(119493),
								zte-NB-Status-Mv(119494),
								zte-VNB-Status-Mv(119495),
								zte-If-Auth-Fail(119496),
								zte-VIf-Auth-Fail(119497),
								zte-If-Rcv-Err-Pkg(119498),
								zte-VIf-Rcv-Err-Pkg(119499),
								zte-If-Cfg-Err(119500),
								zte-VIf-Cfg-Err(119501),
								zte-Snd-MD5-Msg-Fail(119502),
								zte-Rcv-Err-Req-Pkg(119503),
								zte-DD-Pkg-Inc-Err-No(119504),
								zte-Hello-Pkg-no-Rt-Id(119505),
								zte-Hello-Timeout(119506),
								zte-If-DR-Chg(119507),
								zte-RP-Set-Full(119508),
								zte-RPF-Chk-Fail(119509),
								zte-RIP-Ign-Rcv-Ill-Pkg(119510),
								zte-Port-Status-Hppn-Calc-Chg-Alm(119512),
								zte-VRRP-Set-Non-Learn(119513),
								zte-FLASH-Not-Work-in-Shelf-Start(119514),
								zte-BKBrd-Wrt-Nvram-Fail(119515),
								zte-Dev-Cold-Start(119516),
								zte-Tnnl-Ring-Cmd-RllBck(119517),
								zte-Crt-LSP-Success(119518),
								zte-LSP-Del(119519),
								zte-LSP-Tnnl-If-Lbl-Chg(119520),
								zte-Lcl-Tnnl-BW-Gr-Port(119521),
								zte-In-Prtcl-Status(119522),
								zte-Ms-Sych(119523),
								zte-OPT-OVER-INPUT(104097),
								zte-OPT-LESS-INPUT(104098),
								zte-OPT-NO-INPUT(104099),
								zte-VOA-OVER-INPUT(104106),
								zte-VOA-LESS-INPUT(104107),
								zte-VOA-LO-INPUT(104108),
								zte-15M-THD-CV-UP(104116),
								zte-15M-THD-ES-UP(104117),
								zte-15M-THD-SES-UP(104118),
								zte-15M-THD-UAS-UP(104119),
								zte-24H-THD-CV-UP(104120),
								zte-24H-THD-ES-UP(104121),
								zte-24H-THD-SES-UP(104128),
								zte-24H-THD-UAS-UP(104129),
								zte-15M-THD-CV-B2-UP(104130),
								zte-15M-ER-BHD-FEC(104131),
								zte-24H-THD-CV-B2-UP(104134),
								zte-FEC-LOF(104135),
								zte-15M-BIT-ERRS(104136),
								zte-24H-BIT-ERRS(104137),
								zte-24H-ER-BHD-FEC(104138),
								zte-15M-BER-AFTER-FEC-UP(104139),
								zte-24H-BER-AFTER-FEC-UP(104140),
								zte-15M-ODU-PM-BIP8-UP(104141),
								zte-15M-ODU1-PM-BIP8-UP(104142),
								zte-24H-ODU-PM-BIP8-UP(104143),
								zte-24H-ODU1-PM-BIP8-UP(104144),
								zte-LOS(104145),
								zte-OOF1(104146),
								zte-CRC-ERR-OVER(104161),
								zte-MSG-LOSS-OVER(104162),
								zte-OVER-OLB(104176),
								zte-OVER-OSNR(104177),
								zte-OTN-LOF(104178),
								zte-OTU-SM-TTI-TIM(104179),
								zte-15M-INV-PAC-UP(104182),
								zte-OTU1-TTI-MISMATCH(104185),
								zte-DLOQ(104192),
								zte-DLOA(104193),
								zte-OSC-RDI(104195),
								zte-LINK-FAIL(104197),
								zte-RX-GFP-CSF(104200),
								zte-15M-THD-DCV-UP(104208),
								zte-15M-THD-DSES-UP(104209),
								zte-15M-THD-DSSES-UP(104210),
								zte-15M-THD-DSUAS-UP(104211),
								zte-24H-THD-DCV-UP(104212),
								zte-24H-THD-DSES-UP(104213),
								zte-24H-THD-DSSES-UP(104214),
								zte-24H-THD-DSUAS-UP(104215),
								zte-LOC1(104217),
								zte-LOL1(104224),
								zte-15M-THD-OTN-UAS-UP(104227),
								zte-24H-THD-OTN-UAS-UP(104230),
								zte-OPT-INPUT-EXCEED-UP(104241),
								zte-OPT-INPUT-UNDER-LOWER(104242),
								zte-OSNR-EXCEED-UP(104243),
								zte-OSNR-UNDER-LOWER(104244),
								zte-OPT-OUTPUT-EXCEED-UP(104245),
								zte-OPT-OUTPUT-UNDER-LOWER(104246),
								zte-AWG-BIAS-TMP(104260),
								zte-OVER-BIAS(104354),
								zte-OVER-TEC(104355),
								zte-LD-OVER-OPTEMP(104356),
								zte-AWG-TMP(104358),
								zte-TMP-CTL-CURRENT(104359),
								zte-OVER-BRD-TMP(104368),
								zte-FAN-OUT-SPEED(104369),
								zte-FAN-TEMPTURE(104371),
								zte-MODULE-TEMPTURE(104372),
								zte-LOSS-CLOCK(104385),
								zte-VOA-ADJUST-FAIL(104387),
								zte-EQU-ADJUST-FAIL(104388),
								zte-PRESENCE-WARNING(104401),
								zte-CARD-NO-MATCHING(104402),
								zte-ABSENCE-DATABASE(104404),
								zte-PUMP1-OVER-OUTPUT(104407),
								zte-PUMP1-LESS-OUTPUT(104408),
								zte-PUMP1-LOO(104409),
								zte-OPT-OVER-OUTPUT(104417),
								zte-OPT-LESS-OUTPUT(104418),
								zte-OPT-LOO(104419),
								zte-PUMP2-OVER-OUTPUT(104423),
								zte-PUMP2-LESS-OUTPUT(104424),
								zte-PUMP2-LOO(104425),
								zte-VOA-OVER-OUTPUT(104426),
								zte-VOA-LESS-OUTPUT(104427),
								zte-VOA-LOO(104428),
								zte-PUMP2-LIFEEND(104432),
								zte-OVER-EDF-TMP(104433),
								zte-REFLECT-POWER-OVER(104434),
								zte-REFLECT-RATE-OVER(104435),
								zte-PUMP1-OVER-BIAS(104450),
								zte-PUMP1-OVER-TEC(104451),
								zte-PUMP1-OVER-OPTEMP(104452),
								zte-PUMP2-OVER-BIAS(104453),
								zte-PUMP2-OVER-TEC(104454),
								zte-PUMP2-OVER-OPTEMP(104455),
								zte-PUMP3-OVER-BIAS(104456),
								zte-PUMP3-OVER-TEC(104457),
								zte-PUMP3-OVER-OPTEMP(104458),
								zte-PUMP4-OVER-BIAS(104459),
								zte-PUMP4-OVER-TEC(104460),
								zte-PUMP4-OVER-OPTEMP(104461),
								zte-HPUMP-OVER-BIAS(104462),
								zte-HPUMP-OVER-TEC(104463),
								zte-CLOCK-LOS(104480),
								zte-DCLASER-OVER-BIAS(104481),
								zte-MZ-MOD-OVER-BIAS-V(104482),
								zte-DB-OVERFLOW(104866),
								zte-OVER-ENV-TMP(105136),
								zte-FAN-EOF(106421),
								zte-OTU-SM-BDI(106443),
								zte-OTU1-SM-BDI(106444),
								zte-OTU-SM-BEI(106445),
								zte-OTU1-SM-BEI(106446),
								zte-OTU-SM-BIAE(106447),
								zte-OTU1-SM-BIAE(106448),
								zte-OTU-SM-IAE(106449),
								zte-OTU1-SM-IAE(106450),
								zte-ODU-PM-TTI-TIM(106451),
								zte-OTU1-PM-TTI-MISMATCH(106452),
								zte-ODU-PM-BDI(106453),
								zte-ODU1-PM-BDI(106454),
								zte-ODU-PM-BEI(106455),
								zte-ODU1-PM-BEI(106456),
								zte-ODU-LCK(106461),
								zte-ODU1-LCK(106462),
								zte-ODU-OCI(106463),
								zte-ODU1-OCI(106464),
								zte-OPU-PT-MIS(106465),
								zte-OPU1-PT-MIS(106466),
								zte-24H-INV-PAC-UP(106467),
								zte-15M-LOS-PAC-UP(106468),
								zte-24H-LOS-PAC-UP(106469),
								zte-WB-FAIL(106470),
								zte-WSS-FAIL(106471),
								zte-DSP-FAIL(106473),
								zte-PLUGGABLE-TRANSCEIVER-DISMOUNT(106478),
								zte-NET-LINK-STATUS-ALM(106499),
								zte-EM-GCC-LINK-ALM(106500),
								zte-CP-GCC-LINK-ALM(106501),
								zte-DATA-SYNC-PORT-COM-FAIL(106503),
								zte-THIS-BORAD-ABNORMAL(106504),
								zte-PARITY-BORAD-ABNORMAL(106505),
								zte-TCM1-TTI-TIM(106506),
								zte-TCM1-BDI(106507),
								zte-TCM1-BIAE(106508),
								zte-TCM1-IAE(106509),
								zte-TCM1-LCK(106511),
								zte-TCM1-OCI(106512),
								zte-TCM1-LTC(106513),
								zte-TCM2-TTI-TIM(106514),
								zte-TCM2-BDI(106515),
								zte-TCM2-BIAE(106516),
								zte-TCM2-IAE(106517),
								zte-TCM2-LCK(106519),
								zte-TCM2-OCI(106520),
								zte-TCM2-LTC(106521),
								zte-TCM3-TTI-TIM(106522),
								zte-TCM3-BDI(106523),
								zte-TCM3-BIAE(106524),
								zte-TCM3-IAE(106525),
								zte-TCM3-LCK(106527),
								zte-TCM3-OCI(106528),
								zte-TCM3-LTC(106529),
								zte-TCM4-TTI-TIM(106530),
								zte-TCM4-BDI(106531),
								zte-TCM4-BIAE(106532),
								zte-TCM4-IAE(106533),
								zte-TCM4-LCK(106535),
								zte-TCM4-OCI(106536),
								zte-TCM4-LTC(106537),
								zte-TCM5-TTI-TIM(106538),
								zte-TCM5-BDI(106539),
								zte-TCM5-BIAE(106540),
								zte-TCM5-IAE(106541),
								zte-TCM5-LCK(106543),
								zte-TCM5-OCI(106544),
								zte-TCM5-LTC(106545),
								zte-TCM6-TTI-TIM(106546),
								zte-TCM6-BDI(106547),
								zte-TCM6-BIAE(106548),
								zte-TCM6-IAE(106549),
								zte-TCM6-LCK(106551),
								zte-TCM6-OCI(106552),
								zte-TCM6-LTC(106553),
								zte-15M-TCM1-BIP8-UP(106554),
								zte-24H-TCM1-BIP8-UP(106555),
								zte-15M-TCM2-BIP8-UP(106556),
								zte-24H-TCM2-BIP8-UP(106557),
								zte-15M-TCM3-BIP8-UP(106558),
								zte-24H-TCM3-BIP8-UP(106559),
								zte-15M-TCM4-BIP8-UP(106560),
								zte-24H-TCM4-BIP8-UP(106561),
								zte-15M-TCM5-BIP8-UP(106562),
								zte-24H-TCM5-BIP8-UP(106563),
								zte-15M-TCM6-BIP8-UP(106564),
								zte-24H-TCM6-BIP8-UP(106565),
								zte-SM-DEG(104609),
								zte-PM-DEG(104610),
								zte-TCM1-DEG(104611),
								zte-TCM2-DEG(104612),
								zte-TCM3-DEG(104613),
								zte-TCM4-DEG(104614),
								zte-TCM5-DEG(104615),
								zte-TCM6-DEG(104616),
								zte-RS-DEG(104617),
								zte-OPT-OFFSET-UP(104109),
								zte-OPT-POSITIVE-OFFSET-OVER(104247),
								zte-OPT-NEGATIVE-OFFSET-OVER(104248),
								zte-ODU-LOFLOM(106566),
								zte-OPU-MSI-MIS(106567),
								zte-OW-SELF-CHECK-FAIL(105393),
								zte-OSC-OVER-INPUT(105409),
								zte-OSC-OUT-TMP(105411),
								zte-OTU-SIGLOSS-CH1(105424),
								zte-OW-COMFAIL(105425),
								zte-OA-BACKFACE-POW1(104464),
								zte-OA-BACKFACE-POW2(104465),
								zte-MODULE-PRESENCE-WARNING(104249),
								zte-S-PORT-FAILURE(104250),
								zte-GFP-UPI-MIS(106568),
								zte-TDC-DS-UNLOCK(106474),
								zte-LESS-BIAS(104496),
								zte-BACKPLANE-LOA(106572),
								zte-BACKPLANE-BDI(106573),
								zte-SOME-RDI-CCM(104624),
								zte-SOME-RMEP-CCM(104625),
								zte-ERR-CCM(104626),
								zte-XCON-CCM(104627),
								zte-UNKNOWN-CARD(106431),
								zte-SHELF-ABSENCE(106432),
								zte-SHELF-NO-MATCHING(106433),
								zte-SHELF-PRESENCE(106434),
								zte-SHELF-CABLE-FAIL(106435),
								zte-APS-FOP-PM(106574),
								zte-APS-FOP-NR(106575),
								zte-ODU-CSF(106576),
								zte-OTL-LOL(106577),
								zte-TS-INSUFFICIENT(106578),
								zte-TS-ALLOC-MISMATCH(106579),
								zte-LINK-LF(106582),
								zte-LINK-RF(106583),
								zte-PTP-NODE-FAIL(104497),
								zte-PTP-PORT-FAIL(104498),
								zte-1PPS-TOD-LOSS(104499),
								zte-SATELLITE-SIG-LOSS(104500),
								zte-GPS-MODULE-MISSING(104501),
								zte-PRBS-LSS(106584),
								zte-VER-NO-MATCHING(104405),
								zte-AIS-CCM(104628),
								zte-LCK-CCM(104629),
								zte-EDFA-OPT-ANOMALY(104466),
								zte-IdleInvalidCellDiscards-TCA(101487),
								zte-neIdConflict(100847),
								zte-TE-Lnk-Res-Pre(102036),
								zte-RxAnnounceDiscards-TCA(101486),
								zte-TxAnnounceDiscards-TCA(101484),
								zte-RxPdelay-Resp-Follow-UpDiscards-TCA(101482),
								zte-TxPdelay-Resp-Follow-UpDiscards-TCA(101480),
								zte-RxPdelay-RespDiscards-TCA(101478),
								zte-TxPdelay-RespDiscards-TCA(101476),
								zte-RxPdelay-ReqDiscards-TCA(101474),
								zte-TxPdelay-ReqDiscards-TCA(101472),
								zte-RxDelay-ReqDiscards-TCA(101470),
								zte-TxDelay-ReqDiscards-TCA(101468),
								zte-RxFollow-UpDiscards-TCA(101466),
								zte-TxFollow-UpDiscards-TCA(101464),
								zte-RxSyncDiscards-TCA(101462),
								zte-TxSyncDiscards-TCA(101460),
								zte-LOTS(100690),
								zte-TxOversizeFrames-TCA(101499),
								zte-rmtLnkFailure(100856),
								zte-LnkFailure(100853),
								zte-LD-CHG(119200),
								zte-pSD-TCA(100021),
								zte-pSC-TCA(100020),
								zte-Ev-DB-FAIL(116909),
								zte-Ev-MEM-NOT-ENOUGH(116910),
								zte-Temp-License(102040),
								zte-CP-not-run(102039),
								zte-OSPF-NB-Lost(102031),
								zte-OSPF-CtrlLnk-Brk(102032),
								zte-Call-NOOP(102033),
								zte-TE-Lnk-Fail(102034),
								zte-TE-Lnk-Deg(102035),
								zte-ROUTE-OVERLAP-FOR-RELATE-TRA(102037),
								zte-PRECFG-ROUTE-FAILED(102038),
								zte-trns-port-id-cnflct(102042),
								zte-UR-CPU-TCA(101631),
								zte-UR-RAM-TCA(101632),
								zte-recv-BW-usg-TCA(101633),
								zte-snd-BW-usg-TCA(101634),
								zte-Pwr-In-TCA(100873),
								zte-PPPLnkSndDrpPkg-TCA(101630),
								zte-Rcv-Inv-Rt-1(119473),
								zte-Session-Down(103396),
								zte-RIP-NB-Fail-1(119511),
								zte-OSINLCP-Nego-Fail(103550),
								zte-DCN-Lnk-Fail(103551),
								zte-Clk-Init-Fail(119524),
								zte-LSP-SW-Fail(119525),
								zte-LPR(103552),
								zte-Grp-LnLnk-Dn(103553),
								zte-IP-Pkg-Len-Long(103554),
								zte-Pkg-OvrLps(103555),
								zte-SNTP-Time-Sync(103556),
								zte-CPU-Overload(103557),
								zte-IF-Unlock(103558),
								zte-Baseband-Alm(103559),
								zte-RF-ODU-Fault(103560),
								zte-Trffc-U-Invld(103561),
								zte-IDU-Overheat(103562),
								zte-ODU-Lnk-Brk(103563),
								zte-Single-Sound(103564),
								zte-Air-Lnk-Brk(103565),
								zte-Prt-Fail(103567),
								zte-RMU-SW(118961),
								zte-ODU-FW-upgrad(119526),
								zte-LP-IF-Modem(119527),
								zte-ACM-Chg(119528),
								zte-Tnnl-Share-BW-nprpr(103568),
								zte-CBIT-Diff(103569),
								zte-ODU-Mode-Invld(103566),
								zte-Ev-LCT-Logout(118260),
								zte-IP-Route-Cnt-VRF-TCA(101655),
								zte-MCAPS-Cfg-Diff(103570),
								zte-PW-Rmt-Port-Para(103571),
								zte-Diff-FrmType-Struct(103572),
								zte-15M-SM-BBE-UP(104272),
								zte-15M-SM-FEBBE-UP(104273),
								zte-15M-PM-BBE-UP(104274),
								zte-15M-PM-FEBBE-UP(104275),
								zte-15M-TCM1-BBE-UP(104276),
								zte-15M-TCM2-BBE-UP(104277),
								zte-15M-TCM3-BBE-UP(104278),
								zte-15M-TCM4-BBE-UP(104279),
								zte-15M-TCM5-BBE-UP(104280),
								zte-15M-TCM6-BBE-UP(104281),
								zte-15M-TCM1-FEBBE-UP(104282),
								zte-15M-TCM2-FEBBE-UP(104283),
								zte-15M-TCM3-FEBBE-UP(104284),
								zte-15M-TCM4-FEBBE-UP(104285),
								zte-15M-TCM5-FEBBE-UP(104286),
								zte-15M-TCM6-FEBBE-UP(104287),
								zte-24H-SM-BBE-UP(104288),
								zte-24H-SM-FEBBE-UP(104289),
								zte-24H-PM-BBE-UP(104290),
								zte-24H-PM-FEBBE-UP(104291),
								zte-24H-TCM1-BBE-UP(104292),
								zte-24H-TCM2-BBE-UP(104293),
								zte-24H-TCM3-BBE-UP(104294),
								zte-24H-TCM4-BBE-UP(104295),
								zte-24H-TCM5-BBE-UP(104296),
								zte-24H-TCM6-BBE-UP(104297),
								zte-24H-TCM1-FEBBE-UP(104298),
								zte-24H-TCM2-FEBBE-UP(104299),
								zte-24H-TCM3-FEBBE-UP(104300),
								zte-24H-TCM4-FEBBE-UP(104301),
								zte-24H-TCM5-FEBBE-UP(104302),
								zte-24H-TCM6-FEBBE-UP(104303),
								zte-MS-RDI(104150),
								zte-15M-RS-BBE-UP(104304),
								zte-15M-RS-FEBBE-UP(104305),
								zte-24H-RS-BBE-UP(104306),
								zte-24H-RS-FEBBE-UP(104307),
								zte-G-AIS(106569),
								zte-FREQ-OUT-OF-RANGE(106570),
								zte-MOD-TX-ERR(106424),
								zte-MOD-POWER-FAIL(106425),
								zte-PW-UP-CTRL-OVERVOLTAGE(106427),
								zte-CFG-INCOMPLETE(106428),
								zte-HW-CFG-ERROR(106429),
								zte-HW-NO-MATCHING(106430),
								zte-PW-INPUT-FAIL(106436),
								zte-PW-OUTPUT-FAIL(106437),
								zte-M-S-SHELF-ADD-INCONSISTENT(106438),
								zte-M-S-NE-IP-INCONSISTENT(106439),
								zte-WL-CFG-ERROR(106440),
								zte-RX-GFP-CSF-RDI(106580),
								zte-RX-GFP-CSF-FDI(106581),
								zte-PW-UP-CTRL(106496),
								zte-SHELF-ID-CONFLICT(104502),
								zte-unknown(101001),
								zte-unknown-1(101002),
								zte-unknown-2(101003),
								zte-unknown-3(101004),
								zte-unknown-4(101006),
								zte-unknown-5(101008),
								zte-unknown-6(101009),
								zte-ContinuousWrongPSW(101000),
								zte-unknown-7(101010),
								zte-unknown-8(101011),
								zte-unknown-9(101012),
								zte-unknown-10(101013),
								zte-unknown-11(101014),
								zte-unknown-12(101015),
								zte-unknown-13(101016),
								zte-unknown-14(101017),
								zte-unknown-15(101018),
								zte-unknown-16(101019),
								zte-unknown-17(101021),
								zte-unknown-18(101022),
								zte-ethlock(100022),
								zte-ethlb(100023),
								zte-rmfai(100024),
								zte-crcCross(100025),
								zte-SSF-1(100001),
								zte-unknown-19(101024),
                zte-PTP-SLAVE-PORT-SWITCH(109008),
                zte-CLK-CARD-SWITCH(108996),
                zte-SSM-CHANGE(108997),
                zte-CLK-AUTO-SWITCH(108993),
                zte-CLK-MANUAL-SWITCH(108994),
                zte-CLK-FORCE-SWITCH(108995),
                zte-ACCESS-IN11(108977),
                zte-ACCESS-IN10(108976),
                zte-ACCESS-IN02(108962),
                zte-ACCESS-IN03(108963),
                zte-ACCESS-IN01(108961),
                zte-ACCESS-IN06(108966),
                zte-ACCESS-IN07(108967),
                zte-ACCESS-IN04(108964),
                zte-ACCESS-IN05(108965),
                zte-NE-CONNECTED(120483),
                zte-ACCESS-IN0A(108970),
                zte-GNE-DISCONNECTED(120482),
                zte-ACCESS-IN0B(108971),
                zte-GNE-CONNECTED(120481),
                zte-ACCESS-IN08(108968),
                zte-ACCESS-IN09(108969),
                zte-ACCESS-IN0E(108974),
                zte-ACCESS-IN0F(108975),
                zte-ACCESS-IN0C(108972),
                zte-NE-DISCONNECTED(120484),
                zte-ACCESS-IN0D(108973),
                zte-DSP-DOWNLOAD-ERR(110753),
                zte-DSP-RESET(110752),
                zte-SERVICE-SWITCH-B-TO-A(110755),
                zte-SERVICE-SWITCH-A-TO-B(110754),
                zte-MODULE-CONFIG-CHANGE(110757),
                zte-CENTRAL-WAVELENGTH-SET-FAIL(110756),
                zte-EDFA-GAIN-LACK-ERR(110759),
                zte-OUTPUT-POWER-ADJ-FAIL(110758),
                zte-MAC-OVERFLOW(106590),
                zte-MAC-DRIFTING(106591),
                zte-CPRI-SDI(106588),
                zte-SDI-TRS-LOA(106589),
                zte-CPRI-LOF(106586),
                zte-CPRI-RAI(106587),
                zte-MOD-RX-ERR(106585),
                zte-SSF-2(106571),
                zte-ETH-DEG(106601),
                zte-8031-COMFAIL(105377),
                zte-ETH-LCK(106600),
                zte-ETH-LAG-PLL(106603),
                zte-ETH-LAG-TLL(106602),
                zte-ETH-UNPr(106597),
                zte-unknown-20(101020),
                zte-ETH-UNL(106596),
                zte-unknown-21(101023),
                zte-ETH-AIS(106599),
                zte-ETH-RDI(106598),
                zte-ETH-MMG(106593),
                zte-ETH-LOC(106592),
                zte-ETH-UNP(106595),
                zte-ETH-UNM(106594),
                zte-TCM3-AIS(106526),
                zte-BSES-TCA(101095),
                zte-TCM2-AIS(106518),
                zte-TCM1-AIS(106510),
                zte-PW-SHELL-NO-OUTPUT(106498),
                zte-PW-SHELL-NO-INPUT(106497),
                zte-COM-FAIL(106502),
                zte-LONG-MSG-OVER(108705),
                zte-SHORT-MSG-OVER(108706),
                zte-TCM6-AIS(106550),
                zte-TCM5-AIS(106542),
                zte-TCM4-AIS(106534),
                zte-TC-TIM(100924),
                zte-TS-ALLOCATED(108547),
                zte-SERVICE-RECOGNIZED(108546),
                zte-NOOS-DISAPPEAR(108545),
                zte-NOOS-APPEAR(108544),
                zte-LCT-Logout(108549),
                zte-LCT-Login-1(108548),
                zte-FLOW-MIRR-EN(108560),
                zte-FLOW-MIRR-DIS(108561),
                zte-Tx-Mis-Connected(103422),
                zte-Rx-Mis-Connected(103423),
                zte-OW-HANGUP(109474),
                zte-OW-TALKP(109473),
                zte-E-Mod-notInst(100632),
                zte-SFP-Type-Mis(100639),
                zte-POWER-OFF(104507),
                zte-DCM-INSERTION-LOSS(104506),
                zte-CTI-PORT-FAILURE(104505),
                zte-M-S-DATA-MSIMATCH(104504),
                zte-PCBVerionMissmatch(100616),
                zte-optModuleRateMismatch(100621),
                zte-fanMiss(100609),
                zte-M-S-VER-MISMATCH(104503),
                zte-HWVerionMissmatch(100615),
                zte-SWVerionMissmatch(100614),
                zte-BackboardBusError(100612),
                zte-Fmerge-fail(118264),
                zte-Ev-Agt-M-S-Data(118261),
                zte-Fmerge-success(118263),
                zte-Ev-Agt-S-Data-Sycn-fail(118262),
                zte-powerQxiLow(100702),
                zte-powerQxiHigh(100703),
                zte-powerQxiNoInput(100701),
                zte-powerBAccessFailure(100708),
                zte-powerSciLow(100705),
                zte-powerSciNoInput(100704),
                zte-powerAAccessFailure(100707),
                zte-powerSciHigh(100706),
                zte-TRAIL-FAIL(104880),
                zte-SOFT-DEFECT(104865),
                zte-DISCOVERY-UNDONE(109220),
                zte-LOOPBACK-HAS-OFF(109221),
                zte-RESET-L-UNSATISFIED(109222),
                zte-RESET-R-UNSATISFIED(109223),
                zte-R-LINK-FAULT(109216),
                zte-R-DYING-GASP(109217),
                zte-R-CRITCAL(109218),
                zte-IN-PASSIVE-MODE(109219),
                zte-R-FAILURE-INDICATION(109224),
                zte-R-DISCOVERY-FAILED(109225),
                zte-R-DISCOVERY-SUCCESSFUL(109226),
                zte-REMOTE-LOOPBACK(109227),
                zte-thresholdCrossed(100220),
                zte-outOfMemoryX(100163),
                zte-versionMismatch(100167),
                zte-rfi(100169),
                zte-powerBox2Port1NoInput(100133),
                zte-powerBox1NoOutput(100132),
                zte-powerBox2NoOutput(100135),
                zte-powerBox2Port2NoInput(100134),
                zte-powerBox1Port2NoInput(100131),
                zte-powerBox1Port1NoInput(100130),
                zte-laserModelNotInstall(100137),
                zte-laserModelFailure(100138),
                zte-storageCapacityProblem(100151),
                zte-sfwrDownloadFailure(100156),
                zte-reinitialized(100158),
                zte-memoryMismatch(100152),
                zte-corruptData(100153),
                zte-outOfCPUCycles(100154),
                zte-sfwrEnvironmentProblem(100155),
                zte-eqPSMissing(100100),
                zte-transmitDegrade(100099),
                zte-exec(100098),
                zte-lossOfTimingOutput(100097),
                zte-lossOfTimingInputs(100096),
                zte-coolingFanFailure(100107),
                zte-enclosureDoorOpen(100118),
                zte-enclosureDoorOpen0x77(100119),
                zte-LSP-Tnnl-If-Chg(119532),
                zte-FRR-SW-Back(119531),
                zte-highHumidity(100122),
                zte-HotStb-Prt-Formed(119530),
                zte-highTemperature(100123),
                zte-FRR-Prt-Formed(119529),
                zte-fire(100120),
                zte-LOP(104147),
                zte-J0-MISMATCH(104148),
                zte-MS-AIS(104149),
                zte-15M-OTU1-SM-BIP8-UP(104186),
                zte-24H-OTU1-SM-BIP8-UP(104187),
                zte-OTU-LOM(104184),
                zte-RX-GFP-LFD(104190),
                zte-msBBE-TCA(100302),
                zte-DLOM(104191),
                zte-msFEBBE-TCA(100303),
                zte-OTU1-LOF(104188),
                zte-OTU1-LOM(104189),
                zte-rsBBE-TCA(100301),
                zte-OTU-LOF(104183),
                zte-15M-OTU-SM-BIP8-UP(104180),
                zte-24H-OTU-SM-BIP8-UP(104181),
                zte-bgs10Congoutcellqueue-TCA(100315),
                zte-bgs10Congincellqueue-TCA(100314),
                zte-pathFEBBE-TCA(100305),
                zte-pathBBE-TCA(100304),
                zte-RS-EXBER(104114),
                zte-RS-SD(104115),
                zte-RS-LOF(104113),
                zte-FECSES-TCA(100252),
                zte-CSES-TCA(100251),
                zte-ODU-AIS(106459),
                zte-ODU1-AIS(106460),
                zte-OTU1-AIS(106442),
                zte-OTU-AIS(106441),
                zte-SELF-CHECK-FAIL(106494),
                zte-MODULE-FAIL(106472),
                zte-LASER-FAULT(104196),
                zte-TP-RESC-MISMATCH(102048),
                zte-BACKPLANE-LOM(104222),
                zte-BACKPLANE-LOF(104221),
                zte-24H-BACKPLANE-ERR-UP(104220),
                zte-15M-BACKPLANE-ERR-UP(104219),
                zte-LSYC(104216),
                zte-24H-THD-OTN-ES-UP(104228),
                zte-24H-THD-OTN-SES-UP(104229),
                zte-15M-THD-OTN-ES-UP(104225),
                zte-PW-UP-CTRL-UNDERVOLTAGE(106426),
                zte-15M-THD-OTN-SES-UP(104226),
                zte-PW-SHELL-INTPUT-OVERVOLTAGE(106420),
                zte-PW-OUTPUT-UNDERVOLTAGE(106422),
                zte-PW-OUTPUT-OVERVOLTAGE(106423),
                zte-PW-SHELF-OUTPUT-OVERVOLTAGE(106416),
                zte-PW-SHELF-OUTOFCONTROL(106417),
                zte-PW-SHELF-POWEROFF(106418),
                zte-PW-SHELL-INPUT-UNDERVOLTAGE(106419),
                zte-PW2-SHELF-INTPUT-OVERVOLTAGE(106413),
                zte-PW2-SHELF-INPUT-POWER-FAIL(106412),
                zte-PW-SHELF-OUTPUT-POWER-FAIL(106415),
                zte-PW2-SHELF-CARD-DISMOUNT(106414),
                zte-PW1-SHELF-INPUT-POWER-FAIL(106409),
                zte-PW2-BAY-INPUT-OVERVOLTAGE(106408),
                zte-PW1-SHELF-CARD-DISMOUNT(106411),
                zte-PW1-SHELF-INTPUT-OVERVOLTAGE(106410),
                zte-PW1-BAY-INPUT-POWER-FAIL(106405),
                zte-FAN3-FAIL(106404),
                zte-PW2-BAY-INPUT-POWER-FAIL(106407),
                zte-PW1-BAY-INPUT-OVERVOLTAGE(106406),
                zte-FAN-FAIL(106401),
                zte-FAN2-FAIL(106403),
                zte-FAN1-FAIL(106402),
                zte-interfaceBoardNotInstalled(100091),
                zte-interfaceBoardMismatch(100090),
                zte-boardTypeUnknown(100095),
                zte-expectedBoardNotInstalled(100094),
                zte-boardAttributeMismatch(100093),
                zte-powerSupplyFailureB(100092),
                zte-boardSwNotRunningProperly(100080),
                zte-boardNotRunningProperly(100087),
                zte-boardHandleLoose(100086),
                zte-laserOld(100085),
                zte-boardProtectBoxLose(100084),
                zte-CONN-FAIL(102000),
                zte-lossOfTimingInputs16M(100072),
                zte-lossOfTimingInputs32M(100073),
                zte-powerSupplyFailure(100078),
                zte-signalQualityEvaluationFailure(100079),
                zte-ABSENCE-WARNING(104403),
                zte-transmitterFailure(100067),
                zte-synchronizationSourceMismatch(100064),
                zte-lossOfTimingInputs8k(100070),
                zte-lossOfTimingInputs2M(100071),
                zte-replaceableUnitProblem(100069),
                zte-powerProblem(100058),
                zte-replaceableUnitTypeMismatch(100063),
                zte-replaceableUnitMissing(100062),
                zte-PUMP1-LIFEEND(104416),
                zte-traceIdentifierMismatch(100048),
                zte-LFD-1B(100052),
                zte-outOfFrame(100041),
                zte-rDI(100043),
                zte-m4ILOFStatusInd(100033),
                zte-m4ILOPStatus(100034),
                zte-ppiLos(100035),
                zte-crcOOMF(100019),
                zte-losOfDoubleFrame(100018),
                zte-lossOfMultiFrame(100017),
                zte-losOfMultiFrame(100016),
                zte-UAS(100014),
                zte-EXC(100012),
                zte-lossOfSignal(100008),
                zte-payloadTypeMismatch(100009),
                zte-lossOfFrame(100006),
                zte-lossOfPointer(100007),
                zte-SD(100003),
                zte-LD-EOL(104357),
                zte-MASTER-SLAVE-COMM-ERR(110508),
                zte-LOOP-SET-FAIL(110506),
                zte-MASTER-SLAVE-VER-DIF(110507),
                zte-BRD-CALIBRATION-INCOMPLETE(110504),
                zte-DATA-SERVICE-CONFIG-FAIL(110505),
                zte-PORT-LINK-DOWN(110502),
                zte-PORT-COMM-ERR(110503),
                zte-DATA-SYNC-FAIL(110500),
                zte-PORT-LINK-UP(110501),
                zte-FAN-SPD-CHANGE(110498),
                zte-EEPROM-DATA-ERR(110499),
                zte-MCU-RESET(110496),
                zte-NCP-186-RESET(110497),
                zte-MSSWT-PARITY-BOARD-ABSENT(108289),
                zte-MASTER-SLAVE-SWITCH(108288),
                zte-MSSWT-PARITY-ABNORMAL(108291),
                zte-MSSWT-PARITY-HEARTBEAT-LOST(108290),
                zte-Tx-Unusable-FE(103426),
                zte-Rx-Unusable-FE(103427),
                zte-LD-APS-UP(108456),
                zte-PLUG-MOD-PULL(108457),
                zte-LD-MANUAL-UP(108454),
                zte-LD-APS-SHD(108455),
                zte-EDFA1-AUTO-UP(108452),
                zte-LD-MANUAL-SHD(108453),
                zte-LD-AUTO-UP(108450),
                zte-EDFA1-AUTO-SHD(108451),
                zte-LD-AUTO-SHD(108449),
                zte-CRC-ERR(108465),
                zte-HOT-PLUG-MOD-PLUG(108464),
                zte-FEC-DEENCODE(108520),
                zte-REPEAT-SWITCH(108521),
                zte-SWITCH-RESTORE(108514),
                zte-SD-Storage-Usage-TCA(101658),
                zte-APR-BEGIN(108515),
                zte-RSL-TCA(101659),
                zte-SWITCH-FAIL(108512),
                zte-Peer-unReach(101656),
                zte-SWITCH-CHANGE(108513),
                zte-FEC-ENCODE(108518),
                zte-FEC-DECODE(108519),
                zte-APR-END(108516),
                zte-FEC-BYPASS(108517),
                zte-WAVE-CARD-MISMATCH(108539),
                zte-Memb-Attr-Diff(103595),
                zte-WAVE-CARD-ABSENT(108538),
                zte-CHCAP-Athu-Fail(103594),
                zte-WAVE-CARD-NOT-FOUND(108537),
                zte-PAP-Athu-Fail(103593),
                zte-OFFSET-OVERRANGE(108536),
                zte-ChipErr(103592),
                zte-WAVELENGTH-MONITOR-END(108543), 
                zte-WAVELENGTH-MONITOR-START(108542),
                zte-OPT-INPUT-OVERLOAD(108541),      
                zte-OPT-INPUT-LESS(108540),   
                zte-WAVELENGTH-ADJ-FAIL(108531),
                zte-Out-ShortCircuit(103587),
                zte-WAVELENGTH-ADJ-SUCC(108530),
                zte-Conn-Mother-Line-card-abn(103586),
                zte-CIRCUIT-LOCKER-FAIL(108529),
                zte-LpBk-Timeout(103585),
                zte-VOA-FAIL(108528),
                zte-SVC-Exception(103584),
                zte-ADJ-OVER-TIME(108535),
                zte-Vlan-PTP-lost-annc(103591),
                zte-TOO-MANY-TIMES-FAIL(108534),
                zte-PTP-Offset(103590),
                zte-ADJ-FAIL(108533),
                zte-FPGA-HW(103589),
                zte-WAVELENGTH-MISMATCH(108532),
                zte-In-AC-Off(103588),
                zte-MS-MAC-Diff(103576),
                zte-FarEnd-APS-Fail(103577),
                zte-ATPC-fail(103578),
                zte-ChipTempHigh(103579),
                zte-ChipTempLow(103580),
                zte-ClkSrc-Signal-LTI(103581),
                zte-L2L3Bride-BW-Limit(103582),
                zte-SVC-Interrupt(103583),
                zte-Eth-Port-Dmpn(103573),
                zte-Save-Data-Fail(103574),
                zte-OHP-HANGUP(108497),
                zte-OHP-TALKP(108496),
                zte-OW-FAIL(108498),
                zte-UPLOAD-FILE-DEL-FAIL(110244),
                zte-ILLEGAL-ACCESS(110241),
                zte-ILLEGAL-LOGIN(110242),
                zte-ILLEGAL-SWITCH(110243),
                zte-unknown-22(101513),
                zte-CLEAR-FAIL(108212),
                zte-EXERSWT-FAIL(108209),
                zte-EXER-SWITCH(108208),
                zte-CLEAR-EXTCMD(108211),
                zte-EXERSWT-PREEMPT(108210),
                zte-PLOCK-FAIL(108200),
                zte-AUTO-PLOCK(108201),
                zte-RLOCK-FAIL(108196),
                zte-SPAN-WLOCK(108197),
                zte-SLOCK-FAIL(108198),
                zte-SYS-PLOCK(108199),
                zte-APSC-TEST(108193),
                zte-APSC-TEST-FAIL(108194),
                zte-RING-WLOCK(108195),
                zte-CLK-AUTO-SWITCH-FAIL(108275),
                zte-CLK-SRC-AUTO-SWITCH(108274),
                zte-FE-send-clt-data-frm-TCA(101388),
                zte-CHANN-SWITCH(108256),
                zte-CHASWT-FAIL(108257),
                zte-CHANN-RESTORE(108258),
                zte-CHARST-FAIL(108259),
                zte-CHANN-ADD-DROP(108260),
                zte-LSRST-FAIL(108243),
                zte-LSSWT-RESTORE(108242),
                zte-LSSWT-FAIL(108241),
                zte-LINE-SSWITCH(108240),
                zte-LRSWT-RESTORE(108226),
                zte-LRRST-FAIL(108227),
                zte-LINE-RSWITCH(108224),
                zte-LRSWT-FAIL(108225)

  -- The following UMTS specific values are defined:
	-- <UMTS specific values to be inserted here>
        }        

-- ********************************************************************
-- Table And Object  Definition
-- ********************************************************************
-- ********************************************************************
-- Alarm Definitoin 
-- ********************************************************************
zteuAlarmTable  OBJECT-TYPE
        SYNTAX          SEQUENCE OF ZTEUAlarmEntry
        MAX-ACCESS      not-accessible
        STATUS          current
        DESCRIPTION
                "Current Alarm Table"
        ::= { zteuAlmObjects 1 }

zteuAlarmEntry  OBJECT-TYPE
        SYNTAX          ZTEUAlarmEntry
        MAX-ACCESS      not-accessible
        STATUS          current
        DESCRIPTION
                "Current Alarm Entry"
        --INDEX  {alarmSource,alarmDetector,alarmProbableCause,alarmTime,alarmLayerRate,alarmIsClearable}
        INDEX {alarmID}
        ::= { zteuAlarmTable 1 }

ZTEUAlarmEntry ::=  SEQUENCE
        {   
                alarmID						AlarmID-TC,
                alarmSource                 NamingAttributes-T,
				alarmDetector               NamingAttributes-T,
                alarmLayerRate              LayerRate-TC,				
                alarmServerity              PerceivedSeverity-TC, 
                alarmProbableCause          ProbableCause-TC,
				alarmVendorProbableCause	DisplayString,
				alarmType					AlarmType-TC,
                alarmTime                   Time-TC,
				alarmIsClearable			INTEGER,
				tcaPMLocation               PMLocation-TC,
                tcaGranularity              Granularity-TC,
                tcaThresholdType            PMThresholdType-TC,
                tcaThresholdValue           PMValue-TC, 
                tcaPMValue                  PMValue-TC, 
                tcaUnit                     Unit-TC,
				pseProtectionType           INTEGER,
				pseSwitchReason             DisplayString,
				pseGroupName                NamingAttributes-T,
                pseProtectedTP              NamingAttributes-T,
                pseSwitchAwayFromTP         NamingAttributes-T,
				pseSwitchToTP               NamingAttributes-T,
				alarmCorrelated             DisplayString,
				alarmDescInfo			    DisplayString,
                alarmAdditionalInfo         ObjectNVSList-T
        }   
        
alarmID OBJECT-TYPE
     SYNTAX AlarmID-TC
     MAX-ACCESS read-only
     STATUS current
     DESCRIPTION "
     This variable presents alarm identifier,
     It is used to identify an alarm
     "
     ::= {zteuAlarmEntry 1}
	 
   
alarmSource OBJECT-TYPE
     SYNTAX NamingAttributes-T
     MAX-ACCESS read-only
     STATUS current
     DESCRIPTION "
     This variable presents alarm source     
     For details,please refer NamingAttributes-T definition
     "
     ::= {zteuAlarmEntry 2}  
     
alarmDetector OBJECT-TYPE
     SYNTAX NamingAttributes-T
     MAX-ACCESS read-only
     STATUS current
     DESCRIPTION "
     This variable presents the detector of the alarm, 
     For details,please refer NamingAttributes-T definition
	 It can be null if the alarm source and the detector is the same object.
     "
     ::= {zteuAlarmEntry 3}  

alarmLayerRate OBJECT-TYPE
     SYNTAX LayerRate-TC
     MAX-ACCESS read-only
     STATUS current
     DESCRIPTION "
     This variable presents the layer of alarm source 
     layerrate
     "
     ::= {zteuAlarmEntry 4} 
	 
alarmServerity  OBJECT-TYPE
     SYNTAX PerceivedSeverity-TC
     MAX-ACCESS read-only
     STATUS current
     DESCRIPTION "
     This variable presents alarm serverity
     "
     ::= {zteuAlarmEntry 5} 

alarmProbableCause OBJECT-TYPE
     SYNTAX ProbableCause-TC
     MAX-ACCESS read-only
     STATUS current
     DESCRIPTION "
     This variable presents alarm probable cause
     "
     ::= {zteuAlarmEntry 6}

alarmVendorProbableCause OBJECT-TYPE
     SYNTAX DisplayString
     MAX-ACCESS read-only
     STATUS current
     DESCRIPTION "
     This variable presents vendor defined alarm probable cause
     "

     ::= {zteuAlarmEntry 7}

alarmType OBJECT-TYPE
     SYNTAX AlarmType-TC
     MAX-ACCESS read-only
     STATUS current
     DESCRIPTION "
     This variable presents the type of alarm
     "
     ::= {zteuAlarmEntry 8}

alarmTime  OBJECT-TYPE
     SYNTAX Time-TC
     MAX-ACCESS read-only
     STATUS current
     DESCRIPTION "
     This variable presents raise or clear time of alarm,alarm clear identified by alarmServerity
     "
     ::= {zteuAlarmEntry 9}

alarmIsClearable  OBJECT-TYPE
         SYNTAX INTEGER 
	   {
		  ac-False(0),
		  ac-True(1)       
	   }
        MAX-ACCESS      read-only
		STATUS          current
        DESCRIPTION
        " This variable Indicates if the event is clearable (or is itself a clear),This field is used to 
		identify the clearing of an alarm"

        ::= { zteuAlarmEntry 10 } 

tcaPMLocation         OBJECT-TYPE
     SYNTAX PMLocation-TC
     MAX-ACCESS read-only
     STATUS current
     DESCRIPTION "
     This variable presents monitor location of 
     the performance value,reserved"
       ::= { zteuAlarmEntry 11 }
	   
tcaGranularity    OBJECT-TYPE
     SYNTAX Granularity-TC
     MAX-ACCESS read-only
     STATUS current
     DESCRIPTION "
     This variable presents monitor granuarity of 
     the performance value
     "
     ::= {zteuAlarmEntry 12}   
            
tcaThresholdType    OBJECT-TYPE
     SYNTAX PMThresholdType-TC
     MAX-ACCESS read-only
     STATUS current
     DESCRIPTION "
     This variable presents threshold 
     type of performance
     "
     ::= {zteuAlarmEntry 13}
               
tcaThresholdValue   OBJECT-TYPE
     SYNTAX PMValue-TC
     MAX-ACCESS read-only
     STATUS current
     DESCRIPTION "
     This variable presents threshold value
     of performance
     "
     ::= {zteuAlarmEntry 14}   
             
tcaPMValue           OBJECT-TYPE
     SYNTAX PMValue-TC
     MAX-ACCESS read-only
     STATUS current
     DESCRIPTION "
     This variable presents performance value
     "
     ::= {zteuAlarmEntry 15}  
            
tcaUnit     OBJECT-TYPE
     SYNTAX Unit-TC
     MAX-ACCESS read-only
     STATUS current
     DESCRIPTION "
     This variable presents unit of 
     performance value
     "
     ::= {zteuAlarmEntry 16}   

pseProtectionType  OBJECT-TYPE
     SYNTAX          INTEGER(0..32767)
     MAX-ACCESS      read-only
     STATUS          current
     DESCRIPTION
     "This attribute presents protection type of protection group
      "
     ::= { zteuAlarmEntry 17 } 

pseSwitchReason OBJECT-TYPE
        SYNTAX          DisplayString
        MAX-ACCESS      read-only
        STATUS          current
        DESCRIPTION
        "This attribute presents switch reason of PSE"

     ::= {  zteuAlarmEntry 18  }    


pseGroupName OBJECT-TYPE
        SYNTAX          NamingAttributes-T
        MAX-ACCESS      read-only
        STATUS          current
        DESCRIPTION
        " This attribute presents protection group name"

        ::= { zteuAlarmEntry 19  }

pseProtectedTP OBJECT-TYPE
        SYNTAX NamingAttributes-T
        MAX-ACCESS      read-only
        STATUS          current
        DESCRIPTION
        " This attribute presents protected TP of protection group,Reserved"
        ::= { zteuAlarmEntry 20  }



pseSwitchAwayFromTP OBJECT-TYPE
        SYNTAX NamingAttributes-T
        MAX-ACCESS      read-only
        STATUS          current
        DESCRIPTION
        "Identifies the TP being switched away from."
        ::= { zteuAlarmEntry 21 }  



pseSwitchToTP OBJECT-TYPE
        SYNTAX NamingAttributes-T
        MAX-ACCESS      read-only
        STATUS          current
        DESCRIPTION
        "Identifies the TP which is being switched to."
        ::= { zteuAlarmEntry 22 }  

alarmCorrelated     OBJECT-TYPE
     SYNTAX DisplayString
     MAX-ACCESS read-only
     STATUS current
     DESCRIPTION "
     This variable presents the correlated alarms identifiers of the specific alarm,the alarm should formated in a string,
	 ','is used to seperate discrete items,'-' is used to seperate continuous items.
     "
     ::= {zteuAlarmEntry 23} 

alarmDescInfo     OBJECT-TYPE
     SYNTAX DisplayString
     MAX-ACCESS read-only
     STATUS current
     DESCRIPTION "
     This variable presents description information for the alarm.
     "
     ::= {zteuAlarmEntry 24}
				  
alarmAdditionalInfo       OBJECT-TYPE
     SYNTAX ObjectNVSList-T
     MAX-ACCESS read-only
     STATUS current
     DESCRIPTION 
     "  This attribute presents additional information,,it is consist of
				a list of parameters,represented in name-value pairs format
				(see example in creationObjectInfo of zteuObjectCreationTrap):
						Name                      Value
						'ServiceAffecting'        DisplayString,the optional values are:'Impact','No Impact', 
						'VendorAlarmCode'         DisplayString,filled with the alarm code of the vendor
						'MEUserLabel'             Display alarm-related Managed Element Information
     "     
    
     ::= {zteuAlarmEntry 25}        

zteuAlarmEntryGroup OBJECT-GROUP
	OBJECTS
        {   
                alarmID,
                alarmSource,
				alarmDetector,
                alarmLayerRate,				
                alarmServerity, 
                alarmProbableCause,
				alarmVendorProbableCause,
				alarmType,
                alarmTime,
				alarmIsClearable,
				tcaPMLocation,
                tcaGranularity,
                tcaThresholdType,
                tcaThresholdValue, 
                tcaPMValue, 
                tcaUnit,
				pseProtectionType,
				pseSwitchReason,
				pseGroupName,
                pseProtectedTP,
                pseSwitchAwayFromTP,
				pseSwitchToTP,
				alarmCorrelated,
				alarmDescInfo,
                alarmAdditionalInfo
        }   
	STATUS current
	DESCRIPTION 
	"A object group of current alarm"     
	::= {zteuAlmObjects 20}	
	
	
zteuAlarmDiagnoseInfoTable  OBJECT-TYPE
        SYNTAX          SEQUENCE OF ZTEUAlarmDiagnoseInfoEntry
        MAX-ACCESS      not-accessible
        STATUS          current
        DESCRIPTION
        "Alarm diagnose Information Table"

        ::= { zteuAlmObjects 2 }



zteuAlarmDiagnoseInfoEntry  OBJECT-TYPE
        SYNTAX          ZTEUAlarmDiagnoseInfoEntry
        MAX-ACCESS      not-accessible
        STATUS          current
        DESCRIPTION
        "Alarm Diagnose Information Entry"
        INDEX {adLayerRate,adAlarmCode}
        ::= { zteuAlarmDiagnoseInfoTable 1 }

ZTEUAlarmDiagnoseInfoEntry ::=  SEQUENCE
        {   
                adLayerRate                 LayerRate-TC,
				adAlarmCode					INTEGER,
                adProbableCause             ProbableCause-TC,
				adExplanation			    DisplayString,
				adDiagnoseInfo              DisplayString				
		}   

adLayerRate OBJECT-TYPE
     SYNTAX LayerRate-TC
     MAX-ACCESS read-only
     STATUS current
     DESCRIPTION "
     This variable presents the layerrate of alarm source 
     "
     ::= {zteuAlarmDiagnoseInfoEntry 1} 
	 

adAlarmCode  OBJECT-TYPE
     SYNTAX INTEGER(1..65535)
     MAX-ACCESS read-only
     STATUS current
     DESCRIPTION "
     This variable presents vendor alarm code
	 "
     ::= {zteuAlarmDiagnoseInfoEntry 2} 

adProbableCause OBJECT-TYPE
     SYNTAX ProbableCause-TC
     MAX-ACCESS read-only
     STATUS current
     DESCRIPTION "
     This variable presents alarm probable cause
     "
     ::= {zteuAlarmDiagnoseInfoEntry 3}


adExplanation OBJECT-TYPE
     SYNTAX DisplayString
     MAX-ACCESS read-only
     STATUS current
     DESCRIPTION "
     This variable presents the description for the alarm
     "
     ::= {zteuAlarmDiagnoseInfoEntry 4}


adDiagnoseInfo  OBJECT-TYPE
     SYNTAX DisplayString
     MAX-ACCESS read-only
     STATUS current
     DESCRIPTION "
     This variable presents the detail reason and related 
	 indication to recover the fault.
     "
     ::= {zteuAlarmDiagnoseInfoEntry 5}


zteuAlarmDiagnoseInfoEntryGroup OBJECT-GROUP

	OBJECTS
        {   
                adLayerRate,
				adAlarmCode,
                adProbableCause,
				adExplanation,
				adDiagnoseInfo
        }   

	STATUS current

	DESCRIPTION 

	"A object group of current alarm"     

	::= {zteuAlmObjects 21}	
	
	
END
