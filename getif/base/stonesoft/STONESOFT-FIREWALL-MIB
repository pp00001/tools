STONESOFT-FIREWALL-MIB DEFINITIONS ::= BEGIN

      -- SUBTREE: 1.3.6.1.4.1.1369.5.2
	  -- iso.org.dod.internet.private.enterprises.stonesoft.stonesoftProducts.stonesoftFirewall

IMPORTS
    Integer32, Counter64, Unsigned32, MODULE-IDENTITY, OBJECT-TYPE, NOTIFICATION-TYPE
        FROM SNMPv2-SMI
    DisplayString, TimeStamp
        FROM SNMPv2-TC
    OBJECT-GROUP, NOTIFICATION-GROUP, MODULE-COMPLIANCE
        FROM SNMPv2-CONF
    stonesoftModules, stonesoftFirewall
        FROM STONESOFT-SMI-MIB;

stonesoftFirewallMibModule MODULE-IDENTITY
      LAST-UPDATED	"201101010000Z"
      ORGANIZATION	"Stonesoft Corp"
      CONTACT-INFO	"email: support@stonesoft.com"
      DESCRIPTION	"MIB for Stonesoft's Firewall products"
      REVISION	    "201101010000Z"
      DESCRIPTION	"Firewall related statistics objects introduced"
      REVISION	    "200406160000Z"
      DESCRIPTION	"First public revision"
      ::= { stonesoftModules 3 }


firewallObjects     OBJECT IDENTIFIER ::= { stonesoftFirewall 1 }
firewallEvents      OBJECT IDENTIFIER ::= { stonesoftFirewall 2 }
firewallEventsV2    OBJECT IDENTIFIER ::= { firewallEvents 0 }
firewallConformance OBJECT IDENTIFIER ::= { stonesoftFirewall 3 }

--
-- Firewall objects
--
fwSoftwareVersion   OBJECT-TYPE
              SYNTAX        DisplayString
              MAX-ACCESS    read-only
              STATUS        current
              DESCRIPTION
                  "Version string of the firewall software"
              ::= { firewallObjects 1 }

fwSecurityPolicy  OBJECT-TYPE
              SYNTAX        DisplayString
              MAX-ACCESS    read-only
              STATUS        current
              DESCRIPTION
                  "Name of the current security policy on the
                  firewall"
              ::= { firewallObjects 2 }

fwPolicyTime  OBJECT-TYPE
              SYNTAX        TimeStamp
              MAX-ACCESS    read-only
              STATUS        current
              DESCRIPTION
                  "The time when the security policy was
                  installed to the firewall"
              ::= { firewallObjects 3 }

-- Global firewall informations

fwConnNumber OBJECT-TYPE
              SYNTAX		Counter64
              MAX-ACCESS	read-only
              STATUS		current
              DESCRIPTION
                  "Number of current connections"
              ::= { firewallObjects 4 }

fwAccepted OBJECT-TYPE
              SYNTAX		Counter64
              MAX-ACCESS	read-only
              STATUS		current
              DESCRIPTION
                  "Number of accepted packets"
              ::= { firewallObjects 5 }

fwDropped OBJECT-TYPE
              SYNTAX		Counter64
              MAX-ACCESS	read-only
              STATUS		current
              DESCRIPTION
                  "Number of dropped packets"
              ::= { firewallObjects 6 }

fwLogged OBJECT-TYPE
              SYNTAX		Counter64
              MAX-ACCESS	read-only
              STATUS		current
              DESCRIPTION
                  "Number of logged packets"
              ::= { firewallObjects 7 }

fwAccounted OBJECT-TYPE
              SYNTAX		Counter64
              MAX-ACCESS	read-only
              STATUS		current
              DESCRIPTION
                  "Number of accounted packets"
              ::= { firewallObjects 8 }

fwRejected OBJECT-TYPE
              SYNTAX		Counter64
              MAX-ACCESS	read-only
              STATUS		current
              DESCRIPTION
                  "Number of rejected packets"
              ::= { firewallObjects 9 }


-- interface related objects

fwIfTable  OBJECT-TYPE
              SYNTAX		SEQUENCE OF FwIfStatsEntry
              MAX-ACCESS	not-accessible
              STATUS		current
              DESCRIPTION
                  "This table contains an entry for each
                   interface in system"
              ::= { firewallObjects 10 }

-- Statistics

fwIfStatsEntry OBJECT-TYPE
              SYNTAX 		FwIfStatsEntry
              MAX-ACCESS	not-accessible
              STATUS		current
              DESCRIPTION	"Row for a interface"
              INDEX         { fwIfStatsIndex }
              ::= { fwIfTable 1 }

FwIfStatsEntry ::=
    SEQUENCE {
            fwIfStatsIndex        INTEGER,
            fwIfName              DisplayString,
            fwIfAcceptedPkts      Counter64,
            fwIfDroppedPkts       Counter64,
            fwIfLoggedPkts        Counter64,
            fwIfAccountedPkts     Counter64,
            fwIfRejectedPkts      Counter64,
            fwIfAcceptedBytes     Counter64,
            fwIfDroppedBytes      Counter64,
            fwIfLoggedBytes       Counter64,
            fwIfAccountedBytes    Counter64,
            fwIfRejectedBytes     Counter64
            }

fwIfStatsIndex OBJECT-TYPE
              SYNTAX        INTEGER(1..2147483647)
              MAX-ACCESS    read-only
              STATUS        current
              DESCRIPTION   
                "A unique value, greater than zero, for each interface or
                 interface sub-layer in the managed system."
              ::= { fwIfStatsEntry 1 }

fwIfName	OBJECT-TYPE
              SYNTAX        DisplayString
              MAX-ACCESS    read-only
              STATUS        current
              DESCRIPTION
                  "Name of interface"
              ::= { fwIfStatsEntry 2 }

fwIfAcceptedPkts OBJECT-TYPE
              SYNTAX        Counter64
              MAX-ACCESS    read-only
              STATUS        current
              DESCRIPTION
                  "Number of accepted packets by firewall rules"
              ::= { fwIfStatsEntry 3 }

fwIfDroppedPkts OBJECT-TYPE
              SYNTAX        Counter64
              MAX-ACCESS    read-only
              STATUS        current
              DESCRIPTION
                  "Number of dropped packets by firewall rules"
              ::= { fwIfStatsEntry 4 }

fwIfLoggedPkts OBJECT-TYPE
              SYNTAX        Counter64
              MAX-ACCESS    read-only
              STATUS        current
              DESCRIPTION
                  "Number of logged packets by firewall rules"
              ::= { fwIfStatsEntry 5 }

fwIfRejectedPkts OBJECT-TYPE
              SYNTAX        Counter64
              MAX-ACCESS    read-only
              STATUS        current
              DESCRIPTION
                  "Number of rejected packets by firewall rules"
              ::= { fwIfStatsEntry 6 }

fwIfAccountedPkts OBJECT-TYPE
              SYNTAX        Counter64
              MAX-ACCESS    read-only
              STATUS        current
              DESCRIPTION
                  "Number of accounted packets by firewall rules"
              ::= { fwIfStatsEntry 7 }

fwIfAcceptedBytes	OBJECT-TYPE
              SYNTAX        Counter64
              MAX-ACCESS    read-only
              STATUS        current
              DESCRIPTION
                  "Number of accepted bytes by firewall rules"
              ::= { fwIfStatsEntry 8 }

fwIfDroppedBytes	OBJECT-TYPE
              SYNTAX        Counter64
              MAX-ACCESS    read-only
              STATUS        current
              DESCRIPTION
                  "Number of dropped bytes by firewall rules"
              ::= { fwIfStatsEntry 9 }

fwIfLoggedBytes	OBJECT-TYPE
              SYNTAX        Counter64
              MAX-ACCESS    read-only
              STATUS        current
              DESCRIPTION
                  "Number of logged bytes by firewall rules"
              ::= { fwIfStatsEntry 10 }

fwIfRejectedBytes	OBJECT-TYPE
              SYNTAX        Counter64
              MAX-ACCESS    read-only
              STATUS        current
              DESCRIPTION
                  "Number of rejected bytes by firewall rules"
              ::= { fwIfStatsEntry 11 }

fwIfAccountedBytes	OBJECT-TYPE
              SYNTAX        Counter64
              MAX-ACCESS    read-only
              STATUS        current
              DESCRIPTION
                  "Number of accounted bytes by firewall rules"
              ::= { fwIfStatsEntry 12 }


-- hardware related objects

fwHardware OBJECT IDENTIFIER ::= { firewallObjects 11 }


-- Processor

fwCpuTable  OBJECT-TYPE
              SYNTAX        SEQUENCE OF FwCpuEntry
              MAX-ACCESS    not-accessible
              STATUS        current
              DESCRIPTION   "This table contains an entry for each cpu in
                            a system."
              ::= { fwHardware 1 }

fwCpuStats OBJECT-TYPE
              SYNTAX        FwCpuEntry
              MAX-ACCESS    not-accessible
              STATUS        current
              DESCRIPTION   "Row with information about cpu usage"
              INDEX         { fwCpuStatsId }
              ::= { fwCpuTable 1 }

FwCpuEntry ::= SEQUENCE {
            fwCpuStatsId    INTEGER,
            fwCpuName       DisplayString,
            fwCpuTotal      Unsigned32,
            fwCpuUser       Unsigned32,
            fwCpuSystem     Unsigned32,
            fwCpuNice       Unsigned32,
            fwCpuIdle       Unsigned32,
            fwCpuIoWait     Unsigned32,
            fwCpuHwIrq      Unsigned32,
            fwCpuSoftIrq    Unsigned32
            }


fwCpuStatsId     OBJECT-TYPE
              SYNTAX        INTEGER(1..1024)
              MAX-ACCESS    read-only
              STATUS        current
              DESCRIPTION   "A unique value, greater than zero, for each 
                             CPU in the managed system. First element with id '0'
                             is designed for total values."
              ::= { fwCpuStats 1 }

fwCpuName   OBJECT-TYPE
              SYNTAX        DisplayString (SIZE (0..255))
              MAX-ACCESS    read-only
              STATUS        current
              DESCRIPTION   "Name of data current line concern"
              ::= { fwCpuStats 2 }

fwCpuTotal  OBJECT-TYPE
              SYNTAX        Unsigned32
              UNITS         "percent"
              MAX-ACCESS    read-only
              STATUS        current
              DESCRIPTION   "The total CPU load percentage"
              ::= { fwCpuStats 3 }

fwCpuUser   OBJECT-TYPE
              SYNTAX        Unsigned32
              UNITS         "percent"
              MAX-ACCESS    read-only
              STATUS        current
              DESCRIPTION   "The percentage of time the CPU has spent running 
                             users' processes that are not niced"
              ::= { fwCpuStats 4 }

fwCpuSystem OBJECT-TYPE
              SYNTAX        Unsigned32
              UNITS         "percent"
              MAX-ACCESS    read-only
              STATUS        current
              DESCRIPTION   "The percentage of time the CPU has spent running
                             the kernel and its processes"
              ::= { fwCpuStats 5 }

fwCpuNice   OBJECT-TYPE
              SYNTAX        Unsigned32
              UNITS         "percent"
              MAX-ACCESS    read-only
              STATUS        current
              DESCRIPTION   "The percentage of time the CPU has spent running
                             users' proccess that have been niced"
              ::= { fwCpuStats 6 }

fwCpuIdle   OBJECT-TYPE
              SYNTAX        Unsigned32
              UNITS         "percent"
              MAX-ACCESS    read-only
              STATUS        current
              DESCRIPTION   "The percentage of time the CPU was idle"
              ::= { fwCpuStats 7 }

fwCpuIoWait OBJECT-TYPE
              SYNTAX        Unsigned32
              UNITS         "percent"
              MAX-ACCESS    read-only
              STATUS        current
              DESCRIPTION   "The percentage of time the CPU has been waiting
                             for I/O to complete"
              ::= { fwCpuStats 8 }

fwCpuHwIrq  OBJECT-TYPE
              SYNTAX        Unsigned32
              UNITS         "percent"
              MAX-ACCESS    read-only
              STATUS        current
              DESCRIPTION   "The percentage of time the CPU has been servicing
                             hardware interrupts"
              ::= { fwCpuStats 9 }

fwCpuSoftIrq OBJECT-TYPE
              SYNTAX        Unsigned32
              UNITS         "percent"
              MAX-ACCESS    read-only
              STATUS        current
              DESCRIPTION   "The percentage of time the CPU has been servicing
                             software interrupts"
              ::= { fwCpuStats 10 }


-- Memory

fwMemoryInfo OBJECT IDENTIFIER ::= { fwHardware 2 }


fwSwapBytesTotal OBJECT-TYPE
              SYNTAX Counter64
              UNITS "bytes"
              MAX-ACCESS read-only
              STATUS current
              DESCRIPTION  "Total swap space"
              ::= { fwMemoryInfo 1 }

fwSwapBytesUsed OBJECT-TYPE
              SYNTAX Counter64
              UNITS "bytes"
              MAX-ACCESS read-only
              STATUS current
              DESCRIPTION  "Used swap space"
              ::= { fwMemoryInfo 2 }

fwSwapBytesUnused OBJECT-TYPE
              SYNTAX Counter64
              UNITS "bytes"
              MAX-ACCESS read-only
              STATUS current
              DESCRIPTION  "Unused swap space"
              ::= { fwMemoryInfo 3 }


fwMemBytesTotal OBJECT-TYPE
              SYNTAX Counter64
              UNITS "bytes"
              MAX-ACCESS read-only
              STATUS current
              DESCRIPTION  "Number of available bytes of physical memory"
              ::= { fwMemoryInfo 4 }

fwMemBytesUsed OBJECT-TYPE
              SYNTAX Counter64
              UNITS "bytes"
              MAX-ACCESS read-only
              STATUS current
              DESCRIPTION  "Amount of used bytes of physical memory"
              ::= { fwMemoryInfo 5 }

fwMemBytesUnused OBJECT-TYPE
              SYNTAX Counter64
              UNITS "bytes"
              MAX-ACCESS read-only
              STATUS current
              DESCRIPTION  "Amount of unused bytes of physical memory"
              ::= { fwMemoryInfo 6 }

fwMemBytesBuffers OBJECT-TYPE
              SYNTAX Counter64
              UNITS "bytes"
              MAX-ACCESS read-only
              STATUS current
              DESCRIPTION  "Amount of memory used as buffers"
              ::= { fwMemoryInfo 7 }

fwMemBytesCached OBJECT-TYPE
              SYNTAX Counter64
              UNITS "bytes"
              MAX-ACCESS read-only
              STATUS current
              DESCRIPTION  "Amount of memory used as cache"
              ::= { fwMemoryInfo 8 }



-- disk(s) statistics

fwDiskSpaceUsageTable  OBJECT-TYPE
              SYNTAX        SEQUENCE OF FwDiskStatsEntry
              MAX-ACCESS    not-accessible
              STATUS        current
              DESCRIPTION   "Table contains an entry for each partition
                             mounted in a system."
              ::= { fwHardware 3 }

fwDiskStats OBJECT-TYPE
              SYNTAX        FwDiskStatsEntry
              MAX-ACCESS    not-accessible
              STATUS        current
              DESCRIPTION   "Row of information concerning one partition"
              INDEX         { fwPartitionIndex }
              ::= { fwDiskSpaceUsageTable 1 }

FwDiskStatsEntry ::= SEQUENCE {
                fwPartitionIndex    INTEGER,
                fwPartitionDevName  DisplayString,
                fwMountPointName    DisplayString,
                fwPartitionSize     Counter64,
                fwPartitionUsed     Counter64,
                fwPartitionAvail    Counter64
            }


fwPartitionIndex  OBJECT-TYPE
              SYNTAX        INTEGER(1..1024)
              MAX-ACCESS    read-only
              STATUS        current
              DESCRIPTION   "A unique value, greater than zero, for each partition"
              ::= { fwDiskStats 1 }

fwPartitionDevName  OBJECT-TYPE
              SYNTAX        DisplayString (SIZE (0..255))
              MAX-ACCESS    read-only
              STATUS        current
              DESCRIPTION   "A unique name of a device"
              ::= { fwDiskStats 2 }

fwMountPointName    OBJECT-TYPE
              SYNTAX        DisplayString (SIZE (0..255))
              MAX-ACCESS    read-only
              STATUS        current
              DESCRIPTION   "Name of a mount point"
              ::= { fwDiskStats 3 }

fwPartitionSize OBJECT-TYPE
              SYNTAX        Counter64
              UNITS         "kbytes"
              MAX-ACCESS    read-only
              STATUS        current
              DESCRIPTION   "Total size of the partition"
              ::= { fwDiskStats 4 }

fwPartitionUsed OBJECT-TYPE
              SYNTAX        Counter64
              UNITS         "kbytes"
              MAX-ACCESS    read-only
              STATUS        current
              DESCRIPTION   "Amount of used space of the partition
                             (in kilobytes)"
              ::= { fwDiskStats 5 }

fwPartitionAvail    OBJECT-TYPE
              SYNTAX        Counter64
              UNITS         "kbytes"
              MAX-ACCESS    read-only
              STATUS        current
              DESCRIPTION   "Information about amount of free space on 
                             partition (in kilobytes)"
              ::= { fwDiskStats 6 }

-- ADSL related objects

fwADSL        OBJECT IDENTIFIER ::= { firewallObjects 12 }

adslModulation OBJECT-TYPE
              SYNTAX		DisplayString
              MAX-ACCESS	read-only
              STATUS		current
              DESCRIPTION
                  "Modulation protocol"
              ::= { fwADSL 1 }

adslChannel OBJECT-TYPE
              SYNTAX		DisplayString
              MAX-ACCESS	read-only
              STATUS		current
              DESCRIPTION
                  "Channel type"
              ::= { fwADSL 2 }

adslConnStatus OBJECT-TYPE
              SYNTAX		DisplayString
              MAX-ACCESS	read-only
              STATUS		current
              DESCRIPTION
                  "The status of the DSL link or communication status
                   with DSL modem in case of communication error."
              ::= { fwADSL 3 }

adslConnUptime OBJECT-TYPE
              SYNTAX		TimeStamp
              MAX-ACCESS	read-only
              STATUS		current
              DESCRIPTION
                  "Uptime of current ADSL connection."
              ::= { fwADSL 4 }

adslLineStatus OBJECT-TYPE
              SYNTAX		DisplayString
              MAX-ACCESS	read-only
              STATUS		current
              DESCRIPTION
                  "Current status of DSL line."
              ::= { fwADSL 5 }

adslInOctets OBJECT-TYPE
              SYNTAX		INTEGER
              MAX-ACCESS	read-only
              STATUS		current
              DESCRIPTION
                  "Number of bytes received by ADSL interface"
              ::= { fwADSL 6 }

adslOutOctets OBJECT-TYPE
              SYNTAX		INTEGER
              MAX-ACCESS	read-only
              STATUS		current
              DESCRIPTION
                  "Number of bytes transmitted by ADSL interface"
              ::= { fwADSL 7 }

adslSynchroSpeedUp OBJECT-TYPE
              SYNTAX		INTEGER
              MAX-ACCESS	read-only
              STATUS		current
              DESCRIPTION
                  "The actual rate at which data is flowing upstream."
              ::= { fwADSL 8 }

adslSynchroSpeedDown OBJECT-TYPE
              SYNTAX		INTEGER
              MAX-ACCESS	read-only
              STATUS		current
              DESCRIPTION
                  "The actual rate at which data is flowing downstream."
              ::= { fwADSL 9 }

adslAttenuationUp OBJECT-TYPE
              SYNTAX		INTEGER
              MAX-ACCESS	read-only
              STATUS		current
              DESCRIPTION
                  "An estimate of the average loop attenuation upstream."
              ::= { fwADSL 10 }

adslAttenuationDown OBJECT-TYPE
              SYNTAX		INTEGER
              MAX-ACCESS	read-only
              STATUS		current
              DESCRIPTION
                  "An estimate of the average loop attenuation downstream."
              ::= { fwADSL 11 }

adslNoiseMarginUp OBJECT-TYPE
              SYNTAX		INTEGER
              MAX-ACCESS	read-only
              STATUS		current
              DESCRIPTION
                  "This is a signal-to-noise ratio (SNR) margin for
                   traffic going upstream"
              ::= { fwADSL 12 }

adslNoiseMarginDown OBJECT-TYPE
              SYNTAX		INTEGER
              MAX-ACCESS	read-only
              STATUS		current
              DESCRIPTION
                  "This is a signal-to-noise ratio (SNR) margin for
                   traffic going downstream"
              ::= { fwADSL 13 }

adslHecErrorsUp OBJECT-TYPE
              SYNTAX		INTEGER
              MAX-ACCESS	read-only
              STATUS		current
              DESCRIPTION
                  "The total number of header error checksum errors upstream."
              ::= { fwADSL 14 }

adslHecErrorsDown OBJECT-TYPE
              SYNTAX		INTEGER
              MAX-ACCESS	read-only
              STATUS		current
              DESCRIPTION
                  "The total number of header error checksum errors downstream."
              ::= { fwADSL 15 }

adslOcdErrorsUp OBJECT-TYPE
              SYNTAX		INTEGER
              MAX-ACCESS	read-only
              STATUS		current
              DESCRIPTION
                  "The number of out-of-cell delineation errors upstream."
              ::= { fwADSL 16 }

adslOcdErrorsDown OBJECT-TYPE
              SYNTAX		INTEGER
              MAX-ACCESS	read-only
              STATUS		current
              DESCRIPTION
                  "The number of out-of-cell delineation errors downstream."
              ::= { fwADSL 17 }

adslLcdErrorsUp OBJECT-TYPE
              SYNTAX		INTEGER
              MAX-ACCESS	read-only
              STATUS		current
              DESCRIPTION
                  "The total of lost-cell-delineation errors upstream."
              ::= { fwADSL 18 }

adslLcdErrorsDown OBJECT-TYPE
              SYNTAX		INTEGER
              MAX-ACCESS	read-only
              STATUS		current
              DESCRIPTION
                  "The total of lost-cell-delineation errors downstream."
              ::= { fwADSL 19 }

adslBitErrorsUp OBJECT-TYPE
              SYNTAX		INTEGER
              MAX-ACCESS	read-only
              STATUS		current
              DESCRIPTION
                  "The number of bit errors upstream."
              ::= { fwADSL 20 }

adslBitErrorsDown OBJECT-TYPE
              SYNTAX		INTEGER
              MAX-ACCESS	read-only
              STATUS		current
              DESCRIPTION
                  "The number of bit errors downstream."
              ::= { fwADSL 21 }

--
-- Firewall events
-- 

fwPolicyInstall     NOTIFICATION-TYPE
              OBJECTS       { fwSecurityPolicy }
              STATUS        current
              DESCRIPTION   "A firewall policy was (re)installed"
              ::= {firewallEventsV2 1 }

-- Conformance information

firewallGroups        OBJECT IDENTIFIER ::= { firewallConformance 1 }
firewallCompliances   OBJECT IDENTIFIER ::= { firewallConformance 2 }

firewallCompliance1 MODULE-COMPLIANCE
      STATUS current
      DESCRIPTION
          "The compliance statement for firewalls"
      MODULE  -- this module --
          MANDATORY-GROUPS { firewallGeneralInformationGroup,
                             firewallGeneralNotificationsGroup,
                             firewallGeneralStatsGroup,
                             firewallIfaceStatsGroup,
                             firewallHardwareGroup,
                             firewallAdslGroup }
      ::= { firewallCompliances 1 }


firewallGeneralInformationGroup   OBJECT-GROUP
      OBJECTS	{ fwSoftwareVersion, fwSecurityPolicy, fwPolicyTime }
      STATUS	current
      DESCRIPTION
          "A collection of objects giving general information about the
           firewall"
      ::= { firewallGroups 1 }

firewallGeneralNotificationsGroup NOTIFICATION-GROUP
      NOTIFICATIONS	{ fwPolicyInstall }
      STATUS	current
      DESCRIPTION
          "A collection of notification giving information about
           general events in the firewall"
      ::= { firewallGroups 2 }

firewallIfaceStatsGroup  OBJECT-GROUP
      OBJECTS { fwIfStatsIndex, fwIfName, fwIfAcceptedPkts, fwIfDroppedPkts,
                fwIfLoggedPkts, fwIfAccountedPkts, fwIfRejectedPkts, fwIfAcceptedBytes,
                fwIfDroppedBytes, fwIfLoggedBytes, fwIfRejectedBytes,
                fwIfAccountedBytes }
      STATUS current
      DESCRIPTION
          "A collection of objects giving information about the
           current firewall interface related traffic statistics"
      ::= { firewallGroups 3 }

firewallGeneralStatsGroup   OBJECT-GROUP
      OBJECTS	{ fwConnNumber, fwAccepted, fwDropped,
                  fwLogged, fwAccounted, fwRejected }
      STATUS	current
      DESCRIPTION
          "A collection of objects giving general information about the
           firewall traffic statistics"
      ::= { firewallGroups 4 }

firewallHardwareGroup   OBJECT-GROUP
      OBJECTS   { fwCpuStatsId, fwCpuName, fwCpuTotal, fwCpuUser, fwCpuSystem,
                  fwCpuNice, fwCpuIdle, fwCpuIoWait, fwCpuHwIrq, fwCpuSoftIrq,
                  fwSwapBytesTotal, fwSwapBytesUsed, fwSwapBytesUnused,
                  fwMemBytesTotal, fwMemBytesUsed, fwMemBytesUnused, 
                  fwMemBytesBuffers, fwMemBytesCached, 
                  fwPartitionIndex, fwPartitionDevName, fwMountPointName, 
                  fwPartitionSize, fwPartitionUsed, fwPartitionAvail }
      STATUS    current
      DESCRIPTION
          "A collection of objects giving information about the
           hardware parameters"
      ::= { firewallGroups 5 }

firewallAdslGroup   OBJECT-GROUP
      OBJECTS	{ adslModulation, adslChannel, adslConnStatus, adslConnUptime,
                  adslLineStatus, adslInOctets, adslOutOctets,
                  adslSynchroSpeedUp, adslSynchroSpeedDown,
                  adslAttenuationUp, adslAttenuationDown, adslNoiseMarginUp,
                  adslNoiseMarginDown, adslHecErrorsUp, adslHecErrorsDown,
                  adslOcdErrorsUp, adslOcdErrorsDown, adslLcdErrorsUp,
                  adslLcdErrorsDown, adslBitErrorsUp, adslBitErrorsDown  }
      STATUS	current
      DESCRIPTION
          "A collection of objects giving information about the
           ADSL modem parameters"
      ::= { firewallGroups 6 }


END
