---------------------------------------------------------------
--
--              SM - PDH - Network Element
--
--                        MIB
--
--              Management Information Base
--
---------------------------------------------------------------
-- CHANGE HISTORY
---------------------------------------------------------------
-- Revision: 1.0.0   22/09/98
---------------------------------------------------------------
-- Revision: 1.0.1   10/05/99
---------------------------------------------------------------
-- Revision: 1.0.2   22/01/99
---------------------------------------------------------------
-- Revision: 1.0.3   10/05/99
---------------------------------------------------------------
-- Revision: 1.0.4   24/06/99
--   modified: DisplayString size of:
--             unitLabel
--             unitHwEdition
--             unitParentPartNumber
--             unitParentSerialNumber
--             unitPartNumber
--             radioEquipmentRtCodeLabel
--   modified: enumeration in equipmentType
--   added:    equipRemoteElementType in  Equipment group remote NE table
--   deleted   equipPartNumber
--             equipSerialNumber
--   modified: equipIpAddress become equipIpEthOsiAddress
--   added:    equipIpEthOsiNetMask 
--   added:    equipIpEthAddress
--   added:    equipIpEthNetMask 
--   added:    equipIpPPPAddress
--   added:    equipIpPPPNetMask 
--   added:    equipPPPMode
--   added:    equipPPPBaudRate
--   added:    equipLctPPPBaudRate
--   added:    equipL1L2IsIsRouting
--   added:    equipAlarmAlign
--   modified: radioBranchRxForcedSwitch, radioBranchTxForcedSwitch moved to radioEquipment
--             as radioEquipmentRxForcedSwitch, radioEquipmentTxManualSwitch; changed 
--             enumeration
--   modified: unitExpectedType as read-only
--   modified: unitExpectedType, unitActualType enumeration
---------------------------------------------------------------
-- Revision: 1.0.5 
--   added:    Two varbind to all trap belonging to radioEquipment group
--   modified: radioBranchRxActiveStatusSeverityCode, radioBranchTxActiveStatusSeverityCode 
--             enumeration
--   modified: equipRestartRequest in equipRequest and modified emunumeration
--   added:    equipment objects for PPPradio
---------------------------------------------------------------
-- Revision: 1.0.6 del 10/12/99 
--   added:    equipIpLctPPPAddress
--   added:    equipIpLctPPPNetMask
--   modified: equipConfigChangeSeverityCode in equipConfigChangeTrapEnable and modified emunumeration
--   added:    alarmLogFTPStatus, alarmLogFTPStatusTrapNotification, alarmLogFTPStatusTrap
--   modified: equipLOMConnected emunumeration constant value. 
--             Now equipLOMConnected is a status and no more an Alarm
--             modified: equipLOMConnectedSeverityCode in equipLOMConnectedTrapEnable
--             modified: equipLOMConnectedTrapEnable enumeration constant value
--   add:      pmG826CounterTimeStamp
--   add:      pmRxPwrCounterTimeStamp
--   modified: alarmLogFTPStatus enumeration
--   modified: softwareDownloadStatus enumeration
--   modified: radioBranchRxActiveStatus, radioBranchTxActiveStatus is no more an alarm but
--             a status. 
--             Modified radioBranchRxActiveStatus and radioBranchTxActiveStatus enumeration
--             value
--             Modified radioBranchRxActiveStatusSeverityCode object name in 
--             radioBranchRxActiveStatusTrapEnable
--             Modified radioBranchTxActiveStatusSeverityCode object name in 
--             radioBranchTxActiveStatusTrapEnable
--             Deleted TRAP radioBranchRxActiveStatusCleared, radioBranchRxActiveStatusSet
--             Deleted TRAP radioBranchTxActiveStatusCleared, radioBranchTxActiveStatusSet
--             Added   TRAP radioBranchRxActiveStatusChange, radioBranchRxActiveStatusChange
--   modified: pmG82615MEsThreshold, pmG82615MSesThreshold, pmG82624HEsThreshold ,
--             pmG82624HSesThreshold DEFVAL clause
--   modified: pmRxPwr24HRlts1Threshold, pmRxPwr24HRlts2Threshold, pmRxPwr24HRlts3Threshold,
--             pmRxPwr24HRlts4Threshold, pmRxPwr15MRlts1Threshold, pmRxPwr15MRlts2Threshold,
--             pmRxPwr15MRlts3Threshold, pmRxPwr15MRlts4Threshold DEFVAL clause
--   add:      radioEquipmentEarlyWarningRxSw in radioEquipment group
--
---------------------------------------------------------------
-- Revision: 01.00.07 del 16/02/2000
--   modified: softwareUnitActualRelease, softwareUnitReleaseBench1,
--             softwareUnitReleaseBench2 SIZE clause. 
--   added:    radioEquipmentRxTribFailAlarm, radioEquipmentRxTribFailAlarmSeverityCode
--             in radioEquipment group and related trap radioEquipmentRxTribFailAlarmSet,
--             radioEquipmentRxTribFailAlarmCleared
--   modified: pmRxPwrRlt1Threshold, pmRxPwrRlt2Threshold, pmRxPwrRlt3Threshold, pmRxPwrRlt4Threshold
--             DEFVAL clause
--   added:    equipIpSnmpAgentAddress
--   modified: equipRequest emunumeration
--   modified: ACCESS clause in read-write for unitParentSerialNumber
--   modified: radioEquipmentRtCode emunumeration
--
---------------------------------------------------------------
-- Revision: 01.01.00 31/03/2000
--   added:    equipManOpTable in equip group
--   added:    equipManOpTimeOut in equip group
--   added:    radioEquipmentManualSwitch in radioEquipment group
--   modified: description of radioBranchPtx
--   modified: equipSummaryManagedObjectInstance SYNTAX from INTEGER to
--             OBJECT IDENTIFIER
--   added:    equipLOMConnectedMonitor trap (trap 109) implemented but not described
--               in the MIB.
--   modified: ACCESS clause in unitParentPartNumber
--
---------------------------------------------------------------
-- Revision: 01.01.01 23/05/2000
--   modified: equipRequest emunumeration (added routeTableClear)
--   added:    equipManager1IpAddr in equip group
--   added:    equipManager2IpAddr in equip group
--   modified: radioEquipmentRtCode  was a set of values, it become an integer.
--   modified: radioEquipmentRtCode  description.
--   modified: userOutputActiveStatus and userOutputPsuFailActiveState value
--             description
--   modified: pmRxPwrCounterTimeStamp description
--   modified: pmG826CounterTimeStamp description
---------------------------------------------------------------
-- Revision: 01.02.00 5/07/2000
--   added:    radioBranchDemMantBer, radioBranchDemExpBer, radioBranchDemErr,
--             radioBranchTimeBer, radioBranchStartBer managing ERR and BER evaluation.
--   added:    radioBranchLocalChNum managing radio channel of the local terminal.
--   added:    radioEquipmentLocalLinkId managing link id of the local terminal.
--   modified: radioEquipmentConfig (become read and write object)
--   added:    Port Service Group
--   modified: unitExpectedType unitActualType (added port service unit type)
--   added:    pmG826BlockFrame1x2Mbit, pmG826BlockFrame2x2Mbit, pmG826BlockFrame4x2Mbit
--             pmG826BlockFrame8x2Mbit, pmG826BlockFrame16x2Mbit
---------------------------------------------------------------
-- Revision: 01.02.01 30/09/2000
--   added:    radioBranchOduBncAccess
--   modified: equipType emunumeration (added sdhc-1-0)
--   modified: radioEquipmentCapacity enumeration
--   modified: equipRequest enumeration (added uploadBaseBand)
---------------------------------------------------------------

               PDH-SIAE-MIB

               --FORCE-INCLUDE <envoy/h/asn1.h>
               --FORCE-INCLUDE <envoy/h/mib.h>
               --FORCE-INCLUDE <envoy/h/snmp.h>
               --FORCE-INCLUDE "../include/pdh-profile.h"
               --FORCE-INCLUDE "../include/pdh-mib.h"

               -- exclude all rfc1213 group not implemented
               --EXCLUDE at
               --EXCLUDE icmp
               --EXCLUDE egp


               DEFINITIONS ::= BEGIN

               IMPORTS
                       mgmt, private, OBJECT-TYPE, IpAddress,
                       Counter, Opaque, TimeTicks
                           FROM RFC1155-SMI

                       TRAP-TYPE
                           FROM RFC-1215
                                                     
                       DisplayString,
                       system,
                       interfaces,
                       ip,
                       udp,
                       snmp
                           FROM RFC1213-MIB;


                enterprises         OBJECT IDENTIFIER ::= { private 1 }
                siae                OBJECT IDENTIFIER ::= { enterprises 3373 }
                pdh                 OBJECT IDENTIFIER ::= { siae 1}
                equipment           OBJECT IDENTIFIER ::= { pdh 1 }
                userInput           OBJECT IDENTIFIER ::= { pdh 2 }
                userOutput     	    OBJECT IDENTIFIER ::= { pdh 3 }
                alarmLog	          OBJECT IDENTIFIER ::= { pdh 4 }
                accessControl  	    OBJECT IDENTIFIER ::= { pdh 5 }
                unit 		            OBJECT IDENTIFIER ::= { pdh 6 }
                software            OBJECT IDENTIFIER ::= { pdh 7 }
                radioEquipment	    OBJECT IDENTIFIER ::= { pdh 8 }
                ppi 		            OBJECT IDENTIFIER ::= { pdh 9 }
                radioBranch	        OBJECT IDENTIFIER ::= { pdh 10 }
                pmG826	            OBJECT IDENTIFIER ::= { pdh 11 }
                pmRxPwr             OBJECT IDENTIFIER ::= { pdh 12 }
                portService		      OBJECT IDENTIFIER ::= { pdh 16}



----------------------------------------------------------------------------------
--  4.2 THE  EQUIPMENT GROUP
----------------------------------------------------------------------------------
--  The following listed objects are general object common to all  PDH equipment .
----------------------------------------------------------------------------------

equipCurrentTime   OBJECT-TYPE
     SYNTAX      TimeTicks
     ACCESS      read-write
     STATUS      mandatory
     DESCRIPTION "
           Seconds since  01/01/1970
  "  ::=  { equipment 1 }

equipUpTime   OBJECT-TYPE                                                       
   	SYNTAX      TimeTicks                                                       
   	ACCESS      read-only                                                       
 	  STATUS      mandatory                                                       
   	DESCRIPTION                                                                 
          "The time when the system was last re-initialized (in seconds)        
           since 1/1/1970"                                                      
    ::= { equipment 2 }                                                           


equipType   OBJECT-TYPE
     SYNTAX    INTEGER  {
                             radioSDH             (1),
                             pmp                  (2),
    	                       famSDH               (3),
                             commServer           (4),
                             microMux             (5),
                             admc                 (6),
                             radioPDH-SPU5-LC     (7),
                             radioPDH-SPU5-LC-A   (8),
                             radioPDH-SPU5-LC-B   (9),
                             radioPDH-SPU5-MC     (10),
                             radioPDH-SPU5-HC     (11),
                             radioPDH-SPU4-LC     (12),
                             radioPDH-SPU4-MC     (13),
                             radioPDH-SPU4-HC     (14),
                             radioPDH-SPU6-LC     (15),
                             radioPDH-SPU6-MC     (16),
                             radioPDH-SPU6-HC     (17)
     }
     ACCESS      read-only
     STATUS      mandatory
     DESCRIPTION "
           Type of SIAE PDH Radio Equipment:
           LC Low Capacity (up to 4x2Mbit)
           MC Medium Capacity (8x2Mbit and 16x2Mbit)
           HC  High Capacity (2x8Mbit and 34Mbit)
  "  ::=  { equipment 3 }
  
    equipIpEthOsiAddress   OBJECT-TYPE
        SYNTAX      IpAddress
        ACCESS      read-write
        STATUS      mandatory
        DESCRIPTION
            "Ip address of the equipment on Ethernet-OSI interface"
        ::=  {equipment 4}

 equipGosipAddress  OBJECT-TYPE                                                 
     SYNTAX      OCTET STRING    (SIZE(0..31))                                  
     ACCESS      read-write                                                     
     STATUS      mandatory                                                      
     DESCRIPTION                                                                
         "GOSIP  address of the equipment"                                      
     ::=  { equipment 5 }                                                         
                                                                             
 equipRemoteElementTable  OBJECT-TYPE                                           
     SYNTAX SEQUENCE OF EquipRemoteElementEntry                                 
     ACCESS      not-accessible                                                 
     STATUS      mandatory                                                      
     DESCRIPTION                                                                
         "Table with ISO/OSI remote element that are reacheable from this NE"   
     ::= { equipment 6 }                                                          
                                                                             
 equipRemoteElementEntry  OBJECT-TYPE                                           
     SYNTAX    EquipRemoteElementEntry                                          
     ACCESS    not-accessible                                                   
     STATUS    mandatory                                                        
     DESCRIPTION                                                                
         "Remote element record"                                                
     INDEX     {equipRemoteElementIpAddress}                                    
     ::= { equipRemoteElementTable 1 }                                            
                                                                             
 EquipRemoteElementEntry  ::=                                                   
     SEQUENCE {                                                                 
         equipRemoteElementIpAddress                                            
             IpAddress,                                                         
         equipRemoteElementGosipAddress                                         
             OCTET STRING,                                                      
            equipRemoteElementLabel
                DisplayString,
            equipRemoteElementType
                INTEGER
     }                                                                          
                                                                             
 equipRemoteElementIpAddress  OBJECT-TYPE                                       
     SYNTAX      IpAddress                                                      
     ACCESS      read-write                                                     
     STATUS      mandatory                                                      
     DESCRIPTION                                                                
         "IP address of remote element"                                         
     ::=  {equipRemoteElementEntry 1}                                           
                                                                             
 equipRemoteElementGosipAddress  OBJECT-TYPE                                    
     SYNTAX      OCTET STRING    (SIZE(0..31))                                  
     ACCESS      read-write                                                     
     STATUS      mandatory                                                      
     DESCRIPTION                                                                
         "Gosip address of remote element"                                      
     ::=  {equipRemoteElementEntry 2}                                           
                                                                             
 equipRemoteElementLabel  OBJECT-TYPE                                           
     SYNTAX      DisplayString   (SIZE(0..31))                                  
     ACCESS      read-write                                                     
     STATUS      mandatory                                                      
     DESCRIPTION                                                                
         "ASII string used for label the remote element"                        
     ::=  {equipRemoteElementEntry 3}                                           

 equipRemoteElementType   OBJECT-TYPE
        SYNTAX      INTEGER {
                             elemManager (1),
    	                       external (2),
                             remote (3),
                             snm   (4)
                            }
        ACCESS      read-write
        STATUS      mandatory
        DESCRIPTION
            "Type of Remote Network Element:
              * Element Manager (1)
              * External: the NE is used as a gateway to connect the element
              * Remote: the equipment connected to the other end of radio link
              * SNM: equipment managed by SubNetwork Manager"
        ::= {equipRemoteElementEntry 4 }


 equipIpEthOsiNetMask   OBJECT-TYPE
        SYNTAX      IpAddress
        ACCESS      read-write
        STATUS      mandatory
        DESCRIPTION
            "The subnet Mask associated with the IP address of OSI ethernet interface.
             The value of the Mask is an IP address with all the network bits set to 1
             and all the hosts bits set to 0."
        ::=  {equipment 7}

 equipL1L2IsIsRouting   OBJECT-TYPE
        SYNTAX      INTEGER {
                             l1 (1),
    	                       l2 (2)
                            }
        ACCESS      read-write
        STATUS      mandatory
        DESCRIPTION
            "It defines the IS-IS routing type: L1 within  the same area, L2 among 
             different areas"
        DEFVAL { l1 } 
        ::= {equipment 8}

 equipStationID  OBJECT-TYPE
     SYNTAX      DisplayString   (SIZE(0..31))
     ACCESS      read-write
     STATUS      mandatory
     DESCRIPTION "
          ASCII string  assigned by the operator to identify the specific equipment
  "  ::=  { equipment 9 }

 equipPhoneNumber  OBJECT-TYPE
     SYNTAX      INTEGER
     ACCESS      read-write
     STATUS      mandatory
     DESCRIPTION "
           Phone number assigned to the equipment
  "  ::=  { equipment 10 }          
  
equipTrapAckNotificationCount  OBJECT-TYPE                                     
    SYNTAX      INTEGER   (1..5)                                               
    ACCESS      read-write                                                     
    STATUS      mandatory                                                      
    DESCRIPTION                                                                
        "Notificatin count time before a TrapWithAck not acknowledged cause    
         a forced logoff to remote user"                                       
    DEFVAL { 3 }                                                               
    ::= { equipment 11 }                                                         
                                                                           
equipTrapAckNotificationTime  OBJECT-TYPE                                      
    SYNTAX      TimeTicks   (1..60)                                            
    ACCESS      read-write                                                     
    STATUS      mandatory                                                      
    DESCRIPTION                                                                
        "Waiting time before a new notification of a TrapWithAck not           
         acknowledged"                                                         
    DEFVAL { 10 }                                                              
    ::= { equipment 12 }                                                         
                                                                           
equipTrapAcknowledge  OBJECT-TYPE                                              
    SYNTAX      INTEGER                                                        
    ACCESS      write-only                                                     
    STATUS      mandatory                                                      
    DESCRIPTION                                                                
        "Code number related to the Trap to be acknowledged"                   
    ::= { equipment 13 }                                                         

equipAlarmSyntesysCritical OBJECT-TYPE
     SYNTAX    INTEGER {
                           cleared                   (1),
                           activeReportable-Critical (6)
                       }
     ACCESS      read-only
     STATUS      mandatory
     DESCRIPTION "
           OR of all Critical Alarms
  "  ::=  { equipment 14 }

equipAlarmSyntesysCriticalSeverityCode  OBJECT-TYPE
     SYNTAX      INTEGER {
                            disable                    (1),
                            critical-trapEnable        (6),
                            critical-trapEnableWithACK (38),
                            critical-trapDisable       (22)
                         }
     ACCESS      read-write
     STATUS      mandatory
     DESCRIPTION "
     Define the severity associated to the EquipAlarmSyntesyscriticaland  enable/disable the trap generation on status change event.
     "  DEFVAL{ critical-trapEnable }
    ::=  { equipment  15 }

equipAlarmSyntesysMajor OBJECT-TYPE
     SYNTAX    INTEGER {
                           cleared                 (1),
                           activeReportable-Major  (5)
                       }
     ACCESS      read-only
     STATUS      mandatory
     DESCRIPTION "
           OR of all Major Alarms
  "  ::=  { equipment  16 }


equipAlarmSyntesysMajorSeverityCode  OBJECT-TYPE
     SYNTAX    INTEGER {
                            disable                 (1),
                            major-trapEnable        (5),
                            major-trapEnableWithACK (37),
                            major-trapDisable       (21)
                       }
     ACCESS      read-write
     STATUS      mandatory
     DESCRIPTION "
           Define the severity associated to EquipAlarmSyntesysMajor  and  enable/disable the trap generation on status change event.
     "  DEFVAL{ major-trapEnable }
    ::=  { equipment  17 }

equipAlarmSyntesysMinor  OBJECT-TYPE
     SYNTAX    INTEGER {
                           cleared                 (1),
                           activeReportable-Minor  (4)
                       }
     ACCESS      read-only
     STATUS      mandatory
     DESCRIPTION "
           OR of all Minor Alarms
  "  ::=  { equipment  18}

equipAlarmSyntesysMinorSeverityCode  OBJECT-TYPE
     SYNTAX    INTEGER {
                            disable                 (1),
                            minor-trapEnable        (4),
                            minor-trapEnableWithACK (36),
                            minor-trapDisable       (20)
                       }
     ACCESS      read-write
     STATUS      mandatory
     DESCRIPTION "
           Define the severity associated to EquipAlarmSyntesysMinor  and  enable/disable the trap generation on status change event.
     "  DEFVAL{ minor-trapEnable }
    ::=  { equipment  19 }

equipAlarmSyntesysWarning  OBJECT-TYPE
     SYNTAX    INTEGER {
                           cleared                 (1),
                           activeReportable-Warning(3)
                       }
     ACCESS      read-only
     STATUS      mandatory
     DESCRIPTION "
           OR of all warningAlarms
  "  ::=  { equipment  20 }

equipAlarmSyntesysWarningSeverityCode  OBJECT-TYPE
     SYNTAX    INTEGER {
                            disable                   (1),
                            warning-trapEnable        (3),
                            warning-trapEnableWithACK (35),
                            warning-trapDisable       (19)
                       }

     ACCESS      read-write
     STATUS      mandatory
     DESCRIPTION "
     Define the severity associated to EquipAlarmSyntesyswarningand  enable/disable the trap generation on status change event.
     "  DEFVAL{ warning-trapEnable }
    ::=  { equipment  21 }


equipLOMConfigEnable  OBJECT-TYPE
    SYNTAX      INTEGER {
                          disable (1),
                          enable  (2)
                        }
    ACCESS      read-write
    STATUS      mandatory
    DESCRIPTION
       "Enable/Disable the capabilityto connect a LOM in Configuration Mode"
     ::= { equipment 22 }

equipLOMConnected  OBJECT-TYPE
     SYNTAX    INTEGER {
                           cleared                     (1),
                           connectionAsMonitor         (2),
                           connectionAsConfig          (3)
                       }
     ACCESS      read-only
     STATUS      mandatory
     DESCRIPTION "
           Signal when the LOM is connected to the NE and if the connection is for monitor or configuration
  "  ::=  { equipment  23 }

    equipLOMConnectedTrapEnable   OBJECT-TYPE
        SYNTAX      INTEGER {
                            trapDisable        (1),
                            trapEnable         (2),
                            trapEnableWithAck  (3)
                            }
        ACCESS      read-write
        STATUS      mandatory
        DESCRIPTION
            "Enable/disable the trap generation on EquipLOMConnected status change event."
        DEFVAL      { trapEnable }
        ::= {equipment 24}


equipManualOperation  OBJECT-TYPE
     SYNTAX    INTEGER {
                           cleared (1),
                           activeReportable-Warning (2)
                       }
     ACCESS      read-only
     STATUS      mandatory
     DESCRIPTION "
           Manual Operation active on the equipment
  "  ::=  { equipment  25 }

equipManualOperationSeverityCode  OBJECT-TYPE
     SYNTAX    INTEGER {
                            disable                   (1),
                            warning-trapEnable        (3),
                            warning-trapEnableWithACK (35),
                            warning-trapDisable       (19)
                       }

     ACCESS      read-write
     STATUS      mandatory
     DESCRIPTION "
 Enable/disable the trap generation on  EquipManualOperation  status change event.
     "  DEFVAL{ warning-trapEnable }
    ::=  { equipment  26 }

    equipConfigChange  OBJECT-TYPE
        SYNTAX      OCTET STRING    (SIZE(6))
        ACCESS      read-write
        STATUS      mandatory
        DESCRIPTION
             "Set by the NE when the equipment configuration is changed by the local
              or Remote LOM. 
              The octet string is a bit stream of flags; a set bit is a change on a
              specific item. We had:
              Byte 0.7: change in configuration for equipment group
              Byte 0.6: change in configuration for userInput group
              Byte 0.5: change in configuration for userOutput group
              Byte 0.4: change in configuration for alarmLog group
              ......
              Byte 3.7: change in a severity for equipment group
              Byte 3.6: change in a severity for userInput group
              Byte 3.5: change in a severity for userOutput group
              Byte 3.4: change in a severity for alarmLog group
              CEM can reset the change condition writing one to desired bit flag
              ......
              "
        ::= {equipment 27}


equipConfigChangeTrapEnable  OBJECT-TYPE
     SYNTAX    INTEGER {
                            trapDisable        (1),
                            trapEnable         (2),
                            trapEnableWithACK  (3)
                       }
     ACCESS      read-write
     STATUS      mandatory
     DESCRIPTION "
 Enable/disable the trap generation on  EquipConfigChange  status change event.
     "  DEFVAL{ trapEnable }
    ::=  { equipment  28 }

equipRequest   OBJECT-TYPE
     SYNTAX    INTEGER {
                            restart               (1),
                            applyIfChange         (2),
                            revertIfChange        (3),
                            configClearAndRestart (4),
                            routeTableClear       (5),
                            uploadBaseBand        (6)
                       }
     ACCESS      write-only
     STATUS      mandatory
     DESCRIPTION 
         "Force Equipment Controller restart or change in interface properties"
     ::=  { equipment  29 }

equipSummaryAlarmTable  OBJECT-TYPE
     SYNTAX    SEQUENCE OF EquipSummaryAlarmEntry
     ACCESS      not-accessible
     STATUS      mandatory
     DESCRIPTION "
          Table with one record for each Alarms&Controls that is active in the NE
  "  ::=  { equipment  36 }

equipSummaryAlarmEntry  OBJECT-TYPE
     SYNTAX      EquipSummaryAlarmEntry
     ACCESS      not-accessible
     STATUS      mandatory
     DESCRIPTION "
          Alarms&Controls  records"
     INDEX { equipSummaryRecordId }
    ::=  { equipSummaryAlarmTable  1 }

EquipSummaryAlarmEntry  ::=
     SEQUENCE {
        equipSummaryRecordId
            INTEGER,
        equipSummaryManagedObject
            OBJECT IDENTIFIER,
        equipSummaryManagedObjectInstance
            OBJECT IDENTIFIER,
        equipSummaryEventDescription
            DisplayString,
        equipSummaryProbableCause
            INTEGER,
        equipSummaryAlarmStatus
            INTEGER,            
        equipSummaryEventTime
            TimeTicks 
     }

equipSummaryRecordId  OBJECT-TYPE
     SYNTAX      INTEGER
     ACCESS      read-only
     STATUS      mandatory
     DESCRIPTION "
           This object  is used as Index of equipSummaryAlarmTable.
  "  ::=  { equipSummaryAlarmEntry  1 }

equipSummaryManagedObject  OBJECT-TYPE
     SYNTAX      OBJECT IDENTIFIER
     ACCESS      read-only
     STATUS      mandatory
     DESCRIPTION "
           The Object Identifier of  the Managed Object with  Alarms or  Controls  active (not cleared Alarm Status)
  "  ::=  { equipSummaryAlarmEntry 2 }

equipSummaryManagedObjectInstance  OBJECT-TYPE
     SYNTAX      OBJECT IDENTIFIER
     ACCESS      read-only
     STATUS      mandatory
     DESCRIPTION "
           This object  is the instance of the ManagedObject.
  "  ::=  { equipSummaryAlarmEntry  3 }

equipSummaryEventDescription  OBJECT-TYPE
     SYNTAX      DisplayString   (SIZE(0..80))
     ACCESS      read-only
     STATUS      mandatory
     DESCRIPTION "
           ASCII string used to describe the event (can be an empty string).
  "  ::=  { equipSummaryAlarmEntry  4 }

equipSummaryProbableCause  OBJECT-TYPE
     SYNTAX    INTEGER
     ACCESS      read-only
     STATUS      mandatory
     DESCRIPTION "
           This object  identifies the type of alarm.
  "  ::=  { equipSummaryAlarmEntry  5 }

equipSummaryAlarmStatus OBJECT-TYPE
     SYNTAX    INTEGER {
                            activeReportable-Status   (2),
                            activeReportable-Warning  (3),
                            activeReportable-Minor    (4),
                            activeReportable-Major    (5),
                            activeReportable-Critical (6)
                       }
     ACCESS      read-only
     STATUS      mandatory
     DESCRIPTION "
           Alarm statuswith associated severity
  "  ::=  { equipSummaryAlarmEntry  6 }

    equipSummaryEventTime  OBJECT-TYPE
        SYNTAX      TimeTicks
        ACCESS      read-only
        STATUS      mandatory
        DESCRIPTION
            "The time when the Alarm became active.
             In seconds since 01/01/70"
        ::= { equipSummaryAlarmEntry 7 }

    equipIpEthAddress   OBJECT-TYPE
        SYNTAX      IpAddress
        ACCESS      read-write
        STATUS      mandatory
        DESCRIPTION
            "Ip address of the equipment on Ethernet interface"
        ::=  {equipment 38 }

    equipIpEthNetMask   OBJECT-TYPE
        SYNTAX      IpAddress
        ACCESS      read-write
        STATUS      mandatory
        DESCRIPTION
            "The subnet Mask associated with the IP address of  ethernet interface.
             The value of the Mask is an IP address with all the network bits set to 1
             and all the hosts bits set to 0."
        ::=  {equipment 39}

    equipIpPPPAddress   OBJECT-TYPE
        SYNTAX      IpAddress
        ACCESS      read-write
        STATUS      mandatory
        DESCRIPTION
            "Ip address of the equipment on PPP interface"
        ::=  {equipment 40 }

    equipIpPPPNetMask   OBJECT-TYPE
        SYNTAX      IpAddress
        ACCESS      read-write
        STATUS      mandatory
        DESCRIPTION
            "The subnet Mask associated with the IP address of  PPP interface.
             The value of the Mask is an IP address with all the network bits set to 1
             and all the hosts bits set to 0."
        ::=  {equipment 41 }
        
    equipPPPMode   OBJECT-TYPE
        SYNTAX      INTEGER {
                             client           (1),
    	                       server           (2),
    	                       auto             (3)
                            }
        ACCESS      read-write
        STATUS      mandatory
        DESCRIPTION
            "It defines  the working mode of PPP protocol"
        DEFVAL      { server }
        ::= {equipment 42}

    equipPPPBaudRate   OBJECT-TYPE
        SYNTAX      INTEGER {
                             b9600             (1),
    	                       b19200            (2),
                             b38400		         (3),
                             b57600            (4)
                            }
        ACCESS      read-write
        STATUS      mandatory
        DESCRIPTION
            "It defines the baud rate of  PPP port"
        DEFVAL      { b38400 }
        ::= {equipment 43}

    equipLctPPPBaudRate   OBJECT-TYPE
        SYNTAX      INTEGER {
                             b9600             (1),
    	                       b19200            (2),
                             b38400		         (3),
                             b57600            (4)
                            }
        ACCESS      read-write
        STATUS      mandatory
        DESCRIPTION
            "It defines the baud rate of  LCT-PPP port"
        DEFVAL      { b38400 }
        ::= {equipment 44}

    equipOsiamParameter   OBJECT-TYPE
        SYNTAX      Opaque
        ACCESS      read-write
        STATUS      mandatory
        DESCRIPTION
            "It defines the set-up  parameter for OSI stack "
        ::= {equipment 45}

    equipAlarmAlign   OBJECT-TYPE
        SYNTAX      INTEGER {
                             align           (1)
                            }
        ACCESS      write-only
        STATUS      mandatory
        DESCRIPTION
            "Force equipment to re-send all trap of active alarm"
        ::= {equipment 46}
        
    equipIpPPPradioAddress   OBJECT-TYPE
        SYNTAX      IpAddress
        ACCESS      read-write
        STATUS      mandatory
        DESCRIPTION
            "Ip address of the PPP radio interface"
        ::=  {equipment 47 }

    equipIpPPPradioNetMask   OBJECT-TYPE
        SYNTAX      IpAddress
        ACCESS      read-write
        STATUS      mandatory
        DESCRIPTION
            "The subnet Mask associated with the IP address of PPP radio interface.
             The value of the Mask is an IP address with all the network bits set to 1
             and all the hosts bits set to 0."
        ::=  {equipment 48 }
        
    equipPPPradioMode   OBJECT-TYPE
        SYNTAX      INTEGER {
                             client           (1),
    	                       server           (2)
                            }
        ACCESS      read-write
        STATUS      mandatory
        DESCRIPTION
            "It defines the working mode of PPP radio protocol"
        DEFVAL      { server }
        ::= {equipment 49}
        
    equipIpLctPPPAddress   OBJECT-TYPE
        SYNTAX      IpAddress
        ACCESS      read-write
        STATUS      mandatory
        DESCRIPTION
            "Ip address of the LCT interface"
        ::=  {equipment 50 }

    equipIpLctPPPNetMask   OBJECT-TYPE
        SYNTAX      IpAddress
        ACCESS      read-write
        STATUS      mandatory
        DESCRIPTION
            "The subnet Mask associated with the IP address of PPP Lct interface.
             The value of the Mask is an IP address with all the network bits set to 1
             and all the hosts bits set to 0."
        ::=  {equipment 51 }
        
    equipIpSnmpAgentAddress   OBJECT-TYPE
        SYNTAX      IpAddress
        ACCESS      read-write
        STATUS      mandatory
        DESCRIPTION
            "Ip address used by SNMP Agent for mark generated TRAP"
        ::=  {equipment 52 }

    equipManOpTable  OBJECT-TYPE
        SYNTAX SEQUENCE OF EquipManOpRecord
        ACCESS      not-accessible
        STATUS      mandatory
        DESCRIPTION
            "Table with manual operation record"
        ::= {equipment 53}

    equipManOpRecord  OBJECT-TYPE
        SYNTAX    EquipManOpRecord
        ACCESS    not-accessible
        STATUS    mandatory
        DESCRIPTION
            "manual operation record"
        INDEX     {equipManOpId}
        ::= {equipManOpTable 1}

    EquipManOpRecord  ::=
        SEQUENCE {
            equipManOpId
                INTEGER,
            equipManOpObjectId
                OBJECT IDENTIFIER,
            equipManOpInstanceId
                OBJECT IDENTIFIER
        }

    equipManOpId  OBJECT-TYPE
        SYNTAX      INTEGER
        ACCESS      read-only
        STATUS      mandatory
        DESCRIPTION
            "manual operation index"
        ::=  {equipManOpRecord 1}

    equipManOpObjectId  OBJECT-TYPE
        SYNTAX      OBJECT IDENTIFIER
        ACCESS      read-only
        STATUS      mandatory
        DESCRIPTION
            "object identifier of the manual operation active element"
        ::=  {equipManOpRecord 2}

    equipManOpInstanceId  OBJECT-TYPE
        SYNTAX      OBJECT IDENTIFIER
        ACCESS      read-only
        STATUS      mandatory
        DESCRIPTION
            "instance of the manual operation active element"
        ::=  {equipManOpRecord 3}

    equipManOpTimeOut  OBJECT-TYPE
        SYNTAX      INTEGER   (0..65535)
        ACCESS      read-write
        STATUS      mandatory
        DESCRIPTION
            "this object defines the time (in seconds) after wich the manual
             operations are cleared. The value range from 1 to 0FFFFh.
             A zero means no Time-out"
        DEFVAL      { 2 }
        ::=  {equipment 54}

    equipManager1IpAddr   OBJECT-TYPE
        SYNTAX      IpAddress
        ACCESS      read-write
        STATUS      mandatory
        DESCRIPTION
            "First IP address of a SNMP Manager always logged to this equipment.
             The address 0.0.0.0 mean that manager is not present"
        ::=  {equipment 55 }

    equipManager2IpAddr   OBJECT-TYPE
        SYNTAX      IpAddress
        ACCESS      read-write
        STATUS      mandatory
        DESCRIPTION
            "Second IP address of a SNMP Manager always logged to this equipment.
             The address 0.0.0.0 mean that manager is not present"
        ::=  {equipment 56 }


-----------------------------------------------------------------------------------
---  The Equipment  Group generates the following TRAPs:
-----------------------------------------------------------------------------------

    equipAlarmSyntesysCriticalSet TRAP-TYPE
        ENTERPRISE pdh
        DESCRIPTION
            "This event is generated by SDH-NE when equipAlarmSyntesysCritical is set
             The data passed with the event are:
                1) equipAlarmSyntesysCritical
                2) equipTrapAcknowledge code number"
    ::= 101

    equipAlarmSyntesysCriticalCleared TRAP-TYPE
        ENTERPRISE pdh
        DESCRIPTION
            "This event is generated by SDH-NE when equipAlarmSyntesysCritical is cleared
             The data passed with the event are:
                1) equipAlarmSyntesysCritical
                2) equipTrapAcknowledge code number"
    ::= 102

    equipAlarmSyntesysMajorSet TRAP-TYPE
        ENTERPRISE pdh
        DESCRIPTION
            "This event is generated by SDH-NE when equipAlarmSyntesysMajor is set
             The data passed with the event are:
                1) equipAlarmSyntesysMajor
                2) equipTrapAcknowledge code number"
    ::= 103

    equipAlarmSyntesysMajorCleared  TRAP-TYPE
        ENTERPRISE pdh
        DESCRIPTION
            "This event is generated by SDH-NE when EquipAlarmSyntesysMajor is cleared
             The data passed with the event are:
                1) equipAlarmSyntesysMajor
                2) equipTrapAcknowledge code number"
    ::= 104

    equipAlarmSyntesysMinorSet  TRAP-TYPE
        ENTERPRISE pdh
        DESCRIPTION
            "This event is generated by SDH-NE when EquipAlarmSyntesysMinor is set
             The data passed with the event are:
                1) EquipAlarmSyntesysMinor
                2) equipTrapAcknowledge code number"
    ::= 105

    equipAlarmSyntesysMinorCleared  TRAP-TYPE
        ENTERPRISE pdh
        DESCRIPTION
            "This event is generated by SDH-NE when EquipAlarmSyntesysMinor is cleared
             The data passed with the event are:
                1) EquipAlarmSyntesysMinor
                2) equipTrapAcknowledge code number"
    ::= 106

    equipAlarmSyntesysWarningSet  TRAP-TYPE
        ENTERPRISE pdh
        DESCRIPTION
            "This event is generated by SDH-NE when EquipAlarmSyntesysWarning is set
             The data passed with the event are:
                1) EquipAlarmSyntesysWarning
                2) equipTrapAcknowledge code number"
    ::= 107

    equipAlarmSyntesysWarningCleared  TRAP-TYPE
        ENTERPRISE pdh
        DESCRIPTION
            "This event is generated by SDH-NE when EquipAlarmSyntesysWarning is cleared
             The data passed with the event are:
                1) EquipAlarmSynthesisWarning
                2) equipTrapAcknowledge code number"
    ::= 108

    equipLOMConnectedMonitor  TRAP-TYPE
        ENTERPRISE pdh
        DESCRIPTION
            "This event is generated by SDH-NE when equipLOMConnected is set to Monitor mode
             The data passed with the event are:
                1) equipLOMConnected
                2) equipTrapAcknowledge code number"
    ::= 109

    equipLOMConnectedConfig  TRAP-TYPE
        ENTERPRISE pdh
        DESCRIPTION
            "This event is generated by SDH-NE when equipLOMConnected is set to Configuration  mode
             The data passed with the event are:
                1) equipLOMConnected
                2) equipTrapAcknowledge code number"
    ::= 110

    equipLOMDisconnected  TRAP-TYPE
        ENTERPRISE pdh
        DESCRIPTION
            "This event is generated by SDH-NE when LOMConnected is cleared
             The data passed with the event are:
                1) equipLOMConnected
                2) equipTrapAcknowledge code number"
    ::= 111

    equipManualOperationSet  TRAP-TYPE
        ENTERPRISE pdh
        DESCRIPTION
            "This event is generated by SDH-NE when equipManualOperation is set
             The data passed with the event are:
                1) equipManualOperation
                2) equipTrapAcknowledge code number"
    ::= 112

    equipManualOperationCleared  TRAP-TYPE
        ENTERPRISE pdh
        DESCRIPTION
            "This event is generated by  DH-NE when EquipManualOperation is cleared
             The data passed with the event are:
                1) equipManualOperation
                2) equipTrapAcknowledge code number"
    ::= 113

    equipConfigChangeStatus  TRAP-TYPE
        ENTERPRISE pdh
        DESCRIPTION
            "This event is generated by SDH-NE when equipConfigChange is changed
             The data passed with the event are:
                1) equipConfigChange
                2) equipTrapAcknowledge code number"
    ::= 114


----------------------------------------------------------------------------------
--  4.3 USER INPUT GROUP
--  This group is used to describe the user inputs available on the equipment.
--  It is a table  with a row for each equipped user input.
----------------------------------------------------------------------------------

userInputTable  OBJECT-TYPE
     SYNTAX      SEQUENCE OF UserInputEntry
     ACCESS      not-accessible
     STATUS      mandatory
     DESCRIPTION "
          Table with User Input records
  "  ::=  { userInput  1 }

userInputEntry  OBJECT-TYPE
     SYNTAX      UserInputEntry
     ACCESS      not-accessible
     STATUS      mandatory
     DESCRIPTION "
          User Input records"
     INDEX { userInputNumber }
    ::=  { userInputTable  1 }

UserInputEntry  ::=
     SEQUENCE {
        userInputNumber
            INTEGER,
         userInputLabel
            DisplayString,
         userInputActiveState
            INTEGER,
         userInputAlarmStatus
            INTEGER,
         userInputAlarmSeverityCode
            INTEGER
     }

userInputNumber  OBJECT-TYPE
     SYNTAX      INTEGER
     ACCESS      read-only
     STATUS      mandatory
     DESCRIPTION "
           User Input number is used as the index for the user input table
  "  ::=  { userInputEntry  1 }

userInputLabel   OBJECT-TYPE
     SYNTAX      DisplayString  (SIZE(0..20))
     ACCESS      read-write
     STATUS      mandatory
     DESCRIPTION 
         "ASCII string used by the operator to identify  the user input"
     ::=  { userInputEntry  2 }

userInputActiveState  OBJECT-TYPE
     SYNTAX    INTEGER {
                           open   (1),
                           closed (2)
                     }
     ACCESS      read-write
     STATUS      mandatory
     DESCRIPTION 
         "User Input Active State"  
     ::=  { userInputEntry  3 }

userInputAlarmStatus OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
           User Input status with associated Severity
  "  ::=  { userInputEntry  4 }

userInputAlarmSeverityCode  OBJECT-TYPE
     SYNTAX    INTEGER {
                            disable                     (1),
                            status-trapEnable           (2),
                            status-trapEnableWithACK    (34),
                            warning-trapEnable          (3),
                            warning-trapEnableWithACK   (35),
                            minor-trapEnable            (4),
                            minor-trapEnableWithACK     (36),
                            major-trapEnable            (5),
                            major-trapEnableWithACK     (37),
                            critical-trapEnable         (6),
                            critical-trapEnableWithACK  (38),
                            status-trapDisable          (18),
                            warning-trapDisable         (19),
                            minor-trapDisable           (20),
                            major-trapDisable           (21),
                            critical-trapDisable        (22)
                       }

     ACCESS      read-write
     STATUS      mandatory
     DESCRIPTION "
           Define the severity associated to the user input and
           enable/disable the trap generation on status change event.
     "  DEFVAL{ major-trapEnable }
    ::=  { userInputEntry  5 }

----------------------------------------------------------------------------------
--  The User Input Group generates the following TRAP:
----------------------------------------------------------------------------------

    userInputAlarmStatusSet  TRAP-TYPE
        ENTERPRISE pdh
        DESCRIPTION
            "This event is generated by  PDH-NE when an User Input is set
             The data passed with the event are:
                1) UserInputNumber
                2) UserInputLabel
                3) UserInputAlarmStatus
                4) equipTrapAcknowledge code number"
        ::= 201

    userInputAlarmStatusCleared TRAP-TYPE
        ENTERPRISE pdh
        DESCRIPTION
            "This event is generated by  PDH-NE when an User Input is set
             The data passed with the event are:
               1) UserInputNumber
               2) UserInputLabel
               3) UserInputAlarmStatus
               4) equipTrapAcknowledge code number"
        ::= 202



----------------------------------------------------------------------------------
--  4.4 USER OUTPUT GROUP
--  This group is used to describe the User Outputs (relay) available
--  on the equipment. It is a table  with a row for each equipped User Output.
----------------------------------------------------------------------------------

userOutputTable  OBJECT-TYPE
     SYNTAX      SEQUENCE OF UserOutputEntry
     ACCESS      not-accessible
     STATUS      mandatory
     DESCRIPTION "
          Table with User Output records
  "  ::=  { userOutput  1 }

userOutputEntry  OBJECT-TYPE
     SYNTAX      UserOutputEntry
     ACCESS      not-accessible
     STATUS      mandatory
     DESCRIPTION "
          User Output records"
     INDEX { userOutputNumber }
    ::=  { userOutputTable  1 }

UserOutputEntry  ::=
     SEQUENCE {
        userOutputNumber
            INTEGER,
        userOutputLabel
            DisplayString,
        userOutputForcedOperatorStatus
            INTEGER,
        userOutputInternalStatus
            Opaque
        }

userOutputNumber  OBJECT-TYPE
     SYNTAX      INTEGER
     ACCESS      read-only
     STATUS      mandatory
     DESCRIPTION "
           User Output number is used as the index for the User  Output table
  "  ::=  { userOutputEntry  1 }

userOutputLabel  OBJECT-TYPE
     SYNTAX      DisplayString   (SIZE(0..31))
     ACCESS      read-write
     STATUS      mandatory
     DESCRIPTION 
         "ASCII string used by the operator to identify the User Output"
     ::=  { userOutputEntry  2 }

userOutputForcedOperatorStatus OBJECT-TYPE
     SYNTAX    INTEGER {
                           notActive    (1),
                           active       (2)
                       }
     ACCESS      read-write
     STATUS      mandatory
     DESCRIPTION "
           User Output status forced by the operator.
  "  ::=  { userOutputEntry  3 }

userOutputInternalStatus OBJECT-TYPE
     SYNTAX      Opaque         --(SIZE(34))
     ACCESS      read-write
     STATUS      mandatory
     DESCRIPTION "
           User Output status connected to internal condition
  "  ::=  { userOutputEntry  4 }

userOutputActiveStatus OBJECT-TYPE
        SYNTAX    INTEGER {
                           open (1),
                           closed (2)
                          }
        ACCESS      read-write
        STATUS      mandatory
        DESCRIPTION
            "Define the Active State of User Output"
     ::=  { userOutput  2 }

userOutputPsuFailActiveState OBJECT-TYPE
        SYNTAX    INTEGER {
                           open (1),
                           closed (2)
                          }
        ACCESS      read-write
        STATUS      mandatory
        DESCRIPTION
            "Define the Active State of User Output reserved to the power supply"
     ::=  { userOutput  3 }



----------------------------------------------------------------------------------
--  4.5 ALARM LOG GROUP
--  This group is used to manage the alarm log.
----------------------------------------------------------------------------------

alarmLogTable  OBJECT-TYPE
     SYNTAX      SEQUENCE OF AlarmRecord
     ACCESS      not-accessible
     STATUS      mandatory
     DESCRIPTION "
          Table with Alarm  records
  "  ::=  { alarmLog 1 }

alarmLogRecord  OBJECT-TYPE
     SYNTAX      AlarmRecord
     ACCESS      not-accessible
     STATUS      mandatory
     DESCRIPTION "
          Alarm  records"
     INDEX { alarmLogRecordId }
    ::=  { alarmLogTable 1 }

AlarmRecord  ::=
    SEQUENCE {
        alarmLogRecordId
            INTEGER,
        alarmLogManagedObject
            OBJECT IDENTIFIER,
        alarmLogManagedObjectInstance
            OBJECT IDENTIFIER,
        alarmLogEventDescription
            DisplayString,
        alarmLogProbableCause
            INTEGER,
        alarmLogAlarmStatus
            INTEGER,
        alarmLogEventTime
            TimeTicks
     }

alarmLogRecordId  OBJECT-TYPE
     SYNTAX      INTEGER
     ACCESS      read-only
     STATUS      mandatory
     DESCRIPTION "
           This object  is used as Index of AlarmLogTable.
  "  ::=  { alarmLogRecord  1 }

alarmLogManagedObject  OBJECT-TYPE
     SYNTAX      OBJECT IDENTIFIER
     ACCESS      read-only
     STATUS      mandatory
     DESCRIPTION "
           The Object Identifier of  the Managed Object.
  "  ::=  { alarmLogRecord 2 }

alarmLogManagedObjectInstance  OBJECT-TYPE
     SYNTAX      OBJECT IDENTIFIER
     ACCESS      read-only
     STATUS      mandatory
     DESCRIPTION "
           This object  is the instance of the ManagedObject.
  "  ::=  { alarmLogRecord  3 }

alarmLogEventDescription  OBJECT-TYPE
     SYNTAX      DisplayString   (SIZE(0..80))
     ACCESS      read-only
     STATUS      mandatory
     DESCRIPTION "
           ASCII string used to describe the event (can be an empty string).
  "  ::=  { alarmLogRecord  4 }

alarmLogProbableCause  OBJECT-TYPE
     SYNTAX      INTEGER
     ACCESS      read-only
     STATUS      mandatory
     DESCRIPTION "
           This object  identifies the type of alarm.
  "  ::=  { alarmLogRecord  5 }

alarmLogAlarmStatus OBJECT-TYPE
     SYNTAX    INTEGER {
                           cleared                        (1),
                           activeReportable-Status        (2),
                           activeReportable-Warning       (3),
                           activeReportable-Minor         (4),
                           activeReportable-Major         (5),
                           activeReportable-Critical      (6)
                       }
     ACCESS      read-only
     STATUS      mandatory
     DESCRIPTION "
           Alarm statuswith associated severity
  "  ::=  { alarmLogRecord  6 }

alarmLogEventTime  OBJECT-TYPE
     SYNTAX      TimeTicks
     ACCESS      read-only
     STATUS      mandatory
     DESCRIPTION "
           The time (in secs ) when the event was registered in the Log since 1/1/1970
  "  ::=  { alarmLogRecord  7 }


----------------------------------------------------------------------------------
-- The following objects are used  to map the "action"
-- (delete record , transfer the log using NFS ...):
----------------------------------------------------------------------------------


alarmLogActionRequest  OBJECT-TYPE
     SYNTAX    INTEGER {
                           delete (1),
                           read   (2)
                       }
     ACCESS      write-only
     STATUS      mandatory
     DESCRIPTION "
           This object is used to delete or  to read the LOG  using Ftp (file transfer)
  "  ::=  { alarmLog  2 }

alarmLogFtpfile OBJECT-TYPE
     SYNTAX      DisplayString   (SIZE(0..255))
     ACCESS      read-write
     STATUS      mandatory
     DESCRIPTION "
           Path and file name used when  the log is transferred  using Ftp (action =  read)
  "  ::=  { alarmLog  3 }

----------------------------------------------------------------------------------
--  The following objects are used  to enable/disable  the event
--  record write in the Log.
----------------------------------------------------------------------------------

alarmLogAlarmSeverityEnable  OBJECT-TYPE
     SYNTAX      INTEGER
     ACCESS      read-write
     STATUS      mandatory
     DESCRIPTION "
           This object  enables the event record write in the log according to the severity:
            Bit0 = Status
            Bit1 = Warning
            Bit2 = Minor
            Bit3 = Major
            Bit4 = Critical
      "  DEFVAL{  '1f'h  }
    ::=  { alarmLog  4 }

alarmLogStartHourEnable  OBJECT-TYPE
     SYNTAX      INTEGER
     ACCESS      read-write
     STATUS      mandatory
     DESCRIPTION "
     This object  defines  whit AlarmLogEndHourEnable the period during a day when the alarm records must be written in the log.
      "  DEFVAL{  0  }
    ::=  { alarmLog  5 }

alarmLogEndHourEnable  OBJECT-TYPE
     SYNTAX      INTEGER
     ACCESS      read-write
     STATUS      mandatory
     DESCRIPTION "
     This object  defines  whit AlarmLogStartHourEnable the period during a day when the alarm records must be written in the log.
      "  DEFVAL{  23  }
    ::=  { alarmLog  6 }

----------------------------------------------------------------------------------
--  The following objects are used  as filters  when the manager reads or
--  deletes the events in the LOG.
----------------------------------------------------------------------------------

alarmLogStartTimeFilter  OBJECT-TYPE
     SYNTAX      TimeTicks
     ACCESS      read-write
     STATUS      mandatory
     DESCRIPTION "
           The events with EventTime greater than this object are read/delete  from the log. Null value means no filter
     "  DEFVAL{  0  }
    ::=  { alarmLog  7 }

alarmLogEndTimeFilter  OBJECT-TYPE
     SYNTAX      TimeTicks
     ACCESS      read-write
     STATUS      mandatory
     DESCRIPTION "
           The events with EventTime less than this object are read/delete  from the log. Null value means no filter
     "  DEFVAL{  0  }
    ::=  { alarmLog  8 }

alarmLogManagedObjectFilter OBJECT-TYPE
     SYNTAX      OBJECT IDENTIFIER
     ACCESS      read-write
     STATUS      mandatory
     DESCRIPTION "
           The Object Identifier of  the Managed Object that  has to be read/delete  from the log. Null value means no filter
     "  DEFVAL{  pdh  }
    ::=  { alarmLog  9 }

alarmLogAlarmSeverityFilter  OBJECT-TYPE
     SYNTAX    INTEGER
     ACCESS      read-write
     STATUS      mandatory
     DESCRIPTION "
           This object  defines the alarm severity of the records that must be read/delete from the log.
            Bit0 = Status
            Bit1 = Warning
            Bit2 = Minor
            Bit3 = Major
            Bit4 = Critical
      "  DEFVAL{  '1f'h  }
    ::=  { alarmLog  10 }

alarmLogProbableCauseFilter  OBJECT-TYPE
     SYNTAX    INTEGER
     ACCESS      read-write
     STATUS      mandatory
     DESCRIPTION "
           This object  defines the Probable Cause  of the records that must be read/delete from the log. Null value means no filter
     "  DEFVAL{  0  }
    ::=  { alarmLog  11 }


--
-- The following objects are used as status indicator of FTP transfer
--

    alarmLogFTPStatus OBJECT-TYPE
        SYNTAX      INTEGER{
                            transferring (1),
                            completed    (2),
                            interrupted  (3),
                            empty        (4)
                           }
        ACCESS      read-only
        STATUS      mandatory
        DESCRIPTION
            "Status of alarm logger Ftp transfer operation"
        DEFVAL      { completed }
        ::= { alarmLog 12 }

    alarmLogFTPStatusTrapNotification OBJECT-TYPE
        SYNTAX      INTEGER {
                             trapDisable (1),
                             trapEnable (2),
                             trapEnableWithACK (34)
                            }
        ACCESS      read-write
        STATUS      mandatory
        DESCRIPTION
            "Enable/disable the trap generation on FTP tranfer operation."
        DEFVAL      { trapEnable }
        ::= { alarmLog 13 }


--
-- The Alarm Log generates the following TRAP:
--

    alarmLogFTPStatusTrap  TRAP-TYPE
        ENTERPRISE pdh
        DESCRIPTION
            "This event is generated by SDH-NE when the status of FTP transfer is changed
             The data passed with the event are
             1) alarmLogFTPStatus
             2) accessControlLoginIpAddress
             3) equipTrapAcknowledge code number"
        ::= 401



----------------------------------------------------------------------------------
-- 4.6 ACCESS CONTROL GROUP
--
-- This table defines the users allowed to access the system.
-- The maximum number of user (number of records) is 13.
----------------------------------------------------------------------------------

accessControlUserTable  OBJECT-TYPE
     SYNTAX      SEQUENCE OF AccessControlUserRecord
     ACCESS      not-accessible
     STATUS      mandatory
     DESCRIPTION "
          Table with User  records
  "  ::=  { accessControl 1 }

accessControlUserRecord  OBJECT-TYPE
     SYNTAX      AccessControlUserRecord
     ACCESS      not-accessible
     STATUS      mandatory
     DESCRIPTION "
          Alarm  records"
     INDEX { accessControlUsername }
    ::=  { accessControlUserTable 1 }

AccessControlUserRecord  ::=
     SEQUENCE {
        accessControlUsername
            DisplayString,
        accessControlPassword
            DisplayString,
        accessControlUserProfile
            INTEGER,
        accessControlLoginTimeout   
            INTEGER
     }

accessControlUsername  OBJECT-TYPE
     SYNTAX      DisplayString   (SIZE(0..8))
     ACCESS      read-write
     STATUS      mandatory
     DESCRIPTION "
           ASCII string identifying the user, it is used as Index for the table.
           The write of a not existing Username  is used to create, a new user,
           the write of a Null string to a specific (UserId) record  is used to delete an user.
  "  ::=  { accessControlUserRecord  1 }

accessControlPassword  OBJECT-TYPE
     SYNTAX      DisplayString   (SIZE(0..8))
     ACCESS      write-only
     STATUS      mandatory
     DESCRIPTION "
           ASCII string used as password.
  "  ::=  { accessControlUserRecord  2 }

accessControlUserProfile OBJECT-TYPE
     SYNTAX INTEGER {
                           system                (1),
                           stationOperator       (2),
                           maintenanceOperatorA  (3),
                           maintenanceOperatorB  (4)
                    }
     ACCESS      read-write
     STATUS      mandatory
     DESCRIPTION "
           This object defines the user  access privilege. It's not possible to change
           profile into system (1).
  "  ::=  { accessControlUserRecord  3 }

accessControlLoginTimeout  OBJECT-TYPE
     SYNTAX      INTEGER
     ACCESS      read-write
     STATUS      mandatory
     DESCRIPTION "
           This object defines the  time (seconds) after wich the login session is closed
           if no messages are received from the manager.
           The value is from 1 to 0xFFFF, 0 means no time out.
   "  ::=  { accessControlUserRecord  4 }

----------------------------------------------------------------------------------
-- The following table  is used to manage the user login,
-- up to four logins are possible (1 CEM  + 3 LOM).
----------------------------------------------------------------------------------

accessControlLoginTable  OBJECT-TYPE
     SYNTAX      SEQUENCE OF AccessControlLoginRecord
     ACCESS      not-accessible
     STATUS      mandatory
     DESCRIPTION "
          Table with Login  records. Max. number of Login equal 4.
  "  ::=  {accessControl 2 }

accessControlLoginRecord  OBJECT-TYPE
     SYNTAX      AccessControlLoginRecord
     ACCESS      not-accessible
     STATUS      mandatory
     DESCRIPTION "
          Alarm  records"
     INDEX { accessControlLoginIpAddress, accessControlLoginUsername }
    ::=  {accessControlLoginTable 1 }

AccessControlLoginRecord  ::=
   SEQUENCE {
        accessControlLoginUsername
            DisplayString,
        accessControlLoginPassword
            DisplayString,
        accessControlLoginRequest
            INTEGER,
        accessControlLoginIpAddress
           IpAddress,
        accessControlTrapEnable
           INTEGER
     }

accessControlLoginUsername  OBJECT-TYPE
     SYNTAX      DisplayString   (SIZE(0..8))
     ACCESS      read-write
     STATUS      mandatory
     DESCRIPTION "
           ASCII string identifying the user.
  "  ::=  { accessControlLoginRecord  1 }

accessControlLoginPassword  OBJECT-TYPE
     SYNTAX      DisplayString   (SIZE(0..8))
     ACCESS      write-only
     STATUS      mandatory
     DESCRIPTION "
           ASCII string used to verify if the user can access the system.
  "  ::=  { accessControlLoginRecord  2 }

accessControlLoginRequest  OBJECT-TYPE
     SYNTAX  INTEGER {
                           login  (1),
                           logout (2)
                     }

     ACCESS      write-only
     STATUS      mandatory
     DESCRIPTION "
This object is used to request the login/logout of the user.
  "  ::=  { accessControlLoginRecord  3 }

accessControlLoginIpAddress  OBJECT-TYPE
     SYNTAX  IpAddress
     ACCESS      read-write
     STATUS      mandatory
     DESCRIPTION "
           It is the IP address of the logged user.
  "  ::=  { accessControlLoginRecord  4 }

accessControlTrapEnable  OBJECT-TYPE
     SYNTAX  INTEGER {
                           trapDisable          (1),
                           trapEnableWithAck    (2),
                           trapEnableWithoutAck (3)
                     }

     ACCESS      read-write
     STATUS      mandatory
     DESCRIPTION "
Enable/disable of the trap toward the element defined by the IP address. The trap can be with or without acknowledge from  the receiving entity
  "  ::=  { accessControlLoginRecord  5 }



----------------------------------------------------------------------------------
-- 4.7 UNIT  GROUP
----------------------------------------------------------------------------------
-- This group is used to manage the units  (board and in general replaceable part) present in the equipment.
----------------------------------------------------------------------------------

unitTable  OBJECT-TYPE
     SYNTAX      SEQUENCE OF UnitRecord
     ACCESS      not-accessible
     STATUS      mandatory
     DESCRIPTION "
          Table with Unit  records.
  "  ::=  { unit 1 }

unitRecord  OBJECT-TYPE
     SYNTAX      UnitRecord
     ACCESS      not-accessible
     STATUS      mandatory
     DESCRIPTION "
          Unit record"
     INDEX { unitId }
    ::=  { unitTable 1 }

UnitRecord  ::=
   SEQUENCE {
       unitId
           INTEGER,
       unitExpectedType
           INTEGER,
       unitActualType
           INTEGER,
       unitLabel
           DisplayString,
       unitFailAlarm
           INTEGER,
       unitMissingAlarm
           INTEGER,
       unitNotRespondingAlarm
           INTEGER,
       unitHwMismatchAlarm
           INTEGER,
       unitSwMismatchAlarm
           INTEGER,
       unitHwEdition
           DisplayString,
       unitPartNumber
           DisplayString,
       unitParentPartNumber
           DisplayString,
       unitParentSerialNumber
           DisplayString
     }

unitId  OBJECT-TYPE
     SYNTAX      INTEGER
     ACCESS      read-only
     STATUS      mandatory
     DESCRIPTION "
           This object  is used as Index of the Unit Table.
  "  ::=  { unitRecord 1 }

    unitExpectedType  OBJECT-TYPE
        SYNTAX      INTEGER{
                            unequipped          (1),
                            eqController        (2),
                            baseBand            (3),
                            rim                 (4),
                            radio               (5),
                            asynchDataV11-V28-1 (6),
                            asynchDataV24-2     (7),
                            eowVoiceChannel-3   (8),
                            dataChannel9600-4   (9),
                            voiceChannel-5      (10),
                            dataChannel64Kbit-6 (11),
                            dialVoiceChannel-8  (12)
                           }

        ACCESS      read-only
        STATUS      mandatory
        DESCRIPTION
            "Define the expected unit type"
        ::= { unitRecord 2 }

    unitActualType  OBJECT-TYPE
        SYNTAX      INTEGER{
                            unequipped          (1),
                            eqController        (2),
                            baseBand            (3),
                            rim                 (4),
                            radio               (5),
                            asynchDataV11-V28-1 (6),
                            asynchDataV24-2     (7),
                            eowVoiceChannel-3   (8),
                            dataChannel9600-4   (9),
                            voiceChannel-5      (10),
                            dataChannel64Kbit-6 (11),
                            dialVoiceChannel-8  (12)
                           }

        ACCESS      read-only
        STATUS      mandatory
        DESCRIPTION
            "Define the real unit type actually configurated"
        ::= { unitRecord 3 }

    unitLabel  OBJECT-TYPE
        SYNTAX      DisplayString (SIZE (0..30))
        ACCESS      read-only
        STATUS      mandatory
        DESCRIPTION
            "ASCII string used to assign a name to the unit"
        ::= { unitRecord 4 }

    unitFailAlarm  OBJECT-TYPE
        SYNTAX      INTEGER{
                            cleared (1),
                            activeReportable-Status (2),
                            activeReportable-Warning (3),
                            activeReportable-Minor (4),
                            activeReportable-Major (5),
                            activeReportable-Critical (6)
                           }

        ACCESS      read-only
        STATUS      mandatory
        DESCRIPTION
            "Unit Fail alarm status (Probable cause = ReplaceableUnitProblem)
             status with associated Severity"
        ::= { unitRecord 5 }

    unitMissingAlarm  OBJECT-TYPE
        SYNTAX      INTEGER{
                            cleared (1),
                            activeReportable-Status (2),
                            activeReportable-Warning (3),
                            activeReportable-Minor (4),
                            activeReportable-Major (5),
                            activeReportable-Critical (6)
                           }

        ACCESS      read-only
        STATUS      mandatory
        DESCRIPTION
            "Unit Missing alarm status (Probable cause = ReplaceableUnitMissing)
             status with associated Severity"
        ::= { unitRecord 6 }

    unitNotRespondingAlarm  OBJECT-TYPE
        SYNTAX      INTEGER{
                            cleared (1),
                            activeReportable-Status (2),
                            activeReportable-Warning (3),
                            activeReportable-Minor (4),
                            activeReportable-Major (5),
                            activeReportable-Critical (6)
                           }

        ACCESS      read-only
        STATUS      mandatory
        DESCRIPTION
            "Unit Not Responding alarm status (Probable cause = ReplaceableUnitMalfunction)
             status with associated Severity"
        ::= { unitRecord 7 }



    unitHwMismatchAlarm  OBJECT-TYPE
        SYNTAX      INTEGER{
                            cleared (1),
                            activeReportable-Status (2),
                            activeReportable-Warning (3),
                            activeReportable-Minor (4),
                            activeReportable-Major (5),
                            activeReportable-Critical (6)
                           }

        ACCESS      read-only
        STATUS      mandatory
        DESCRIPTION
            "Unit type Mismatch alarm status (Probable cause = ReplaceableUnitTypeMismatch)
             status with associated Severity"
        ::= { unitRecord 8 }


    unitSwMismatchAlarm  OBJECT-TYPE
        SYNTAX      INTEGER{
                            cleared (1),
                            activeReportable-Status (2),
                            activeReportable-Warning (3),
                            activeReportable-Minor (4),
                            activeReportable-Major (5),
                            activeReportable-Critical (6)
                           }

        ACCESS      read-only
        STATUS      mandatory
        DESCRIPTION
            "Unit  with Sw Release  Mismatch alarm status (Probable cause = SfwrEnviromentProbleme)
             status with associated Severity"
        ::= { unitRecord 9 }

    unitHwEdition  OBJECT-TYPE
        SYNTAX      DisplayString (SIZE (0..10))
        ACCESS      read-only
        STATUS      mandatory
        DESCRIPTION
            "ASCII string used to identify Hw edition of the unit."
        ::= { unitRecord 10 }

    unitPartNumber  OBJECT-TYPE
        SYNTAX      DisplayString (SIZE (0..30))
        ACCESS      read-only
        STATUS      mandatory
        DESCRIPTION
            "ASCII string to identify the Part Number of the unit"
        ::= { unitRecord 11 }

    unitParentPartNumber  OBJECT-TYPE
        SYNTAX      DisplayString (SIZE (0..30))
        ACCESS      read-write
        STATUS      mandatory
        DESCRIPTION
            "ASCII string to identify the parent Part Number of the unit"
        ::= { unitRecord 12 }


    unitParentSerialNumber  OBJECT-TYPE
        SYNTAX      DisplayString (SIZE (0..30))
        ACCESS      read-write
        STATUS      mandatory
        DESCRIPTION
            "ASCII string to identify parent Serial Number of the unit"
        ::= { unitRecord 13 }



----------------------------------------------------------------------------------
--  The following objects define the profile of the unit alarms:
----------------------------------------------------------------------------------

unitFailAlarmSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the Unit Fail Alarm  and  enable/disable the trap generation on status change event.
     "  DEFVAL{ major-trapEnable }
    ::=  { unit 2 }

unitMissingAlarmSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the Unit Missing Alarm  and  enable/disable the trap generation on status change event.
     "  DEFVAL{ major-trapEnable }
    ::=  { unit  3}

unitNotRespondingAlarmSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
    Define the severity associated to the Unit Not Responding  Alarm  and  enable/disable the trap generation on status change event.
     "  DEFVAL{ major-trapEnable }
    ::=  { unit  4}


unitHwMismatchAlarmSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
    Define the severity associated to the UnitHwMismatchAlarm Alarm  and  enable/disable the trap generation on status change event.
     "  DEFVAL{ major-trapEnable }
    ::=  { unit 5 }

unitSwMismatchAlarmSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
    Define the severity associated to the Sw Release  mismatch  Alarm  and  enable/disable the trap generation on status change event.
     "  DEFVAL{ major-trapEnable }
    ::=  { unit  6 }

----------------------------------------------------------------------------------
--  The Unit  Group generates the following TRAP:
----------------------------------------------------------------------------------

    unitFailAlarmSet  TRAP-TYPE
        ENTERPRISE pdh
        DESCRIPTION
            "This event is generated by PDH-NE when an Unit Fail Alarm is set
             The data passed with the event are
             1) UnitId
             2) UnitLabel
             3) UnitFailAlarm
             4) equipTrapAcknowledge code number"
        ::= 601

    unitFailAlarmCleared  TRAP-TYPE
        ENTERPRISE pdh
        DESCRIPTION
            "This event is generated by PDH-NE when an Unit Fail Alarm is cleared
             The data passed with the event are
             1) UnitId
             2) UnitLabel
             3) UnitFailAlarm
             4) equipTrapAcknowledge code number"
        ::= 602

    unitMissingAlarmSet  TRAP-TYPE
        ENTERPRISE pdh
        DESCRIPTION
            "This event is generated by PDH-NE when an Unit Missing Alarm is set
             The data passed with the event are
             1) UnitId
             2) UnitLabel
             3) UnitMissingAlarm
             4) equipTrapAcknowledge code number"
        ::= 603

    unitMissingAlarmCleared  TRAP-TYPE
        ENTERPRISE pdh
        DESCRIPTION
            "This event is generated by PDH-NE when an Unit Missing Alarm is cleared
             The data passed with the event are
             1) UnitId
             2) UnitLabel
             3) UnitMissingAlarm
             4) equipTrapAcknowledge code number"
        ::= 604

    unitNotRespondingAlarmSet  TRAP-TYPE
        ENTERPRISE pdh
        DESCRIPTION
            "This event is generated by PDH-NE when an Unit Not Responding Alarm is set
             The data passed with the event are
             1) UnitId
             2) UnitLabel
             3) UnitNotRespondingAlarm
             4) equipTrapAcknowledge code number"
        ::= 605

    unitNotRespondingAlarmCleared  TRAP-TYPE
        ENTERPRISE pdh
        DESCRIPTION
            "This event is generated by PDH-NE when an Unit Not Responding Alarm  is cleared
             The data passed with the event are
             1) UnitId
             2) UnitLabel
             3) UnitNotRespondingAlarm
             4) equipTrapAcknowledge code number"
        ::= 606


    unitHwMismatchAlarmSet  TRAP-TYPE
        ENTERPRISE pdh
        DESCRIPTION
            "This event is generated by PDH-NE when an Unit Hw Mismatch Alarm is set
             The data passed with the event are
             1) UnitId
             2) UnitLabel
             3) Unit HwMismatch Alarm
             4) equipTrapAcknowledge code number"
        ::= 607

    unitHwMismatchAlarmCleared  TRAP-TYPE
        ENTERPRISE pdh
        DESCRIPTION
            "This event is generated by PDH-NE when an Unit Hw Mismatch Alarm is cleared
             The data passed with the event are
             1) UnitId
             2) UnitLabel
             3) Unit HwMismatchAlarm
             4) equipTrapAcknowledge code number"
        ::= 608


    unitSwMismatchAlarmSet  TRAP-TYPE
        ENTERPRISE pdh
        DESCRIPTION
            "This event is generated by PDH-NE when an Unit Hw Mismatch Alarm is set
             The data passed with the event are
             1) UnitId
             2) UnitLabel
             3) Unit HwMismatch Alarm
             4) equipTrapAcknowledge code number"
        ::= 609

    unitSwMismatchAlarmCleared  TRAP-TYPE
        ENTERPRISE pdh
        DESCRIPTION
            "This event is generated by PDH-NE when an Unit Hw Mismatch Alarm is cleared
             The data passed with the event are
             1) UnitId
             2) UnitLabel
             3) Unit HwMismatchAlarm
             4) equipTrapAcknowledge code number"
        ::= 610



--------------
--  4.8 Software Group
--  This group is used to manage the Sw present in the  equipment units.
--

    softwareEquipmentReleaseBench1   OBJECT-TYPE
        SYNTAX      DisplayString   (SIZE(0..15))
        ACCESS      read-only
        STATUS      mandatory
        DESCRIPTION
            "ASCII string identifying the equipment release present in Bench1"
        ::= { software 1 }

    softwareEquipmentReleaseBench1Status  OBJECT-TYPE
        SYNTAX      INTEGER{
                            notLoaded (1),
                            loaded   (2),
                            running (3)
                           }
        ACCESS      read-only
        STATUS      mandatory
        DESCRIPTION
            "Status of the bench 1 software"
        ::= { software 2 }

    softwareEquipmentReleaseBench2   OBJECT-TYPE
        SYNTAX      DisplayString   (SIZE(0..15))
        ACCESS      read-only
        STATUS      mandatory
        DESCRIPTION
            "ASCII string identifying the equipment release present in Bench2"
        ::= { software 3 }

    softwareEquipmentReleaseBench2Status  OBJECT-TYPE
        SYNTAX      INTEGER{
                            notLoaded (1),
                            loaded   (2),
                            running (3)
                           }
        ACCESS      read-only
        STATUS      mandatory
        DESCRIPTION
            "Status of the bench 2 software"
        ::= { software 4 }

    softwareIpAddressDwlServer  OBJECT-TYPE
        SYNTAX      IpAddress
        ACCESS      read-write
        STATUS      mandatory
        DESCRIPTION
            "Ip address of the remote element from which the Software is downloaded"
        ::= { software  5 }

    softwareGosipAddressDwlServer  OBJECT-TYPE
        SYNTAX      OCTET STRING    (SIZE(0..31))
        ACCESS      read-write
        STATUS      mandatory
        DESCRIPTION
            "GOSIP address of the remote element from which the Software is downloaded"
        ::= { software 6 }

    softwareDownloadfile   OBJECT-TYPE
        SYNTAX      DisplayString   (SIZE(0..255))
        ACCESS      read-write
        STATUS      mandatory
        DESCRIPTION
            "CEM or LOM Directory and name of the descriptor file. The files
             with the SW code must be present in the same directory"
        ::= { software 7 }

    softwareActionRequest   OBJECT-TYPE
        SYNTAX      INTEGER
        ACCESS      write-only
        STATUS      mandatory
        DESCRIPTION
            "This Integer is a bit string  with each bit when set has the following meaning:
             BIT 0   -    Download  request
             BIT 1   -    Abort Download  request
             BIT 2   -    Bench switch   request
             BIT 4   -    Partial download
             BIT 5   -    Forced Download 
             BIT 6   -    Implicit Activation
             The bit 4...6  enable/disable the different options on download request."
        ::= { software 8 }

    softwareDownloadStatus  OBJECT-TYPE
        SYNTAX      INTEGER{
                            downloading       (1),
                            completed         (2),
                            interrupted       (3),
                            perif-downloading (4)
                           }
        ACCESS      read-only
        STATUS      mandatory
        DESCRIPTION
            "Status of SW download operation"
        ::= { software 9 }

    softwareUnitTable  OBJECT-TYPE
        SYNTAX      SEQUENCE OF SoftwareUnitRecord
        ACCESS      not-accessible
        STATUS      mandatory
        DESCRIPTION
            "Table with Software records concerning units within the equipment"
        ::= { software 10 }

    softwareUnitRecord  OBJECT-TYPE
        SYNTAX      SoftwareUnitRecord
        ACCESS      not-accessible
        STATUS      mandatory
        DESCRIPTION
            "Software record"
        INDEX       { softwareUnitId, 
                      softwareElementId }
        ::= { softwareUnitTable 1 }

    SoftwareUnitRecord  ::=
        SEQUENCE{
            softwareUnitId
                INTEGER,
            softwareElementId
                INTEGER,
            softwareType
                INTEGER,
            softwareUnitReleaseBench1
                DisplayString,
            softwareUnitReleaseBench2
                DisplayString,
            softwareUnitActualRelease
                DisplayString
        }


    softwareUnitId  OBJECT-TYPE
        SYNTAX      INTEGER 
        ACCESS      read-only
        STATUS      mandatory
        DESCRIPTION
            "This object is used as Index of the softwareUnit Table and also identifies
             the unit in the equipment."
        ::= { softwareUnitRecord 1 }

    softwareElementId  OBJECT-TYPE
        SYNTAX      INTEGER 
        ACCESS      read-only
        STATUS      mandatory
        DESCRIPTION
            "This object is used as Index of the softwareUnit Table and also identifies
             the SW programmable element in the specified unit."
        ::= { softwareUnitRecord 2 }

    softwareType  OBJECT-TYPE
        SYNTAX      INTEGER {
                              s-record    (1),
                              image-FPGA  (2),
                              volatile    (3)
                            }
        ACCESS      read-only
        STATUS      mandatory
        DESCRIPTION
            "Format type"
        ::= { softwareUnitRecord 3 }

    softwareUnitReleaseBench1   OBJECT-TYPE
        SYNTAX      DisplayString   (SIZE(0..8))
        ACCESS      read-only
        STATUS      mandatory
        DESCRIPTION
            "ASCII string identifying the software release present
             in the programmable element of specified unit bench 1."
        ::= { softwareUnitRecord 4 }

    softwareUnitReleaseBench2   OBJECT-TYPE
        SYNTAX      DisplayString   (SIZE(0..8))
        ACCESS      read-only
        STATUS      mandatory
        DESCRIPTION
            "ASCII string identifying the software release present
             in the programmable element of specified unit bench 2"
        ::= { softwareUnitRecord 5 }

    softwareUnitActualRelease   OBJECT-TYPE
        SYNTAX      DisplayString   (SIZE(0..33))
        ACCESS      read-only
        STATUS      mandatory
        DESCRIPTION
            "ASCII string identifying the software release actually present
             in the programmable element of specified unit"
        ::= { softwareUnitRecord 6 }

    softwareDownloadStatusTrapNotification OBJECT-TYPE
        SYNTAX      INTEGER {
                             trapDisable (1),
                             trapEnable (2),
                             trapEnableWithACK (34)
                            }
        ACCESS      read-write
        STATUS      mandatory
        DESCRIPTION
            "Enable/disable the trap generation on download status change."
        DEFVAL      { trapEnable }
        ::= { software 11 }

--
-- The Software Group generates the following TRAP:
--

    softwareDownloadStatusTrap  TRAP-TYPE
        ENTERPRISE pdh
        DESCRIPTION
            "This event is generated by PDH-NE when the status of download is changed
             The data passed with the event are
             1) softwareDownloadStatus
             2) equipTrapAcknowledge code number"
        ::= 701



----------------------------------------------------------------------------------
--  4.9 RADIO EQUIPMENT GROUP
--  This group contains all the objects  that are specific of  the radio equipment.
----------------------------------------------------------------------------------

radioEquipmentRtCodeLabel  OBJECT-TYPE
     SYNTAX    DisplayString   (SIZE(0..20))
     ACCESS    read-only
     STATUS    mandatory
     DESCRIPTION "
           ASCII string used to describe the RT code  (i.e.RT29/17)
  "  ::=  { radioEquipment  1 }

radioEquipmentConfig OBJECT-TYPE
     SYNTAX    INTEGER {
                           normal-1-0 (1),
                           hetero-1-1 (2),
                           iso-1-1    (3)
                       }
     ACCESS      read-write
     STATUS      mandatory
     DESCRIPTION "
            The object describes the Radio equipment  configuration:
            not protected
            protected hetero frequency
            protected iso frequency
  "  ::=  { radioEquipment  2 }

radioEquipmentRtCode OBJECT-TYPE
     SYNTAX    INTEGER 
     ACCESS      read-only
     STATUS      mandatory
     DESCRIPTION "
           Radio equipment Rt code (SIAE number used to identify the channel plan
  "  ::=  { radioEquipment  3}

radioEquipmentCapacity OBJECT-TYPE
     SYNTAX    INTEGER {
                           pdh-2Mbit    (1),
                           pdh-2x2Mbit  (2),
                           pdh-4x2Mbit  (3),
                           pdh-8x2Mbit  (4),
                           pdh-16x2Mbit (5),
                           pdh-8Mbit    (6),
                           pdh-2x8Mbit  (7),
                           pdh-34Mbit   (8)
                      }
     ACCESS      read-write
     STATUS      mandatory
     DESCRIPTION "
           Radio equipment capacity
  "  ::=  { radioEquipment  4}


radioEquipmentFreqCh1 OBJECT-TYPE
     SYNTAX    INTEGER
     ACCESS      read-only
     STATUS      mandatory
     DESCRIPTION "
           First channel frequency (KHz)
  "  ::=  { radioEquipment  5}

radioEquipmentChNumber OBJECT-TYPE
     SYNTAX    INTEGER
     ACCESS      read-only
     STATUS      mandatory
     DESCRIPTION "
           Number of available radio channels
  "  ::=  { radioEquipment  6}

radioEquipmentBandCode OBJECT-TYPE
     SYNTAX    INTEGER {
                           low       (1),
                           high      (2)
                     }
     ACCESS      read-only
     STATUS      mandatory
     DESCRIPTION "
           Band Code
  "  ::=  { radioEquipment  7 }

radioEquipmentChChar OBJECT-TYPE
     SYNTAX    INTEGER {
                           standard  (1),
                           english   (2)
                     }
     ACCESS      read-only
     STATUS      mandatory
     DESCRIPTION "
           Channel Characteristic
  "  ::=  { radioEquipment  8 }

radioEquipmentLinkId OBJECT-TYPE
     SYNTAX    INTEGER
     ACCESS      read-write
     STATUS      mandatory
     DESCRIPTION "
           Link Identification (value 0..255)
  "  ::=  { radioEquipment  9 }


radioEquipmentGndRef  OBJECT-TYPE
     SYNTAX    INTEGER {
                            gnd    (1),
                            float  (2)
                       }
     ACCESS      read-write
     STATUS      mandatory
     DESCRIPTION "
           Tributary  ports  ground reference
  "  ::=  { radioEquipment  10 }

radioEquipmentAisRxInsertion  OBJECT-TYPE
     SYNTAX    INTEGER {
                            disable (1),
                            enable  (2)
                      }
     ACCESS      read-write
     STATUS      mandatory
     DESCRIPTION "
           AIS insertion receiver side enable
  "  ::=  { radioEquipment  11}

radioEquipmentAisTxInsertion  OBJECT-TYPE
     SYNTAX    INTEGER {
                            disable (1),
                            enable  (2)
                      }
     ACCESS      read-write
     STATUS      mandatory
     DESCRIPTION "
           AIS insertion transmitter  side enable
  "  ::=  { radioEquipment  12}

radioEquipmentTxPwrThresh  OBJECT-TYPE
     SYNTAX    INTEGER
     ACCESS      read-write
     STATUS      mandatory
     DESCRIPTION "
           Threshold (value +3 ( +15 dB) relative to nominal value of the TX power below wich the related alarm is set.
  "  ::=  { radioEquipment  13}

radioEquipmentRxPwrThresh  OBJECT-TYPE
     SYNTAX    INTEGER
     ACCESS      read-write
     STATUS      mandatory
     DESCRIPTION "
           Threshold (value -40 ( -99 dBm) for RX power below wich the related alarm is set.
  "  ::=  { radioEquipment  14}

radioEquipmentLberThresh  OBJECT-TYPE
     SYNTAX    INTEGER {
                            e-6  (1),
                            e-7  (2),
                            e-8  (3)
                      }

     ACCESS      read-write
     STATUS      mandatory
     DESCRIPTION "
           Threshold for LBER alarm
  "  ::=  { radioEquipment  15}


radioEquipmentHberThresh  OBJECT-TYPE
     SYNTAX    INTEGER {
                            e-3  (1),
                            e-4  (2),
                            e-5  (3)
                      }

     ACCESS      read-write
     STATUS      mandatory
     DESCRIPTION "
           Threshold for HBER alarm
  "  ::=  { radioEquipment  16}

radioEquipmentHberAisInsRxSw  OBJECT-TYPE
     SYNTAX    INTEGER {
                            disable (1),
                            enable  (2)
                      }
     ACCESS      read-write
     STATUS      mandatory
     DESCRIPTION "
           Enable HBER alarm as switching criterion (1+1 configuration) and for RX AIS insertion
  "  ::=  { radioEquipment  17}

radioEquipmentLberRxSw  OBJECT-TYPE
     SYNTAX    INTEGER {
                            disable (1),
                            enable  (2)
                      }
     ACCESS      read-write
     STATUS      mandatory
     DESCRIPTION "
           Enable LBER alarm as switching criterion (1+1 configuration).
  "  ::=  { radioEquipment  18}

radioEquipmentHdb3CodeAlarmEnable  OBJECT-TYPE
     SYNTAX    INTEGER {
                            disable (1),
                            enable  (2)
                      }
     ACCESS      read-write
     STATUS      mandatory
     DESCRIPTION "
           Enable measurement of the bit error rate in 2Mbit input signal computed on the HDB3 code violation (criterion to set signal
            LOS
  "  ::=  { radioEquipment  19}

radioEquipmentLinkIdAlarm  OBJECT-TYPE
     SYNTAX    INTEGER {
                           cleared                    (1),
                           activeReportable-Status    (2),
                           activeReportable-Warning   (3),
                           activeReportable-Minor     (4),
                           activeReportable-Major     (5),
                           activeReportable-Critical  (6)
                       }
     ACCESS      read-only
     STATUS      mandatory
     DESCRIPTION "
          Link Identification Alarm  with associated Severity
  "  ::=  { radioEquipment  20}

radioEquipmentLinkTelemetryFailAlarm  OBJECT-TYPE
     SYNTAX    INTEGER {
                           cleared                    (1),
                           activeReportable-Status    (2),
                           activeReportable-Warning   (3),
                           activeReportable-Minor     (4),
                           activeReportable-Major     (5),
                           activeReportable-Critical  (6)
                       }
     ACCESS      read-only
     STATUS      mandatory
     DESCRIPTION "
          Fail of link telemetry communication channel with associated Severity
  "  ::=  { radioEquipment  21}


radioEquipmentLinkIdAlarmSeverityCode  OBJECT-TYPE
     SYNTAX    INTEGER {
                            disable                       (1),
                            status-trapEnable             (2),
                            status-trapEnableWithACK      (34),
                            warning-trapEnable            (3),
                            warning-trapEnableWithACK     (35),
                            minor-trapEnable              (4),
                            minor-trapEnableWithACK       (36),
                            major-trapEnable              (5),
                            major-trapEnableWithACK       (37),
                            critical-trapEnable           (6),
                            critical-trapEnableWithACK    (38),
                            status-trapDisable            (18),
                            warning-trapDisable           (19),
                            minor-trapDisable             (20),
                            major-trapDisable             (21),
                            critical-trapDisable          (22)
                       }
     ACCESS      read-write
     STATUS      mandatory
     DESCRIPTION "
           Define the severity associated to theLink Id  Fail Alarm  and  enable/disable the trap generation on status change event.
     "  DEFVAL{ major-trapEnable }
    ::=  { radioEquipment 22 }



radioEquipmentLinkTelemetryFailAlarmSeverityCode  OBJECT-TYPE
     SYNTAX    INTEGER {
                            disable                       (1),
                            status-trapEnable             (2),
                            status-trapEnableWithACK      (34),
                            warning-trapEnable            (3),
                            warning-trapEnableWithACK     (35),
                            minor-trapEnable              (4),
                            minor-trapEnableWithACK       (36),
                            major-trapEnable              (5),
                            major-trapEnableWithACK       (37),
                            critical-trapEnable           (6),
                            critical-trapEnableWithACK    (38),
                            status-trapDisable            (18),
                            warning-trapDisable           (19),
                            minor-trapDisable             (20),
                            major-trapDisable             (21),
                            critical-trapDisable          (22)
                       }
     ACCESS      read-write
     STATUS      mandatory
     DESCRIPTION "
           Define the severity associated to the LinkTelemetryFailAlarm  and  enable/disable the trap generation on status change event.
     "  DEFVAL{ major-trapEnable }
    ::=  { radioEquipment 23 }

    radioEquipmentRxForcedSwitch  OBJECT-TYPE
        SYNTAX      INTEGER{
                            auto (1),
                            branch-1 (2),
                            branch-2 (3)
                           }
        ACCESS      read-write
        STATUS      mandatory
        DESCRIPTION
            "Receiver Forced switch enable (only if 1+1 configuration)"
        DEFVAL      { auto }
        ::= { radioEquipment 24 }

    radioEquipmentTxForcedSwitch  OBJECT-TYPE
        SYNTAX      INTEGER{
                            auto (1),
                            branch-1 (2),
                            branch-2 (3)
                           }
        ACCESS      read-write
        STATUS      mandatory
        DESCRIPTION
            "Transmitter Forced switch enable (only if 1+1 configuration and ISO system)"
        DEFVAL      { auto }
        ::= { radioEquipment 25 }

    radioEquipmentEarlyWarningRxSw  OBJECT-TYPE
        SYNTAX    INTEGER {
                            disable (1),
                            enable  (2)
                          }
        ACCESS      read-write
        STATUS      mandatory
        DESCRIPTION 
            "Enable EarlyWarning  alarm as switching criterion (1+1 configuration).  "  
        DEFVAL      { enable }
        ::=  { radioEquipment 26 }

    radioEquipmentRxTribFailAlarm  OBJECT-TYPE
        SYNTAX    INTEGER {
                           cleared                    (1),
                           activeReportable-Status    (2),
                           activeReportable-Warning   (3),
                           activeReportable-Minor     (4),
                           activeReportable-Major     (5),
                           activeReportable-Critical  (6)
                       }
        ACCESS      read-only
        STATUS      mandatory
        DESCRIPTION 
            "Fail of tributary reception with associated Severity"  
        ::=  { radioEquipment  27}

    radioEquipmentRxTribFailAlarmSeverityCode  OBJECT-TYPE
        SYNTAX    INTEGER {
                            disable                       (1),
                            status-trapEnable             (2),
                            status-trapEnableWithACK      (34),
                            warning-trapEnable            (3),
                            warning-trapEnableWithACK     (35),
                            minor-trapEnable              (4),
                            minor-trapEnableWithACK       (36),
                            major-trapEnable              (5),
                            major-trapEnableWithACK       (37),
                            critical-trapEnable           (6),
                            critical-trapEnableWithACK    (38),
                            status-trapDisable            (18),
                            warning-trapDisable           (19),
                            minor-trapDisable             (20),
                            major-trapDisable             (21),
                            critical-trapDisable          (22)
                       }
        ACCESS      read-write
        STATUS      mandatory
        DESCRIPTION 
            "Define the severity associated to the RxTribFailAlarm  and  
             enable/disable the trap generation on status change event."  
        DEFVAL{ major-trapEnable }
        ::=  { radioEquipment 28 }

    radioEquipmentManualSwitch  OBJECT-TYPE
        SYNTAX      INTEGER{
                            auto (1),
                            branch-1 (2),
                            branch-2 (3)
                           }
        ACCESS      read-write
        STATUS      mandatory
        DESCRIPTION
            "Receiver Manual switch enable (only if 1+1 configuration)"
        DEFVAL      { auto }
        ::= { radioEquipment 29 }

    radioEquipmentLocalLinkId OBJECT-TYPE
        SYNTAX      INTEGER
        ACCESS      read-write
        STATUS      mandatory
        DESCRIPTION 
            "Link Identification (value 0..255) for local terminal"
        ::=  { radioEquipment 30} 


----------------------------------------------------------------------------------
--  The Radio Equipment group generates the following TRAPs:
----------------------------------------------------------------------------------

    radioEquipmentLinkIdAlarmSet   TRAP-TYPE
        ENTERPRISE pdh
        DESCRIPTION
            "This event is generated by  PDH-NE when an radioEquipmentLinkIdAlarm is set
             No data are associated to the trap
             1) radioEquipmentLinkIdAlarm
             2) equipTrapAcknowledge code number"
        ::= 1801

    radioEquipmentLinkIdAlarmCleared   TRAP-TYPE
        ENTERPRISE pdh
        DESCRIPTION
            "This event is generated by  PDH-NE when an radioEquipmentLinkIdAlarm is cleared
             No data are associated to the trap
             1) radioEquipmentLinkIdAlarm
             2) equipTrapAcknowledge code number"
        ::= 1802

    radioEquipmentLinkTelemetryFailAlarmSet   TRAP-TYPE
        ENTERPRISE pdh
        DESCRIPTION
            "This event is generated by  PDH-NE when an radioEquipmentLinkTelemetryFailAlarm is set
             No data are associated to the trap
             1) radioEquipmentLinkTelemetryFailAlarm
             2) equipTrapAcknowledge code number"
        ::= 1803

    radioEquipmentLinkTelemetryFailAlarmCleared   TRAP-TYPE
        ENTERPRISE pdh
        DESCRIPTION
            "This event is generated by  PDH-NE when an radioEquipmentLinkTelemetryFailAlarm is cleared
             No data are associated to the trap
             1) radioEquipmentLinkTelemetryFailAlarm
             2) equipTrapAcknowledge code number"
        ::= 1804

    radioEquipmentRxTribFailAlarmSet   TRAP-TYPE
        ENTERPRISE pdh
        DESCRIPTION
            "This event is generated by  PDH-NE when an radioEquipmentLinkTelemetryFailAlarm is set
             No data are associated to the trap
             1) radioEquipmentLinkTelemetryFailAlarm
             2) equipTrapAcknowledge code number"
        ::= 1805

    radioEquipmentRxTribFailAlarmCleared   TRAP-TYPE
        ENTERPRISE pdh
        DESCRIPTION
            "This event is generated by  PDH-NE when an radioEquipmentLinkTelemetryFailAlarm is cleared
             No data are associated to the trap
             1) radioEquipmentLinkTelemetryFailAlarm
             2) equipTrapAcknowledge code number"
        ::= 1806


----------------------------------------------------------------------
--  4.10 PPI (PDH PHYSICAL INTERFACE) GROUP
----------------------------------------------------------------------------------
--  This object is associated to  the "Unit" object  and describes one of   the Pdh port.
----------------------------------------------------------------------------------

ppiTable  OBJECT-TYPE
     SYNTAX      SEQUENCE OF  PpiRecord
     ACCESS      not-accessible
     STATUS      mandatory
     DESCRIPTION "
          Table with PPI records describing Pdh  ports  within an unit.
  "  ::=  { ppi  1 }

ppiRecord  OBJECT-TYPE
     SYNTAX      PpiRecord
     ACCESS      not-accessible
     STATUS      mandatory
     DESCRIPTION "
          PPI  record"
     INDEX { ppiUnitId,  ppiId }
    ::=  { ppiTable 1 }

PpiRecord  ::=
   SEQUENCE {
        ppiUnitId
           INTEGER,
        ppiId
           INTEGER,
        ppiType
           INTEGER,
        ppiEnable
           INTEGER,
        ppiLosAlarm
           INTEGER,
        ppiLineLoop
           INTEGER,
        ppiRemoteLoop
           INTEGER
      }

ppiUnitId  OBJECT-TYPE
     SYNTAX    INTEGER
     ACCESS      read-only
     STATUS      mandatory
     DESCRIPTION "
           This object  identifies unit  where the PPI is  present LIM or  RIM ( 4x2 A only).
  "  ::=  { ppiRecord  1}

ppiId  OBJECT-TYPE
     SYNTAX    INTEGER
     ACCESS      read-only
     STATUS      mandatory
     DESCRIPTION "
           This object  identifies  the PPI  within the Unit.
  "  ::=  { ppiRecord  2 }

ppiType  OBJECT-TYPE
     SYNTAX    INTEGER {
                            pdh-2Mbit  (1),
                            pdh-8Mbit  (2),
                            pdh-34Mbit (3)
                      }

     ACCESS      read-only
     STATUS      mandatory
     DESCRIPTION "
           Define the  type of the PDH signal
  "  ::=  { ppiRecord  3 }

ppiEnable OBJECT-TYPE
     SYNTAX    INTEGER {
                            off (1),
                            on  (2)
                      }
     ACCESS      read-write
     STATUS      mandatory
     DESCRIPTION "
           Enable/disable the Pdh port on the Unit (This attribute is meanigfull if the Unit is LIM
    "  DEFVAL{ off }
    ::=  { ppiRecord  4 }

ppiLosAlarm  OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
          PPI Loss of  signal alarm  (Probable cause  = LossOf Signal)  status with associated Severity
  "  ::=  { ppiRecord  5}

ppiLineLoop OBJECT-TYPE
     SYNTAX    INTEGER {
                            loopOff (1),
                            loopOn  (2)
                       }
     ACCESS      read-write
     STATUS      mandatory
     DESCRIPTION "
           Enable/disable the line loop on  Pdh port.
    "  DEFVAL{ loopOff }
    ::=  { ppiRecord  6 }

ppiRemoteLoop OBJECT-TYPE
     SYNTAX    INTEGER {
                            loopOff (1),
                            loopOn  (2)
                       }
     ACCESS      read-write
     STATUS      mandatory
     DESCRIPTION "
           Enable/disable the remote   loop on Pdh  port.
    "  DEFVAL{ loopOff }
    ::=  { ppiRecord  9 }

----------------------------------------------------------------------------------
-- The following objects define the profile of the Pdh Phisycal Interface alarms:
----------------------------------------------------------------------------------

ppiLosSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the PPI Loss of  signal  and  enable/disable the trap generation on status change event.
     "  DEFVAL{ major-trapEnable }
    ::=  { ppi  2 }

----------------------------------------------------------------------------------
--  The Ppi  Group generates the following TRAPs:
----------------------------------------------------------------------------------

ppiLosAlarmSet  TRAP-TYPE
  ENTERPRISE pdh
  DESCRIPTION "
    This event is generated by  PDH-NE when  a ppiLosAlarm  is set
    The data passed with the event are:
       1) ppiId
       2) UnitId
       3) UnitLabel
       4) ppiLosAlarm
       5) equipTrapAcknowledge code number"
  ::= 1101

ppiLosAlarmCleared  TRAP-TYPE
  ENTERPRISE pdh
  DESCRIPTION "
    This event is generated by  PDH-NE when a ppiLosAlarm is cleared
    The data passed with the event are:
       1) ppiId
       2) UnitId
       3) UnitLabel
       4) ppiLosAlarm
       5) equipTrapAcknowledge code number"
  ::= 1102



----------------------------------------------------------------------------------
--  4.11 RADIO BRANCH GROUP
----------------------------------------------------------------------------------
--  This object  describes a  Radio Branch (Modulator/Demodulator and Tranceiver units).
----------------------------------------------------------------------------------

radioBranchTable  OBJECT-TYPE
     SYNTAX      SEQUENCE OF  RadioBranchRecord
     ACCESS      not-accessible
     STATUS      mandatory
     DESCRIPTION "
          Table with RadioBranch records: one record for 1+0 configuration and two record for 1+1 configuration.
  "  ::=  { radioBranch  1 }

radioBranchRecord  OBJECT-TYPE
     SYNTAX     RadioBranchRecord
     ACCESS      not-accessible
     STATUS      mandatory
     DESCRIPTION "
          RadioBranch  record"
     INDEX { radioBranchId }
    ::=  { radioBranchTable 1 }

RadioBranchRecord  ::=
   SEQUENCE {
        radioBranchId
           INTEGER,
        radioBranchRadioChannel
           INTEGER,
        radioBranchTransmitterStatus
           INTEGER,
        radioBranchCarrierOnly
           INTEGER,
        radioBranchPrx
           INTEGER,
        radioBranchPtx
           INTEGER, 
        radioBranchRimPsuFailAlarm
           INTEGER,
        radioBranchRtPsuFailAlarm
           INTEGER,
        radioBranchRxPowerLowAlarm
           INTEGER,
        radioBranchTxPowerLowAlarm
           INTEGER,
        radioBranchModulatorFailAlarm
           INTEGER,
        radioBranchDemodulatorFailAlarm
           INTEGER,
        radioBranchDemLberAlarm
           INTEGER,
        radioBranchDemHberAlarm
           INTEGER,
        radioBranchCableOpenAlarm
           INTEGER,
        radioBranchCableShortAlarm
           INTEGER,
        radioBranchBaseBandTxAlarm
           INTEGER,
        radioBranchBaseBandRxAlarm
           INTEGER,
        radioBranch2MbitALosAlarm
           INTEGER,
        radioBranch2MbitBLosAlarm
           INTEGER,
        radioBranch2MbitCLosAlarm
           INTEGER,
        radioBranch2MbitDLosAlarm
           INTEGER,
        radioBranchIduOduCommunicationAlarm
           INTEGER,
        radioBranchIFLoop
           INTEGER,
        radioBranchRFLoop
           INTEGER,
        radioBranchMulLoop
           INTEGER,
        radioBranchBinbexLoop
           INTEGER,
        radioBranchRemoteIFLoop
           INTEGER,
        radioBranchRxActiveStatus
           INTEGER,
        radioBranchTxActiveStatus
           INTEGER,
        radioBranchDemMantBer
           INTEGER,
        radioBranchDemExpBer
           INTEGER,
        radioBranchDemErr
           INTEGER,
        radioBranchTimeBer
           INTEGER,
        radioBranchStartBer
           INTEGER,
        radioBranchLocalChNum
           INTEGER,
        radioBranchOduBncAccess
           INTEGER
      }

radioBranchId  OBJECT-TYPE
     SYNTAX    INTEGER
     ACCESS      read-only
     STATUS      mandatory
     DESCRIPTION "
           This object  identifies  the  Radio Branch.
  "  ::=  { radioBranchRecord  1 }

radioBranchRadioChannel  OBJECT-TYPE
     SYNTAX    INTEGER
     ACCESS      read-write
     STATUS      mandatory
     DESCRIPTION "
         Number of the radio channel
  "  ::=  { radioBranchRecord  2 }

radioBranchTransmitterStatus OBJECT-TYPE
     SYNTAX    INTEGER {
                           transmitterOff (1),
                           transmitterOn  (2)
                        }
     ACCESS      read-write
     STATUS      mandatory
     DESCRIPTION "
         Transmitter status control.
      "  DEFVAL{ transmitterOn }
    ::=  { radioBranchRecord  3 }

radioBranchCarrierOnly  OBJECT-TYPE
     SYNTAX    INTEGER {
                           carrierOnlyOff (1),
                           carrierOnlyOn  (2)
                        }
     ACCESS      read-write
     STATUS      mandatory
     DESCRIPTION "
         Carrier only transmission  control.
      "  DEFVAL{ carrierOnlyOff }
    ::=  { radioBranchRecord  4 }
    
     
radioBranchPrx  OBJECT-TYPE
     SYNTAX      INTEGER
     ACCESS      read-only
     STATUS      mandatory
     DESCRIPTION
        "Received power level (dBm)"
     ::=  { radioBranchRecord  5}    
    
    
radioBranchPtx  OBJECT-TYPE
     SYNTAX      INTEGER
     ACCESS      read-write
     STATUS      mandatory
     DESCRIPTION
         "Attenuation value for transmitted power level (dB)"
     ::=  { radioBranchRecord  6}    
    
    
radioBranchRimPsuFailAlarm OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
         RIM power supply  alarm  (Probable cause  = xxxx)  status with associated Severity.
  "  ::=  { radioBranchRecord  7 }

radioBranchRtPsuFailAlarm  OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
         Tranceiver   power  supply   alarm  (Probable cause  = xxxx)  status with associated Severity.
  "  ::=  { radioBranchRecord  8 }

radioBranchRxPowerLowAlarm  OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
         Receiver  power  low alarm  (Probable cause  = xxxx)  status with associated Severity.
  "  ::=  { radioBranchRecord  9 }

radioBranchTxPowerLowAlarm  OBJECT-TYPE
     SYNTAX    INTEGER {            
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
         Transmitter  power  low   alarm  (Probable cause  = xxxx)  status with associated Severity.
  "  ::=  { radioBranchRecord 10 }

radioBranchModulatorFailAlarm  OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
         Modulator Fail Alarm   (Probable cause  = xxxx)  status with associated Severity.
  "  ::=  { radioBranchRecord  11 }

radioBranchDemodulatorFailAlarm  OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
         Demodulator Fail Alarm   (Probable cause  = xxxx)  status with associated Severity.
  "  ::=  { radioBranchRecord  12 }

radioBranchDemLberAlarm OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
         Low BER Alarm   (Probable cause  = xxxx)  status with associated Severity.
  "  ::=  { radioBranchRecord  13 }

radioBranchDemHberAlarm OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
         High BER Alarm
  "  ::=  { radioBranchRecord  14 }



radioBranchCableOpenAlarm OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
         The cable between IDU and ODU is open (SPU5 only)   (Probable cause  = xxxx)  with associated Severity.
  "  ::=  { radioBranchRecord  15 }

radioBranchCableShortAlarm OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
         A short circuit is present in the cable between IDU and ODU (SPU5 only)   (Probable cause  = xxxx)  with associated
         Severity.
  "  ::=  { radioBranchRecord  16 }

radioBranchBaseBandTxAlarm  OBJECT-TYPE
     SYNTAX    INTEGER { 
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
        Base Band Tx  alarm  (Probable cause  = xxxx)  status with associated Severity.
  "  ::=  { radioBranchRecord  17 }

radioBranchBaseBandRxAlarm  OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
        Base Band Rx  alarm  (Probable cause  = xxxx)  status with associated Severity.
  "  ::=  { radioBranchRecord  18 }

radioBranch2MbitALosAlarm OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
        2Mbit signal loss  at the RIM input (SPU5 4x2 -A only)  (Probable cause  = xxxx)  status with associated Severity.
  "  ::=  { radioBranchRecord  19 }

radioBranch2MbitBLosAlarm OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
        2Mbit signal loss  at the RIM input (SPU5 4x2 -A only)  (Probable cause  = xxxx)  status with associated Severity.
  "  ::=  { radioBranchRecord  20 }

radioBranch2MbitCLosAlarm OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
        2Mbit signal loss  at the RIM input (SPU5 4x2 -A only)  (Probable cause  = xxxx)  status with associated Severity.
  "  ::=  { radioBranchRecord  21 }

radioBranch2MbitDLosAlarm OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
        2Mbit signal loss  at the RIM input (SPU5 4x2 -A only)  (Probable cause  = xxxx)  status with associated Severity.
  "  ::=  { radioBranchRecord  22 }

radioBranchIduOduCommunicationAlarm  OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
        IDU ODU Communication channel alarm  (Probable cause  = xxxx)  status with associated Severity.
  "  ::=  { radioBranchRecord  23 }

radioBranchIFLoop OBJECT-TYPE
     SYNTAX    INTEGER {
                            loopOff (1),
                            loopOn  (2)
                      }
     ACCESS      read-write
     STATUS      mandatory
     DESCRIPTION "
           Enable/disable the  local IF   loop.
    "  DEFVAL{ loopOff }
    ::=  { radioBranchRecord  24 }

radioBranchRFLoop OBJECT-TYPE
     SYNTAX    INTEGER {
                            loopOff (1),
                            loopOn  (2)
                      }
     ACCESS      read-write
     STATUS      mandatory
     DESCRIPTION "
           Enable/disable the  local RF   loop.
    "  DEFVAL{ loopOff }
    ::=  { radioBranchRecord  25 }

radioBranchMulLoop OBJECT-TYPE
     SYNTAX    INTEGER {
                            loopOff (1),
                            loopOn  (2)
                      }
     ACCESS      read-write
     STATUS      mandatory
     DESCRIPTION "
           Enable/disable the  local Mul   loop.
    "  DEFVAL{ loopOff }
    ::=  { radioBranchRecord  26 }

radioBranchBinbexLoop OBJECT-TYPE
     SYNTAX    INTEGER {
                            loopOff (1),
                            loopOn  (2)
                      }
     ACCESS      read-write
     STATUS      mandatory
     DESCRIPTION "
           Enable/disable the  local Binbex   loop.
    "  DEFVAL{ loopOff }
    ::=  { radioBranchRecord  27 }

radioBranchRemoteIFLoop OBJECT-TYPE
     SYNTAX    INTEGER {
                            loopOff (1),
                            loopOn  (2)
                      }
     ACCESS      read-write
     STATUS      mandatory
     DESCRIPTION "
           Enable/disable the  remote IF    loop.
    "  DEFVAL{ loopOff }
    ::=  { radioBranchRecord  28 }

radioBranchRxActiveStatus OBJECT-TYPE
     SYNTAX    INTEGER {
                            cleared (1),
                            active (2)
                        }
     ACCESS      read-only
     STATUS      mandatory
     DESCRIPTION "
           Receiver Active  status  (Probable cause  =  xxxxx )  status with associated Severity (meaningfull in 1+1 configuration)
  "  ::=  { radioBranchRecord  29 }

radioBranchTxActiveStatus OBJECT-TYPE
     SYNTAX    INTEGER {
                            cleared (1),
                            active (2)
                        }
     ACCESS      read-only
     STATUS      mandatory
     DESCRIPTION "
           Transmitter  Active  status  (Probable cause  =  xxxxx )  status with associated Severity (1+1 ISO sistem only)
  "  ::=  { radioBranchRecord  30 }

    radioBranchDemMantBer  OBJECT-TYPE
        SYNTAX      INTEGER
        ACCESS      read-only
        STATUS      mandatory
        DESCRIPTION
            "Mantissa of Measured BER (n*10-x)"
        ::= { radioBranchRecord 31 }

    radioBranchDemExpBer  OBJECT-TYPE
        SYNTAX      INTEGER
        ACCESS      read-only
        STATUS      mandatory
        DESCRIPTION
            "Exponent of Measured BER (n*10-x)"
        ::= { radioBranchRecord 32 }

    radioBranchDemErr  OBJECT-TYPE
        SYNTAX      INTEGER
        ACCESS      read-only
        STATUS      mandatory
        DESCRIPTION
           "Number of error"
        ::= { radioBranchRecord 33 }

    radioBranchTimeBer OBJECT-TYPE
        SYNTAX      INTEGER
        ACCESS      read-only
        STATUS      mandatory
        DESCRIPTION
            "Elapsed time since the start of Ber evaluation command"
        ::= { radioBranchRecord 34 }

   radioBranchStartBer  OBJECT-TYPE
        SYNTAX      INTEGER{
                            on (2)
                            }
        ACCESS      write-only
        STATUS      mandatory
        DESCRIPTION
            "Reset BER and Start BER evaluation"
        ::= { radioBranchRecord 35 }

   radioBranchLocalChNum  OBJECT-TYPE
        SYNTAX    INTEGER
        ACCESS      read-write
        STATUS      mandatory
        DESCRIPTION "
         Number of the radio channel (assigned to the local terminal)
"  ::=  { radioBranchRecord 36 }

  radioBranchOduBncAccess  OBJECT-TYPE
      SYNTAX    INTEGER {
                          agcVoltageMeter   (1),
                          portableTestSet   (2)
                        }
      ACCESS      read-write
      STATUS      mandatory
      DESCRIPTION "
         Select if the Agc Voltage Meter  or the Portable Test Set is connected to the    
         ODU BNC. "
        ::=  { radioBranchRecord  37}


----------------------------------------------------------------------------------
--  The following objects define the profile of the RadioBranch  alarms:
--
--  The general stucture of the object is the following:
--

-- radioBranch<AlarmName>SeverityCode  OBJECT-TYPE
--     SYNTAX    INTEGER {
--                            disable                    (1),
--                            status-trapEnable          (2),
--                            status-trapEnableWithACK   (34),
--                            warning-trapEnable         (3),
--                            warning-trapEnableWithACK  (35),
--                            minor-trapEnable           (4),
--                            minor-trapEnableWithACK    (36),
--                            major-trapEnable           (5),
--                            major-trapEnableWithACK    (37),
--                            critical-trapEnable        (6),
--                            critical-trapEnableWithACK (38),
--                            status-trapDisable         (18),
--                            warning-trapDisable        (19),
--                            minor-trapDisable          (20),
--                            major-trapDisable          (21),
--                            critical-trapDisable       (22)
--                       }
--     ACCESS      read-write
--     STATUS      mandatory
--     DESCRIPTION "
--           Define the severity associated to the  <alarm name>  and  enable/disable the trap generation on status
--           change   event.
--     "  DEFVAL{ x }
--    ::=  {radioBranch  y }
----------------------------------------------------------------------------------

radioBranchRimPsuFailAlarmSeverityCode  OBJECT-TYPE
     SYNTAX     INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the RadioBranchRimPsuFailAlarm and  enable/disable the trap generation on status
           change   event.
     "  DEFVAL{ major-trapEnable }
    ::=  { radioBranch  2 }

radioBranchRtPsuFailAlarmSeverityCode  OBJECT-TYPE
     SYNTAX     INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the RadioBranchRtPsuFailAlarm  and  enable/disable the trap generation on status
           change   event.
     "  DEFVAL{ major-trapEnable }
    ::=  { radioBranch  3 }

radioBranchRxPowerLowAlarmSeverityCode  OBJECT-TYPE
     SYNTAX     INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the RadioBranchRxPowerLowAlarm  and  enable/disable the trap generation on status
           change   event.
     "  DEFVAL{ major-trapEnable }
    ::=  { radioBranch  4 }

radioBranchTxPowerLowAlarmSeverityCode  OBJECT-TYPE
     SYNTAX     INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the radioBranchTxPowerLowAlarm  and  enable/disable the trap generation on status
           change   event.
     "  DEFVAL{ major-trapEnable }
    ::=  { radioBranch  5 }

radioBranchModulatorFailAlarmSeverityCode  OBJECT-TYPE
     SYNTAX     INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the radioBranchModulatorFailAlarm  and  enable/disable the trap generation on status
           change   event.
     "  DEFVAL{ major-trapEnable }
    ::=  { radioBranch  6 }

radioBranchDemodulatorFailAlarmSeverityCode  OBJECT-TYPE
     SYNTAX     INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the radioBranchDemodulatorFailAlarm  and  enable/disable the trap generation on status
           change   event.
     "  DEFVAL{ major-trapEnable }
    ::=  { radioBranch  7 }

radioBranchDemLberAlarmSeverityCode  OBJECT-TYPE
     SYNTAX     INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the radioBranchDemLberAlarm  and  enable/disable the trap generation on status
           change   event.
     "  DEFVAL{ minor-trapEnable }
    ::=  { radioBranch  8 }

radioBranchDemHberAlarmSeverityCode  OBJECT-TYPE
     SYNTAX     INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the radioBranchDemHberAlarm and  enable/disable the trap generation on status
           change   event.
     "  DEFVAL{ major-trapEnable }
    ::=  { radioBranch  9 }

radioBranchCableOpenAlarmSeverityCode  OBJECT-TYPE
     SYNTAX     INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the radioBranchCableOpenAlarm and  enable/disable the trap generation on status
           change   event.
     "  DEFVAL{ major-trapEnable }
    ::=  { radioBranch  10 }

radioBranchCableShortAlarmSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the radioBranchCableShortAlarm and  enable/disable the trap generation on status
           change   event.
     "  DEFVAL{ major-trapEnable }
    ::=  { radioBranch  11 }

radioBranchBaseBandTxAlarmSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the radioBranchBaseBandTxAlarm  and  enable/disable the trap generation on status
           change   event.
     "  DEFVAL{ major-trapEnable }
    ::=  { radioBranch  12 }

radioBranchBaseBandRxAlarmSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the radioBranchBaseBandRxAlarm  and  enable/disable the trap generation on status
           change   event.
     "  DEFVAL{ major-trapEnable }
    ::=  { radioBranch  13 }

radioBranch2MbitALosAlarmSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the radioBranch2MbitALosAlarm  (SPU5 4x2 - A) and  enable/disable the trap generation
           on status change   event.
     "  DEFVAL{ major-trapEnable }
    ::=  { radioBranch  14 }

radioBranch2MbitBLosAlarmSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the radioBranch2MbitBLosAlarm  (SPU5 4x2 - A) and  enable/disable the trap generation
           on status change   event.
     "  DEFVAL{ major-trapEnable }
    ::=  { radioBranch  15 }

radioBranch2MbitCLosAlarmSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the radioBranch2MbitCLosAlarm  (SPU5 4x2 - A) and  enable/disable the trap generation
           on status change   event.
     "  DEFVAL{ major-trapEnable }
    ::=  { radioBranch  16 }

radioBranch2MbitDLosAlarmSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the radioBranch2MbitDLosAlarm  (SPU5 4x2 - A) and  enable/disable the trap generation
           on status change   event.
     "  DEFVAL{ major-trapEnable }
    ::=  { radioBranch  17 }

radioBranchIduOduCommunicationAlarmSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the radioBranchIduOduCommunicationAlarm  and  enable/disable the trap generation
           on status change   event.
     "  DEFVAL{ major-trapEnable }
    ::=  { radioBranch  18 }

radioBranchRxActiveStatusSeverityCode  OBJECT-TYPE
     SYNTAX    INTEGER {
                            trapDisable (1),
                            trapEnable (2),
                            trapEnableWithACK (34)
                       }
     ACCESS      read-write
     STATUS      mandatory
     DESCRIPTION "
           Define the severity associated to the radioBranchRxActivestatus  and  enable/disable the trap generation
           on status change   event."
        DEFVAL{ trapEnable }
    ::=  { radioBranch  19 }

radioBranchTxActiveStatusSeverityCode  OBJECT-TYPE
     SYNTAX    INTEGER {
                            trapDisable (1),
                            trapEnable (2),
                            trapEnableWithACK (34)
                       }
     ACCESS      read-write
     STATUS      mandatory
     DESCRIPTION "
           Define the severity associated to the radioBranchTxActivestatus  and  enable/disable the trap generation
           on status change   event.
     "  DEFVAL{ trapEnable }
    ::=  { radioBranch  20 }
    
radioBranchPrxHysteresisValue  OBJECT-TYPE
     SYNTAX      INTEGER
     ACCESS      read-write
     STATUS      mandatory
     DESCRIPTION
         "Define the delta value associated to the RadioBranchPrx before having a new trap generation.
          A zero disable the trap generation."
     DEFVAL      { 0 }
     ::= { radioBranch 21 }

radioBranchPrxHysteresisValueTrapNotification OBJECT-TYPE
     SYNTAX      INTEGER {
                          trapDisable        (1),
                          trapEnable         (2),
                          trapEnableWithACK  (34)
                         }
     ACCESS      read-write
     STATUS      mandatory
     DESCRIPTION
         "Enable/disable the trap generation on status change event."
     DEFVAL      { trapEnable }
     ::= { radioBranch 22 }


      
----------------------------------------------------------------------------------
--  The RadioBranch  Group generates the following TRAPs:
----------------------------------------------------------------------------------
  
  
radioBranchRimPsuFailAlarmSet  TRAP-TYPE
  ENTERPRISE pdh
  DESCRIPTION "
    This event is generated by  PDH-NE when  a radioBranchRimPsuFailAlarm  is set
    The data passed with the event are:
       1) radioBranchId 
       2) RimPsuFailAlarm
       3) equipTrapAcknowledge code number"
  ::= 1701
  
radioBranchRimPsuFailAlarmCleared  TRAP-TYPE
  ENTERPRISE pdh
  DESCRIPTION "
    This event is generated by  PDH-NE when a radioBranchRimPsuFailAlarm is cleared
    The data passed with the event are:
       1) radioBranchId 
       2) RimPsuFailAlarm
       3) equipTrapAcknowledge code number"
    ::= 1702

radioBranchRtPsuFailAlarmSet  TRAP-TYPE
  ENTERPRISE pdh
  DESCRIPTION "
    This event is generated by  PDH-NE when  a  radioBranchRtPsuFailAlarm  is set
    The data passed with the event are:
       1) radioBranchId 
       2) RtPsuFailAlarm
       3) equipTrapAcknowledge code number"
  ::= 1703

radioBranchRtPsuFailAlarmCleared  TRAP-TYPE
  ENTERPRISE pdh
  DESCRIPTION "
    This event is generated by  PDH-NE when a radioBranchRtPsuFailAlarm is cleared
    The data passed with the event are:
       1) radioBranchId 
       2) RtPsuFailAlarm
       3) equipTrapAcknowledge code number"
  ::= 1704

radioBranchRxPowerLowAlarmSet  TRAP-TYPE
  ENTERPRISE pdh
  DESCRIPTION "
    This event is generated by  PDH-NE when  a radioBranchRxPowerLowAlarm  is set
    The data passed with the event are:
       1) radioBranchId 
       2) RxPowerLowAlarm
       3) equipTrapAcknowledge code number"
  ::= 1705

radioBranchRxPowerLowAlarmCleared  TRAP-TYPE
  ENTERPRISE pdh
  DESCRIPTION "
    This event is generated by  PDH-NE when a radioBranchRxPowerLowAlarm is cleared
    The data passed with the event are:
       1) radioBranchId 
       2) RxPowerLowAlarm
       3) equipTrapAcknowledge code number"
  ::= 1706

radioBranchTxPowerLowAlarmSet  TRAP-TYPE
  ENTERPRISE pdh
  DESCRIPTION "
    This event is generated by  PDH-NE when  a radioBranchTxPowerLowAlarm  is set
    The data passed with the event are:
       1) radioBranchId 
       2) TxPowerLowAlarm
       3) equipTrapAcknowledge code number"
  ::= 1707

radioBranchTxPowerLowAlarmCleared  TRAP-TYPE
  ENTERPRISE pdh
  DESCRIPTION "
    This event is generated by  PDH-NE when a radioBranchTxPowerLowAlarm  is cleared
    The data passed with the event are:
       1) radioBranchId 
       2) TxPowerLowAlarm
       3) equipTrapAcknowledge code number"
  ::= 1708

radioBranchModulatorFailAlarmSet  TRAP-TYPE
  ENTERPRISE pdh
  DESCRIPTION "
    This event is generated by  PDH-NE when  a radioBranchModulatorFailAlarm  is set
    The data passed with the event are:
       1) radioBranchId 
       2) ModulatorFailAlarm
       3) equipTrapAcknowledge code number"
  ::= 1709

radioBranchModulatorFailAlarmCleared  TRAP-TYPE
  ENTERPRISE pdh
  DESCRIPTION "
    This event is generated by  PDH-NE when a radioBranchModulatorFailAlarm   is cleared
    The data passed with the event are:
       1) radioBranchId 
       2) ModulatorFailAlarm
       3) equipTrapAcknowledge code number"
  ::= 1710

radioBranchDemodulatorFailAlarmSet  TRAP-TYPE
  ENTERPRISE pdh
  DESCRIPTION "
    This event is generated by  PDH-NE when  a radioBranchDemodulatorFailAlarm  is set
    The data passed with the event are:
       1) radioBranchId 
       2) DemodulatorFailAlarm
       3) equipTrapAcknowledge code number"
  ::= 1711

radioBranchDemodulatorFailAlarmCleared  TRAP-TYPE
  ENTERPRISE pdh
  DESCRIPTION "
    This event is generated by  PDH-NE when a radioBranchDemodulatorFailAlarm  is cleared
    The data passed with the event are:
       1) radioBranchId 
       2) DemodulatorFailAlarm
       3) equipTrapAcknowledge code number"
  ::= 1712

radioBranchDemLberAlarmSet  TRAP-TYPE
  ENTERPRISE pdh
  DESCRIPTION "
    This event is generated by  PDH-NE when  a radioBranchDemLberAlarm is set
    The data passed with the event are:
       1) radioBranchId
       2) DemLberAlarm 
       3) equipTrapAcknowledge code number"
  ::= 1713

radioBranchDemLberAlarmCleared  TRAP-TYPE
  ENTERPRISE pdh
  DESCRIPTION "
    This event is generated by  PDH-NE when a radioBranchDemLberAlarm is cleared
    The data passed with the event are:
       1) radioBranchId 
       2) DemLberAlarm
       3) equipTrapAcknowledge code number"
  ::= 1714

radioBranchDemHberAlarmSet  TRAP-TYPE
  ENTERPRISE pdh
  DESCRIPTION "
    This event is generated by  PDH-NE when  a radioBranchDemHberAlarm is set
    The data passed with the event are:
       1) radioBranchId 
       2) DemHberAlarm
       3) equipTrapAcknowledge code number"
  ::= 1715

radioBranchDemHberAlarmCleared  TRAP-TYPE
  ENTERPRISE pdh
  DESCRIPTION "
    This event is generated by  PDH-NE when a radioBranchDemHberAlarm  is cleared
    The data passed with the event are:
       1) radioBranchId 
       2) DemHberAlarm
       3) equipTrapAcknowledge code number"
  ::= 1716

radioBranchCableOpenAlarmSet  TRAP-TYPE
  ENTERPRISE pdh
  DESCRIPTION "
    This event is generated by  PDH-NE when  a radioBranchCableOpenAlarm is set
    The data passed with the event are:
       1) radioBranchId 
       2) CableOpenAlarm
       3) equipTrapAcknowledge code number"
  ::= 1717

radioBranchCableOpenAlarmCleared  TRAP-TYPE
  ENTERPRISE pdh
  DESCRIPTION "
    This event is generated by  PDH-NE when a radioBranchCableOpenAlarm is cleared
    The data passed with the event are:
       1) radioBranchId 
       2) CableOpenAlarm
       3) equipTrapAcknowledge code number"
  ::= 1718

radioBranchCableShortAlarmSet  TRAP-TYPE
  ENTERPRISE pdh
  DESCRIPTION "
    This event is generated by  PDH-NE when  a radioBranchCableShortAlarm is set
    The data passed with the event are:
       1) radioBranchId 
       2) CableShortAlarm
       3) equipTrapAcknowledge code number"
  ::= 1719

radioBranchCableShortAlarmCleared  TRAP-TYPE
  ENTERPRISE pdh
  DESCRIPTION "
    This event is generated by  PDH-NE when a radioBranchCableShortAlarm is cleared
    The data passed with the event are:
       1) radioBranchId 
       2) CableShortAlarm
       3) equipTrapAcknowledge code number"
  ::= 1720

radioBranchBaseBandTxAlarmSet  TRAP-TYPE
  ENTERPRISE pdh
  DESCRIPTION "
    This event is generated by  PDH-NE when  a radioBranchBaseBandTxAlarm is set
    The data passed with the event are:
       1) radioBranchId 
       2) BaseBandTxAlarm
       3) equipTrapAcknowledge code number"
  ::= 1721

radioBranchBaseBandTxAlarmCleared  TRAP-TYPE
  ENTERPRISE pdh
  DESCRIPTION "
    This event is generated by  PDH-NE when a radioBranchBaseBandTxAlarm  is cleared
    The data passed with the event are:
       1) radioBranchId 
       2) BaseBandTxAlarm
       3) equipTrapAcknowledge code number"
  ::= 1722

radioBranchBaseBandRxAlarmSet  TRAP-TYPE
  ENTERPRISE pdh
  DESCRIPTION "
    This event is generated by  PDH-NE when  a radioBranchBaseBandRxAlarm is set
    The data passed with the event are:
       1) radioBranchId 
       2) BaseBandRxAlarm
       3) equipTrapAcknowledge code number"
  ::= 1723

radioBranchBaseBandRxAlarmCleared  TRAP-TYPE
  ENTERPRISE pdh
  DESCRIPTION "
    This event is generated by  PDH-NE when a radioBranchBaseBandRxAlarm  is cleared
    The data passed with the event are:
       1) radioBranchId 
       2) BaseBandRxAlarm
       3) equipTrapAcknowledge code number"
  ::= 1724

radioBranch2MbitALosAlarmSet  TRAP-TYPE
  ENTERPRISE pdh
  DESCRIPTION "
    This event is generated by  PDH-NE when  a radioBranch2MbitALosAlarm  is set
    The data passed with the event are:
       1) radioBranchId 
       2) 2MbitALosAlarm
       3) equipTrapAcknowledge code number"
  ::= 1725

radioBranch2MbitALosAlarmCleared  TRAP-TYPE
  ENTERPRISE pdh
  DESCRIPTION "
    This event is generated by  PDH-NE when a radioBranch2MbitALosAlarm is cleared
    The data passed with the event are:
       1) radioBranchId 
       2) 2MbitALosAlarm
       3) equipTrapAcknowledge code number"
  ::= 1726

radioBranch2MbitBLosAlarmSet  TRAP-TYPE
  ENTERPRISE pdh
  DESCRIPTION "
    This event is generated by  PDH-NE when  a radioBranch2MbitBLosAlarm  is set
    The data passed with the event are:
       1) radioBranchId 
       2) 2MbitBLosAlarm
       3) equipTrapAcknowledge code number"
  ::= 1727

radioBranch2MbitBLosAlarmCleared  TRAP-TYPE
  ENTERPRISE pdh
  DESCRIPTION "
    This event is generated by  PDH-NE when a radioBranch2MbitBLosAlarm is cleared
    The data passed with the event are:
       1) radioBranchId 
       2) 2MbitBLosAlarm
       3) equipTrapAcknowledge code number"
  ::= 1728

radioBranch2MbitCLosAlarmSet  TRAP-TYPE
  ENTERPRISE pdh
  DESCRIPTION "
    This event is generated by  PDH-NE when  a radioBranch2MbitCLosAlarm  is set
    The data passed with the event are:
       1) radioBranchId 
       2) 2MbitCLosAlarm
       3) equipTrapAcknowledge code number"
  ::= 1729

radioBranch2MbitCLosAlarmCleared  TRAP-TYPE
  ENTERPRISE pdh
  DESCRIPTION "
    This event is generated by  PDH-NE when a radioBranch2MbitCLosAlarm is cleared
    The data passed with the event are:
       1) radioBranchId 
       2) 2MbitCLosAlarm
       3) equipTrapAcknowledge code number"
  ::= 1730

radioBranch2MbitDLosAlarmSet  TRAP-TYPE
  ENTERPRISE pdh
  DESCRIPTION "
    This event is generated by  PDH-NE when  a radioBranch2MbitDLosAlarm  is set
    The data passed with the event are:
       1) radioBranchId 
       2) 2MbitDLosAlarm
       3) equipTrapAcknowledge code number"
  ::= 1731

radioBranch2MbitDLosAlarmCleared  TRAP-TYPE
  ENTERPRISE pdh
  DESCRIPTION "
    This event is generated by  PDH-NE when a radioBranch2MbitDLosAlarm is cleared
    The data passed with the event are:
       1) radioBranchId 
       2) 2MbitDLosAlarm
       3) equipTrapAcknowledge code number"
  ::= 1732

radioBranchIduOduCommunicationAlarmSet TRAP-TYPE
  ENTERPRISE pdh
  DESCRIPTION "
    This event is generated by  PDH-NE when a radioBranchIduOduCommunicationAlarm is set
    The data passed with the event are:
       1) radioBranchId 
       2) IduOduCommunicationAlarm
       3) equipTrapAcknowledge code number"
  ::= 1733

radioBranchIduOduCommunicationAlarmCleared  TRAP-TYPE
  ENTERPRISE pdh
  DESCRIPTION "
    This event is generated by  PDH-NE when a radioBranchIduOduCommunicationAlarm is cleared
    The data passed with the event are:
       1) radioBranchId 
       2) IduOduCommunicationAlarm
       3) equipTrapAcknowledge code number"
  ::= 1734

radioBranchRxActiveStatusChange  TRAP-TYPE
  ENTERPRISE pdh
  DESCRIPTION "
    This event is generated by  PDH-NE when  a radioBranchRxActivestatus is changed
    The data passed with the event are:
       1) radioBranchId 
       2) RxActiveStatus
       3) equipTrapAcknowledge code number"
  ::= 1735

radioBranchTxActiveStatusChange  TRAP-TYPE
  ENTERPRISE pdh
  DESCRIPTION "
    This event is generated by  PDH-NE when  a radioBranchTxActivestatus is changed
    The data passed with the event are:
       1) radioBranchId 
       2) TxActiveStatus
       3) equipTrapAcknowledge code number"
  ::= 1737

radioBranchPrxChange  TRAP-TYPE
  ENTERPRISE  pdh
  DESCRIPTION
   "This event is generated by SDH-NE when RadioBranchPrx is changed, in modulus, more than 
    radioBranchPrxHysteresisValue from last TRAP
    The data passed with the event are:
       1) RadioBranchId
       2) radioBranchPrx
       3) equipTrapAcknowledge code number"
  ::= 1739



----------------------------------------------------------------------------------
--  4.12  PERFORMANCE MONITORING G.826 GROUP
----------------------------------------------------------------------------------
--  The following objects are used to manage the G.826 Performance Monitoring function.
----------------------------------------------------------------------------------
--  The following table contains the records with  the counters used to evaluate the Performance Monitoring  of the radio according to G.826 specification.
----------------------------------------------------------------------------------

pmG826CounterTable  OBJECT-TYPE
     SYNTAX      SEQUENCE OF  PmG826CounterRecord
     ACCESS      not-accessible
     STATUS      mandatory
     DESCRIPTION "
          Table with PmG826 records: one record for 1+0 configuration and two record for 1+1 configuration.
  "  ::=  { pmG826  1 }

pmG826CounterRecord  OBJECT-TYPE
     SYNTAX      PmG826CounterRecord
     ACCESS      not-accessible
     STATUS      mandatory
     DESCRIPTION "
          PmG826  record"
     INDEX { pmG826BranchId, pmG826CounterBlockId }
    ::=  { pmG826CounterTable 1 }

PmG826CounterRecord  ::=
   SEQUENCE {
        pmG826BranchId
           INTEGER,
        pmG826CounterBlockId
           INTEGER,
        pmG826CounterBlockType
           INTEGER,
        pmG826CounterBlockStatus
           INTEGER,
        pmG826CounterTimeStamp
           TimeTicks,
        pmG826BBECounter
           Counter,
        pmG826ESCounter
           Counter,
        pmG826SESCounter
           Counter,
        pmG826UASCounter
           Counter
     }

pmG826BranchId  OBJECT-TYPE
     SYNTAX    INTEGER
     ACCESS      read-only
     STATUS      mandatory
     DESCRIPTION "
           This object  identifies  the  Radio Branch
  "  ::=  { pmG826CounterRecord  1 }

 pmG826CounterBlockId  OBJECT-TYPE
     SYNTAX    INTEGER
     ACCESS      read-only
     STATUS      mandatory
     DESCRIPTION "
           This object  identifies  the counters block and the counter type according to the following code:
            1		Current Daily counters
            2		Daily counters (Day before counters)
            3		Current 15 minutes counters
            4		15 minutes counters N. 1 (The most recent 15 minutes counters)
            ..............................................
            n		15 minutes counters N. n
           20	15 minutes counters N. 16 (The oldest 15 minutes  counters - 4 hours before)
  "  ::=  { pmG826CounterRecord  2 }

pmG826CounterBlockType  OBJECT-TYPE
     SYNTAX    INTEGER {
                           daily       (1),
                           fifteen-min (2)
                        }
     ACCESS      read-only
     STATUS      mandatory
     DESCRIPTION "
         The type of the counter block
  "  ::=  { pmG826CounterRecord  3}

pmG826CounterBlockStatus OBJECT-TYPE
     SYNTAX    INTEGER {
                           meaningless   (1),
                           meaningfull   (2),
                           incomplete    (3),
                           dummy         (4),
                           lost          (5),
                           restarted     (6)
                        }

     ACCESS      read-only
     STATUS      mandatory
     DESCRIPTION "
         statusf the block counter
  "  ::=  { pmG826CounterRecord  4 }

pmG826CounterTimeStamp OBJECT-TYPE
    SYNTAX      TimeTicks
	  ACCESS      read-only
	  STATUS      mandatory
	  DESCRIPTION
         "The object is the time when the performance record is closed reported
          as the second number since 1/1/70."
    ::=  { pmG826CounterRecord  5 }
    
pmG826BBECounter  OBJECT-TYPE
     SYNTAX    Counter
     ACCESS      read-only
     STATUS      mandatory
     DESCRIPTION "
           G826  BBE  counter
  "  ::=  { pmG826CounterRecord  6 }

pmG826ESCounter  OBJECT-TYPE
     SYNTAX    Counter
     ACCESS      read-only
     STATUS      mandatory
     DESCRIPTION "
           G826  Es  counter
  "  ::=  { pmG826CounterRecord  7 }

pmG826SESCounter  OBJECT-TYPE
     SYNTAX    Counter
     ACCESS      read-only
     STATUS      mandatory
     DESCRIPTION "
           G826  SES  counter
  "  ::=  { pmG826CounterRecord  8 }

pmG826UASCounter  OBJECT-TYPE
     SYNTAX    Counter
     ACCESS      read-only
     STATUS      mandatory
     DESCRIPTION "
           G826  UAS  counter
  "  ::=  { pmG826CounterRecord  9 }


----------------------------------------------------------------------------------
--  The following table contains the records used to manage the P.M. on both radio branch and  the threshold cross alarms
----------------------------------------------------------------------------------

pmG826TpClassTable  OBJECT-TYPE
     SYNTAX    SEQUENCE OF  PmG826TpClassRecord
     ACCESS      not-accessible
     STATUS      mandatory
     DESCRIPTION "
          Table with PmG826TpClass records: one record for 1+0 configuration and two record for 1+1 configuration.
  "  ::=  { pmG826  2 }

pmG826TpClassRecord  OBJECT-TYPE
     SYNTAX     PmG826TpClassRecord
     ACCESS      not-accessible
     STATUS      mandatory
     DESCRIPTION "
          PmG826TpClass  record"
     INDEX { pmG826TpClassBranchId }
    ::=  { pmG826TpClassTable 1 }

PmG826TpClassRecord  ::=
   SEQUENCE {
        pmG826TpClassBranchId
           INTEGER,
        pmG826TpClassStartStop
           INTEGER,
        pmG826TpClassCounterClear
           INTEGER,
        pmG826TpClassAlarmClear
           INTEGER,
        pmG826TpClassCounterBuffer
           Opaque,
        pmG826TpClass15MEsAlarm
           INTEGER,
        pmG826TpClass15MSesEsAlarm
           INTEGER,
        pmG826TpClass24HEsAlarm
           INTEGER,
        pmG826TpClass24HSesEsAlarm
           INTEGER,
        pmG826TpClassUasAlarm
           INTEGER,
        pmG826TpClassTimeStamp
           TimeTicks
     }

pmG826TpClassBranchId  OBJECT-TYPE
     SYNTAX    INTEGER
     ACCESS      read-only
     STATUS      mandatory
     DESCRIPTION "
           This object  identifies  the  Radio Branch
  "  ::=  { pmG826TpClassRecord  1 }

pmG826TpClassStartStop  OBJECT-TYPE
     SYNTAX    INTEGER {
                           start   (1),
                           stop    (2)
                        }
     ACCESS      read-write
     STATUS      mandatory
     DESCRIPTION "
         This object is used to start and to stop the Perfomance Monitoring counter evaluation
  "  ::=  { pmG826TpClassRecord  2 }

pmG826TpClassCounterClear  OBJECT-TYPE
     SYNTAX    INTEGER {
                           clear   (1)
                        }
     ACCESS      write-only
     STATUS      mandatory
     DESCRIPTION "
         This object is used to clear  the Perfomance Monitoring counters.
  "  ::=  { pmG826TpClassRecord  3 }

pmG826TpClassAlarmClear  OBJECT-TYPE
     SYNTAX    INTEGER {
                           clear   (1)
                        }
     ACCESS      write-only
     STATUS      mandatory
     DESCRIPTION "
         This object is used to clear  the Perfomance Monitoring threshold cross alarms
  "  ::=  { pmG826TpClassRecord  4 }

pmG826TpClassCounterBuffer  OBJECT-TYPE
     SYNTAX      Opaque
     ACCESS      read-only
     STATUS      mandatory
     DESCRIPTION "
           This object  is used to transfer  in only one request all G.826 Counters (16x15Minutes and 1x1Day).
            It is used by a dedicated  P.M. application on the Manager.
  "  ::=  { pmG826TpClassRecord  5 }

pmG826TpClass15MEsAlarm  OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
         15 minutes  ES threshold cross alarm  with associated Severity.
  "  ::=  { pmG826TpClassRecord  6 }

pmG826TpClass15MSesEsAlarm  OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
         15 minutes  SES threshold cross alarm  with associated Severity.
  "  ::=  { pmG826TpClassRecord  7 }

pmG826TpClass24HEsAlarm  OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
         Daily  ES threshold cross alarm  with associated Severity.
  "  ::=  { pmG826TpClassRecord  8 }

pmG826TpClass24HSesEsAlarm  OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
         Daily  SES threshold cross alarm  with associated Severity.
  "  ::=  { pmG826TpClassRecord  9 }

pmG826TpClassUasAlarm  OBJECT-TYPE
     SYNTAX    INTEGER {
                           cleared                   (1),
                           activeReportable-Status   (2),
                           activeReportable-Warning  (3),
                           activeReportable-Minor    (4),
                           activeReportable-Major    (5),
                           activeReportable-Critical (6)
                       }
     ACCESS      read-only
     STATUS      mandatory
     DESCRIPTION "
         UAS  alarm  with associated Severity.
  "  ::=  { pmG826TpClassRecord  10 }

pmG826TpClassTimeStamp   OBJECT-TYPE
     SYNTAX      TimeTicks
     ACCESS      read-only
     STATUS      mandatory
     DESCRIPTION
      " "
    ::=  { pmG826TpClassRecord   11 }


----------------------------------------------------------------------------------
--  The following objects are common to both radio branch.
----------------------------------------------------------------------------------


pmG826NSesSetUAS  OBJECT-TYPE
     SYNTAX    INTEGER
     ACCESS      read-write
     STATUS      mandatory
     DESCRIPTION "
           Number of SES (according G.826) to set UAS
     "  DEFVAL{ 10 }
    ::=  { pmG826  3 }

pmG826NSesResetUAS  OBJECT-TYPE
     SYNTAX    INTEGER
     ACCESS      read-write
     STATUS      mandatory
     DESCRIPTION "
           Number of seconds whitout errors (according G.826) to reset UAS
     "  DEFVAL{ 10 }
    ::=  { pmG826  4 }

pmG826NBBESetSES  OBJECT-TYPE
     SYNTAX    INTEGER
     ACCESS      read-write
     STATUS      mandatory
     DESCRIPTION "
          Percentage of BBE in one second to declare SES
     "  DEFVAL{ 30 }
    ::=  { pmG826  5 }



pmG82615MEsThreshold  OBJECT-TYPE
     SYNTAX    INTEGER
     ACCESS      read-write
     STATUS      mandatory
     DESCRIPTION "
           Number of  ES within 15 minutes to set pmG826TpClass15MEsAlarm (zero value disables the alarm)
     "  DEFVAL{ 0 }
    ::=  { pmG826  6 }

pmG82615MSesThreshold  OBJECT-TYPE
     SYNTAX    INTEGER
     ACCESS      read-write
     STATUS      mandatory
     DESCRIPTION "
           Number of  SES within 15 minutes to set pmG826TpClass15MSesAlarm (zero value disables the alarm)
     "  DEFVAL{ 0 }
    ::=  { pmG826 7 }

pmG82624HEsThreshold  OBJECT-TYPE
     SYNTAX    INTEGER
     ACCESS      read-write
     STATUS      mandatory
     DESCRIPTION "
           Number of  ES within one day  to set pmG826TpClass24HEsAlarm (zero value disables the alarm)
     "  DEFVAL{ 0 }
    ::=  { pmG826  8 }

pmG82624HSesThreshold  OBJECT-TYPE
     SYNTAX    INTEGER
     ACCESS      read-write
     STATUS      mandatory
     DESCRIPTION "
           Number of  SES within 15 minutes to set pmG826TpClass24HSesAlarm (zero value disables the alarm)
     "  DEFVAL{ 0 }
    ::=  { pmG826  9 }



----------------------------------------------------------------------------------
--  The following objects define the profile of the threshold cross and UAS  alarms:
--
--  The general stucture of the object is the following:
--
--  pmG826<AlarmName>SeverityCode  OBJECT-TYPE
--     SYNTAX    INTEGER {
--                            disable                    (1),
--                            status-trapEnable          (2),
--                            status-trapEnableWithACK   (34),
--                            warning-trapEnable         (3),
--                            warning-trapEnableWithACK  (35),
--                            minor-trapEnable           (4),
--                            minor-trapEnableWithACK    (36),
--                            major-trapEnable           (5),
--                            major-trapEnableWithACK    (37),
--                            critical-trapEnable        (6),
--                            critical-trapEnableWithACK (38),
--                            status-trapDisable         (18),
--                            warning-trapDisable        (19),
--                            minor-trapDisable          (20),
--                            major-trapDisable          (21),
--                            critical-trapDisable       (22)
--                       }
--
--     ACCESS      read-write
--     STATUS      mandatory
--     DESCRIPTION "
--           Define the severity associated to the  <alarm name>  and  enable/disable the trap generation on status
--           change   event.
--     "  DEFVAL{ x }
--    ::=  { pmG826  y }
----------------------------------------------------------------------------------


pmG826TpClass15MEsAlarmSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the pmG826TpClass15MEsAlarm and  enable/disable the trap generation on status
           change   event.
     "  DEFVAL{ major-trapEnable }
    ::=  { pmG826  10 }

pmG826TpClass15MSesAlarmSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),    
                            warning-trapDisable        (19),
                            minor-trapDisable          (20),
                            major-trapDisable          (21),
                            critical-trapDisable       (22)
                       }
     ACCESS      read-write
     STATUS      mandatory
     DESCRIPTION "
           Define the severity associated to the pmG826TpClass15MSesAlarm and  enable/disable the trap generation on status
           change   event.
     "  DEFVAL{ major-trapEnable }
    ::=  { pmG826  11 }

pmG826TpClass24HEsAlarmSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the pmG826TpClass15MEsAlarm and  enable/disable the trap generation on status
           change   event.
     "  DEFVAL{ major-trapEnable }
    ::=  { pmG826  12 }

pmG826TpClass24HSesAlarmSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the pmG826TpClass15MSesAlarm and  enable/disable the trap generation on status
           change   event.
     "  DEFVAL{ major-trapEnable }
    ::=  { pmG826  13 }

pmG826TpClassUASAlarmSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the pmG826TpClassUASAlarm and  enable/disable the trap generation on status
           change   event.
     "  DEFVAL{ major-trapEnable }
    ::=  { pmG826  14 }

pmG826BlockFrame1x2Mbit  OBJECT-TYPE
     SYNTAX      INTEGER    (1..64)
     ACCESS      read-write
     STATUS      mandatory
     DESCRIPTION "
           Number of  frames per block when the capacity is 1x2Mbit/s"
    ::=  { pmG826  15 }

pmG826BlockFrame2x2Mbit  OBJECT-TYPE
     SYNTAX     INTEGER    (1..64)
     ACCESS     read-write
     STATUS     mandatory
     DESCRIPTION "
           Number of  frames per block when the capacity is 2x2Mbit/s"
    ::=  { pmG826  16 }

pmG826BlockFrame4x2Mbit  OBJECT-TYPE
     SYNTAX     INTEGER    (1..64)
     ACCESS     read-write
     STATUS     mandatory
     DESCRIPTION "
           Number of  frames per block when the capacity is 4x2Mbit/s or 1x8Mbit/s"
    ::=  { pmG826  17 }

pmG826BlockFrame8x2Mbit  OBJECT-TYPE
     SYNTAX     INTEGER    (1..64)
     ACCESS     read-write
     STATUS     mandatory
     DESCRIPTION "
           Number of  frames per block when the capacity is 8x2Mbit/s or 2x8Mbit/s"
    ::=  { pmG826  18 }


pmG826BlockFrame16x2Mbit  OBJECT-TYPE
     SYNTAX     INTEGER    (1..64)
     ACCESS     read-write
     STATUS     mandatory
     DESCRIPTION "
           Number of  frames per block when the capacity is 16x2Mbit/s or 1x34Mbit/s"
    ::=  { pmG826  19 }

----------------------------------------------------------------------------------
--The G.826 Performance group generates the following  trap
----------------------------------------------------------------------------------

pmG826TpClass15MEsAlarmSet  TRAP-TYPE
  ENTERPRISE pdh
  DESCRIPTION "
    This event is generated by  PDH-NE when  a pmG826TpClass15MEsAlarm is set
    The data passed with the event are:
       1) radioBranchId
       2) TpClass15MEsAlarm "
  ::= 1901

pmG826TpClass15MEsAlarmCleared  TRAP-TYPE
  ENTERPRISE pdh
  DESCRIPTION "
    This event is generated by  PDH-NE when a pmG826TpClass15MEsAlarm is cleared
    The data passed with the event are:
      1) radioBranchId 
      2) TpClass15MEsAlarm"
  ::= 1902

pmG826TpClass15MSesAlarmSet  TRAP-TYPE
  ENTERPRISE pdh
  DESCRIPTION "
    This event is generated by  PDH-NE when  a pmG826TpClass15MSesAlarm is set
    The data passed with the event are:
       1) radioBranchId 
       2) TpClass15MSesAlarm"
  ::= 1903

pmG826TpClass15MSesAlarmCleared  TRAP-TYPE
  ENTERPRISE pdh
  DESCRIPTION "
    This event is generated by  PDH-NE when a pmG826TpClass15MSesAlarm is cleared
    The data passed with the event are:
      1) radioBranchId 
      2) TpClass15MSesAlarm"
  ::= 1904

pmG826TpClass24HEsAlarmSet  TRAP-TYPE
  ENTERPRISE pdh
  DESCRIPTION "
    This event is generated by  PDH-NE when  a pmG826TpClass24HEsAlarm is set
    The data passed with the event are:
       1) radioBranchId
       2) TpClass24HEsAlarm "
  ::= 1905

pmG826TpClass24HEsAlarmCleared  TRAP-TYPE
  ENTERPRISE pdh
  DESCRIPTION "
    This event is generated by  PDH-NE when a pmG826TpClass24HEsAlarm is cleared
    The data passed with the event are:
      1) radioBranchId 
      2) TpClass24HEsAlarm"
  ::= 1906

pmG826TpClass24HSesAlarmSet  TRAP-TYPE
  ENTERPRISE pdh
  DESCRIPTION "
    This event is generated by  PDH-NE when  a pmG826TpClass24HSesAlarm is set
    The data passed with the event are:
       1) radioBranchId 
       2) TpClass24HSesAlarm"
  ::= 1907

pmG826TpClass24HSesAlarmCleared  TRAP-TYPE
  ENTERPRISE pdh
  DESCRIPTION "
    This event is generated by  PDH-NE when a pmG826TpClass24HSesAlarm is cleared
    The data passed with the event are:
      1) radioBranchId 
      2) TpClass24HSesAlarm"
  ::= 1908

pmG826TpClassUASAlarmSet  TRAP-TYPE
  ENTERPRISE pdh
  DESCRIPTION "
    This event is generated by  PDH-NE when  a pmG826TpClass24HEsAlarm is set
    The data passed with the event are:
       1) radioBranchId 
       2) TpClassUASAlarm"
  ::= 1909

pmG826TpClassUASAlarmCleared  TRAP-TYPE
  ENTERPRISE pdh
  DESCRIPTION "
    This event is generated by  PDH-NE when a pmG826TpClass24HEsAlarm is cleared
    The data passed with the event are:
      1) radioBranchId 
      2) TpClassUASAlarm"
  ::= 1910


----------------------------------------------------------------------------------
--  4.13 PERFORMANCE MONITORING RECEIVED  POWER LEVEL  GROUP
----------------------------------------------------------------------------------
--  The following objects are used to manage the Received Power  Performance Monitoring function.
----------------------------------------------------------------------------------
--  The following table contains the records with  the counters used to monitor  the received  power  of the radio.
----------------------------------------------------------------------------------

pmRxPwrCounterTable  OBJECT-TYPE
     SYNTAX      SEQUENCE OF  PmRxPwrCounterRecord
     ACCESS      not-accessible
     STATUS      mandatory
     DESCRIPTION "
          Table with PmRxPwr records: one record for 1+0 configuration and two record for 1+1 configuration.
  "  ::=  { pmRxPwr  1 }

pmRxPwrCounterRecord  OBJECT-TYPE
     SYNTAX      PmRxPwrCounterRecord
     ACCESS      not-accessible
     STATUS      mandatory
     DESCRIPTION "
          PmRxPwr  record"
     INDEX {  pmRxPwrBranchId, pmRxPwrCounterBlockId }
    ::=  { pmRxPwrCounterTable 1 }

PmRxPwrCounterRecord  ::=
   SEQUENCE {
        pmRxPwrBranchId
           INTEGER,
        pmRxPwrCounterBlockId
           INTEGER,
        pmRxPwrCounterBlockType
           INTEGER,
        pmRxPwrCounterBlockStatus
           INTEGER,
        pmRxPwrCounterTimeStamp
           TimeTicks,
        pmRxPwrRlts1Counter
           Counter,
        pmRxPwrRlts2Counter
           Counter,
        pmRxPwrRlts3Counter
           Counter,
        pmRxPwrRlts4Counter
           Counter,
        pmRxPwrTMMax
           INTEGER,
        pmRxPwrTMMin
           INTEGER
    }

pmRxPwrBranchId  OBJECT-TYPE
     SYNTAX    INTEGER
     ACCESS      read-only
     STATUS      mandatory
     DESCRIPTION "
           This object  identifies  the  Radio Branch
  "  ::=  { pmRxPwrCounterRecord  1 }

 pmRxPwrCounterBlockId  OBJECT-TYPE
     SYNTAX    INTEGER
     ACCESS      read-only
     STATUS      mandatory
     DESCRIPTION "
           This object  identifies  the counters block and the counter type according to the following code:
            1		Current Daily counters
            2		Daily counters (Day before counters)
            3		Current 15 minutes counters
            4		15 minutes counters N. 1 (The most recent 15 minutes counters)
            ..............................................
            n		15 minutes counters N. n
           20	15 minutes counters N. 16 (The oldest 15 minutes  counters - 4 hours before)
  "  ::=  { pmRxPwrCounterRecord  2 }

pmRxPwrCounterBlockType  OBJECT-TYPE
     SYNTAX    INTEGER {
                           daily       (1),
                           fifteen-min (2)
                        }
     ACCESS      read-only
     STATUS      mandatory
     DESCRIPTION "
         The type of the counter block
  "  ::=  { pmRxPwrCounterRecord  3}

pmRxPwrCounterBlockStatus OBJECT-TYPE
     SYNTAX    INTEGER {
                           meaningless   (1),
                           meaningfull   (2),
                           incomplete    (3),
                           dummy         (4),
                           lost          (5),
                           restarted     (6)
                        }

     ACCESS      read-only
     STATUS      mandatory
     DESCRIPTION "
         statusof the block counter
  "  ::=  { pmRxPwrCounterRecord  4 }
  
pmRxPwrCounterTimeStamp OBJECT-TYPE
    SYNTAX      TimeTicks
	  ACCESS      read-only
	  STATUS      mandatory
	  DESCRIPTION
         "The object is the time when the performance record is closed reported
          as the second number since 1/1/70."
    ::=  { pmRxPwrCounterRecord  5 }

pmRxPwrRlts1Counter  OBJECT-TYPE
     SYNTAX    Counter
     ACCESS      read-only
     STATUS      mandatory
     DESCRIPTION "
           Number of seconds when the Received  power is less than the  threshold  1
  "  ::=  { pmRxPwrCounterRecord  6 }

pmRxPwrRlts2Counter  OBJECT-TYPE
     SYNTAX    Counter
     ACCESS      read-only
     STATUS      mandatory
     DESCRIPTION "
           Number of seconds when the Received  power is less than the  threshold  2
  "  ::=  { pmRxPwrCounterRecord  7 }

pmRxPwrRlts3Counter  OBJECT-TYPE
     SYNTAX    Counter
     ACCESS      read-only
     STATUS      mandatory
     DESCRIPTION "
           Number of seconds when the Received  power is less than the  threshold  3
  "  ::=  { pmRxPwrCounterRecord  8 }

pmRxPwrRlts4Counter  OBJECT-TYPE
     SYNTAX    Counter
     ACCESS      read-only
     STATUS      mandatory
     DESCRIPTION "
           Number of seconds when the Received  power is less than the  threshold  4
  "  ::=  { pmRxPwrCounterRecord  9 }


pmRxPwrTMMax OBJECT-TYPE
     SYNTAX    INTEGER
     ACCESS      read-only
     STATUS      mandatory
     DESCRIPTION "
           Maximum Power Received Level  Tide Mark
  "  ::=  { pmRxPwrCounterRecord  10 }

pmRxPwrTMMin  OBJECT-TYPE
     SYNTAX    INTEGER
     ACCESS      read-only
     STATUS      mandatory
     DESCRIPTION "
           Minimum  Power Received Level  Tide Mark
  "  ::=  { pmRxPwrCounterRecord  11 }



----------------------------------------------------------------------------------
--   The following table contains the records used to manage the P.M. on both radio branch and  the threshold cross alarms
----------------------------------------------------------------------------------

pmRxPwrTpClassTable  OBJECT-TYPE
     SYNTAX      SEQUENCE OF  PmRxPwrTpClassRecord
     ACCESS      not-accessible
     STATUS      mandatory
     DESCRIPTION "
          Table with PmRxPwrTpClass records: one record for 1+0 configuration and two record for 1+1 configuration.
  "  ::=  { pmRxPwr  2 }

pmRxPwrTpClassRecord  OBJECT-TYPE
     SYNTAX      PmRxPwrTpClassRecord
     ACCESS      not-accessible
     STATUS      mandatory
     DESCRIPTION "
          PmRxPwrTpClass  record"
     INDEX {  pmRxPwrTpClassBranchId }
    ::=  { pmRxPwrTpClassTable 1 }

PmRxPwrTpClassRecord  ::=
   SEQUENCE {
        pmRxPwrTpClassBranchId
           INTEGER,
        pmRxPwrTpClassStartStop
           INTEGER,
        pmRxPwrTpClassCounterClear
           INTEGER,
        pmRxPwrTpClassAlarmClear
           INTEGER,
        pmRxPwrTpClassCounterBuffer
           Opaque,
        pmRxPwrTpClass15MRlts1Alarm
           INTEGER,
        pmRxPwrTpClass15MRlts2Alarm
           INTEGER,
        pmRxPwrTpClass15MRlts3Alarm
           INTEGER,
        pmRxPwrTpClass15MRlts4Alarm
           INTEGER,
        pmRxPwrTpClass24HRlts1Alarm
           INTEGER,
        pmRxPwrTpClass24HRlts2Alarm
           INTEGER,
        pmRxPwrTpClass24HRlts3Alarm
           INTEGER,
        pmRxPwrTpClass24HRlts4Alarm
           INTEGER
    }

pmRxPwrTpClassBranchId  OBJECT-TYPE
     SYNTAX    INTEGER
     ACCESS      read-only
     STATUS      mandatory
     DESCRIPTION "
           This object  identifies  the  Radio Branch
  "  ::=  { pmRxPwrTpClassRecord  1 }

pmRxPwrTpClassStartStop  OBJECT-TYPE
     SYNTAX    INTEGER {
                           start   (1),
                           stop    (2)
                        }
     ACCESS      read-write
     STATUS      mandatory
     DESCRIPTION "
         This object is used to start and to stop the Perfomance Monitoring counter evaluation
  "  ::=  { pmRxPwrTpClassRecord  2 }

pmRxPwrTpClassCounterClear  OBJECT-TYPE
     SYNTAX    INTEGER {
                           clear   (1)
                        }
     ACCESS      write-only
     STATUS      mandatory
     DESCRIPTION "
         This object is used to clear  the Perfomance Monitoring counters.
  "  ::=  { pmRxPwrTpClassRecord  3 }

pmRxPwrTpClassAlarmClear  OBJECT-TYPE
     SYNTAX    INTEGER {
                           clear   (1)
                        }
     ACCESS      write-only
     STATUS      mandatory
     DESCRIPTION "
         This object is used to clear  the Perfomance Monitoring threshold cross alarms
  "  ::=  { pmRxPwrTpClassRecord  4 }

pmRxPwrTpClassCounterBuffer  OBJECT-TYPE
     SYNTAX      Opaque
     ACCESS      read-only
     STATUS      mandatory
     DESCRIPTION "
           This object  is used to transfer  in only one request all Rx Power  Counters (16x15Minutes and 1x1Day).
            It is used by a dedicated  P.M. application on the Manager.
  "  ::=  { pmRxPwrTpClassRecord  5 }

pmRxPwrTpClass15MRlts1Alarm  OBJECT-TYPE
     SYNTAX    INTEGER {
                            cleared                   (1),
                            activeReportable-Status   (2),
                            activeReportable-Warning  (3),
                            activeReportable-Minor    (4),
                            activeReportable-Major    (5),
                            activeReportable-Critical (6)
                       }
     ACCESS      read-only
     STATUS      mandatory
     DESCRIPTION "
         15 minutes  Rlts1  threshold cross alarm  with associated Severity.
  "  ::=  { pmRxPwrTpClassRecord  6 }


pmRxPwrTpClass15MRlts2Alarm  OBJECT-TYPE
     SYNTAX    INTEGER {
                            cleared                   (1),
                            activeReportable-Status   (2),
                            activeReportable-Warning  (3),
                            activeReportable-Minor    (4),
                            activeReportable-Major    (5),
                            activeReportable-Critical (6)
                       }
     ACCESS      read-only
     STATUS      mandatory
     DESCRIPTION "
         15 minutes  Rlts2  threshold cross alarm  with associated Severity.
  "  ::=  { pmRxPwrTpClassRecord  7 }

pmRxPwrTpClass15MRlts3Alarm  OBJECT-TYPE
     SYNTAX    INTEGER {
                            cleared                   (1),
                            activeReportable-Status   (2),
                            activeReportable-Warning  (3),
                            activeReportable-Minor    (4),
                            activeReportable-Major    (5),
                            activeReportable-Critical (6)
                       }
     ACCESS      read-only
     STATUS      mandatory
     DESCRIPTION "
         15 minutes  Rlts3  threshold cross alarm  with associated Severity.
  "  ::=  { pmRxPwrTpClassRecord  8 }

pmRxPwrTpClass15MRlts4Alarm  OBJECT-TYPE
     SYNTAX    INTEGER {
                            cleared                   (1),
                            activeReportable-Status   (2),
                            activeReportable-Warning  (3),
                            activeReportable-Minor    (4),
                            activeReportable-Major    (5),
                            activeReportable-Critical (6)
                       }
     ACCESS      read-only
     STATUS      mandatory
     DESCRIPTION "
         15 minutes  Rlts4  threshold cross alarm  with associated Severity.
  "  ::=  { pmRxPwrTpClassRecord  9 }

pmRxPwrTpClass24HRlts1Alarm  OBJECT-TYPE
     SYNTAX    INTEGER {
                            cleared                   (1),
                            activeReportable-Status   (2),
                            activeReportable-Warning  (3),
                            activeReportable-Minor    (4),
                            activeReportable-Major    (5),
                            activeReportable-Critical (6)
                       }
     ACCESS      read-only
     STATUS      mandatory
     DESCRIPTION "
         Daily  Rlts1  threshold cross alarm  with associated Severity.
  "  ::=  { pmRxPwrTpClassRecord  10 }

pmRxPwrTpClass24HRlts2Alarm  OBJECT-TYPE
     SYNTAX    INTEGER {
                            cleared                   (1),
                            activeReportable-Status   (2),
                            activeReportable-Warning  (3),
                            activeReportable-Minor    (4),
                            activeReportable-Major    (5),
                            activeReportable-Critical (6)
                       }
     ACCESS      read-only
     STATUS      mandatory
     DESCRIPTION "
         Daily  Rlts2  threshold cross alarm  with associated Severity.
  "  ::=  { pmRxPwrTpClassRecord  11 }

pmRxPwrTpClass24HRlts3Alarm  OBJECT-TYPE
     SYNTAX    INTEGER {
                            cleared                   (1),
                            activeReportable-Status   (2),
                            activeReportable-Warning  (3),
                            activeReportable-Minor    (4),
                            activeReportable-Major    (5),
                            activeReportable-Critical (6)
                       }
     ACCESS      read-only
     STATUS      mandatory
     DESCRIPTION "
         Daily   Rlts3  threshold cross alarm  with associated Severity.
  "  ::=  { pmRxPwrTpClassRecord  12 }

pmRxPwrTpClass24HRlts4Alarm  OBJECT-TYPE
     SYNTAX    INTEGER {
                            cleared                   (1),
                            activeReportable-Status   (2),
                            activeReportable-Warning  (3),
                            activeReportable-Minor    (4),
                            activeReportable-Major    (5),
                            activeReportable-Critical (6)
                       }
     ACCESS      read-only
     STATUS      mandatory
     DESCRIPTION "
         Daily   Rlts4  threshold cross alarm  with associated Severity.
  "  ::=  { pmRxPwrTpClassRecord  13 }


----------------------------------------------------------------------------------
--  The following objects are common to both radio branches.
----------------------------------------------------------------------------------

pmRxPwr24HRlts1Threshold  OBJECT-TYPE
     SYNTAX    INTEGER
     ACCESS      read-write
     STATUS      mandatory
     DESCRIPTION "
           Number of  seconds  within a day  to set pmRxPwrTpClass24HRlts1Alarm (zero value disables the alarm)
     "  DEFVAL{ 0 }
    ::=  { pmRxPwr  3}

pmRxPwr24HRlts2Threshold  OBJECT-TYPE
     SYNTAX    INTEGER
     ACCESS      read-write
     STATUS      mandatory
     DESCRIPTION "
           Number of  seconds  within a day  to set pmRxPwrTpClass24HRlts2Alarm (zero value disables the alarm)
     "  DEFVAL{ 0 }
    ::=  { pmRxPwr  4}

pmRxPwr24HRlts3Threshold  OBJECT-TYPE
     SYNTAX    INTEGER
     ACCESS      read-write
     STATUS      mandatory
     DESCRIPTION "
           Number of  seconds  within a day  to set pmRxPwrTpClass24HRlts3Alarm (zero value disables the alarm)
     "  DEFVAL{ 0 }
    ::=  { pmRxPwr  5}

pmRxPwr24HRlts4Threshold  OBJECT-TYPE
     SYNTAX    INTEGER
     ACCESS      read-write
     STATUS      mandatory
     DESCRIPTION "
           Number of  seconds  within a day  to set pmRxPwrTpClass24HRlts4Alarm (zero value disables the alarm)
     "  DEFVAL{ 0 }
    ::=  { pmRxPwr  6}

pmRxPwr15MRlts1Threshold  OBJECT-TYPE
     SYNTAX    INTEGER
     ACCESS      read-write
     STATUS      mandatory
     DESCRIPTION "
           Number of  seconds  within 15 minutes  to set pmRxPwrTpClass15MRlts1Alarm (zero value disables the alarm)
     "  DEFVAL{ 0 }
    ::=  { pmRxPwr  7}

pmRxPwr15MRlts2Threshold  OBJECT-TYPE
     SYNTAX    INTEGER
     ACCESS      read-write
     STATUS      mandatory
     DESCRIPTION "
           Number of  seconds  within  15 minutes  to set pmRxPwrTpClass15MRlts2Alarm (zero value disables the alarm)
     "  DEFVAL{ 0 }
    ::=  { pmRxPwr  8}

pmRxPwr15MRlts3Threshold  OBJECT-TYPE
     SYNTAX    INTEGER
     ACCESS      read-write
     STATUS      mandatory
     DESCRIPTION "
           Number of  seconds  within  15 minutes to set pmRxPwrTpClass15MRlts3Alarm (zero value disables the alarm)
     "  DEFVAL{ 0}
    ::=  { pmRxPwr  9}

pmRxPwr15MRlts4Threshold  OBJECT-TYPE
     SYNTAX    INTEGER
     ACCESS      read-write
     STATUS      mandatory
     DESCRIPTION "
           Number of  seconds  within  15 minutes to set pmRxPwrTpClass15MRlts4Alarm (zero value disables the alarm)
     "  DEFVAL{ 0 }
    ::=  { pmRxPwr  10}

pmRxPwrRlt1Threshold  OBJECT-TYPE
     SYNTAX    INTEGER
     ACCESS      read-write
     STATUS      mandatory
     DESCRIPTION "
           Reveived Power Level Threshold 1 (dBm value)
     "  DEFVAL{ -30 }
    ::=  { pmRxPwr  11 }

pmRxPwrRlt2Threshold  OBJECT-TYPE
     SYNTAX    INTEGER
     ACCESS      read-write
     STATUS      mandatory
     DESCRIPTION "
           Reveived Power Level Threshold 2 (dBm value)
     "  DEFVAL{ -40 }
    ::=  { pmRxPwr  12 }

pmRxPwrRlt3Threshold  OBJECT-TYPE
     SYNTAX    INTEGER
     ACCESS      read-write
     STATUS      mandatory
     DESCRIPTION "
           Reveived Power Level Threshold 3 (dBm value)
     "  DEFVAL{ -50 }
    ::=  { pmRxPwr  13 }

pmRxPwrRlt4Threshold  OBJECT-TYPE
     SYNTAX    INTEGER
     ACCESS      read-write
     STATUS      mandatory
     DESCRIPTION "
           Reveived Power Level Threshold 4 (dBm value)
     "  DEFVAL{ -60 }
    ::=  { pmRxPwr  14 }


----------------------------------------------------------------------------------
--  The following objects define the profile of the threshold cross and UAS  alarms:
--
--  The general stucture of the object is the following:
--
--
--   pmRxPwr<AlarmName>SeverityCode  OBJECT-TYPE
--     SYNTAX    INTEGER {
--                            disable                    (1),
--                            status-trapEnable          (2),
--                            status-trapEnableWithACK   (34),
--                            warning-trapEnable         (3),
--                            warning-trapEnableWithACK  (35),
--                            minor-trapEnable           (4),
--                            minor-trapEnableWithACK    (36),
--                            major-trapEnable           (5),
--                            major-trapEnableWithACK    (37),
--                            critical-trapEnable        (6),
--                            critical-trapEnableWithACK (38),
--                            status-trapDisable         (18),
--                            warning-trapDisable        (19),
--                            minor-trapDisable          (20),
--                            major-trapDisable          (21),
--                            critical-trapDisable       (22)
--                       }
--     ACCESS      read-write
--     STATUS      mandatory
--     DESCRIPTION "
--           Define the severity associated to the  <alarm name>  and  enable/disable the trap generation on status
--           change   event.
--     "  DEFVAL{ x }
--    ::=  { pmRxPwr  y }
----------------------------------------------------------------------------------


pmRxPwrTpClass15MRltsAlarmSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),   
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the pmRxPwrTpClass15MRltsAlarm and  enable/disable the trap generation on status
           change   event.
     "  DEFVAL{ major-trapEnable }
    ::=  { pmRxPwr  15 }

pmRxPwrTpClass24RltsAlarmSeverityCode  OBJECT-TYPE
     SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
     ACCESS      read-write
     STATUS      mandatory
     DESCRIPTION "
           Define the severity associated to the pmRxPwrTpClass24RltsAlarm and  enable/disable the trap generation on status
           change   event.
     "  DEFVAL{ major-trapEnable }
    ::=  { pmRxPwr  16 }



----------------------------------------------------------------------------------
--  The Received Power  Performance group generates the following  trap
----------------------------------------------------------------------------------

pmRxPwrTpClass15MRlts1AlarmSet  TRAP-TYPE
  ENTERPRISE pdh
  DESCRIPTION "
    This event is generated by  PDH-NE when  a pmRxPwrTpClass15MRlts1Alarm is set
    The data passed with the event are:
       1) radioBranchId 
       2) RxPwrTpClass15MRlts1Alarm"
  ::= 1201

pmRxPwrTpClass15MRlts1AlarmCleared  TRAP-TYPE
  ENTERPRISE pdh
  DESCRIPTION "
    This event is generated by  PDH-NE when a pmRxPwrTpClass15MRlts1Alarm is cleared
    The data passed with the event are:
      1) radioBranchId 
      2) RxPwrTpClass15MRlts1Alarm"
  ::= 1202

pmRxPwrTpClass15MRlts2AlarmSet  TRAP-TYPE
  ENTERPRISE pdh
  DESCRIPTION "
    This event is generated by  PDH-NE when  a pmRxPwrTpClass15MRlts1Alarm is set
    The data passed with the event are:
       1) radioBranchId 
       2) RxPwrTpClass15MRlts2Alarm"
  ::= 1203

pmRxPwrTpClass15MRlts2AlarmCleared  TRAP-TYPE
  ENTERPRISE pdh
  DESCRIPTION "
    This event is generated by  PDH-NE when a pmRxPwrTpClass15MRlts1Alarm is cleared
    The data passed with the event are:
      1) radioBranchId 
      2) RxPwrTpClass15MRlts2Alarm"
  ::= 1204

pmRxPwrTpClass15MRlts3AlarmSet  TRAP-TYPE
  ENTERPRISE pdh
  DESCRIPTION "
    This event is generated by  PDH-NE when  a pmRxPwrTpClass15MRlts1Alarm is set
    The data passed with the event are:
       1) radioBranchId 
       2) RxPwrTpClass15MRlts3Alarm"
  ::= 1205

pmRxPwrTpClass15MRlts3AlarmCleared  TRAP-TYPE
  ENTERPRISE pdh
  DESCRIPTION "
    This event is generated by  PDH-NE when a pmRxPwrTpClass15MRlts1Alarm is cleared
    The data passed with the event are:
      1) radioBranchId 
      2) RxPwrTpClass15MRlts3Alarm"
  ::= 1206

pmRxPwrTpClass15MRlts4AlarmSet  TRAP-TYPE
  ENTERPRISE pdh
  DESCRIPTION "
    This event is generated by  PDH-NE when  a pmRxPwrTpClass15MRlts4Alarm is set
    The data passed with the event are:
       1) radioBranchId 
       2) RxPwrTpClass15MRlts4Alarm"
  ::= 1207

pmRxPwrTpClass15MRlts4AlarmCleared  TRAP-TYPE
  ENTERPRISE pdh
  DESCRIPTION "
    This event is generated by  PDH-NE when a pmRxPwrTpClass15MRlts4Alarm is cleared
    The data passed with the event are:
      1) radioBranchId 
      2) RxPwrTpClass15MRlts4Alarm"
  ::= 1208

pmRxPwrTpClass24HRlts1AlarmSet  TRAP-TYPE
  ENTERPRISE pdh
  DESCRIPTION "
    This event is generated by  PDH-NE when  a pmRxPwrTpClass24HRlts1Alarm is set
    The data passed with the event are:
       1) radioBranchId 
       2) RxPwrTpClass24HRlts1Alarm"
  ::= 1209

pmRxPwrTpClass24HRlts1AlarmCleared  TRAP-TYPE
  ENTERPRISE pdh
  DESCRIPTION "
    This event is generated by  PDH-NE when a pmRxPwrTpClass24HRlts1Alarm is cleared
    The data passed with the event are:
      1) radioBranchId 
      2) RxPwrTpClass24HRlts1Alarm"
  ::= 1210

pmRxPwrTpClass24HRlts2AlarmSet  TRAP-TYPE
  ENTERPRISE pdh
  DESCRIPTION "
    This event is generated by  PDH-NE when  a pmRxPwrTpClass24HRlts1Alarm is set
    The data passed with the event are:
       1) radioBranchId 
       2) RxPwrTpClass24HRlts2Alarm"
  ::= 1211

pmRxPwrTpClass24HRlts2AlarmCleared  TRAP-TYPE
  ENTERPRISE pdh
  DESCRIPTION "
    This event is generated by  PDH-NE when a pmRxPwrTpClass24HRlts1Alarm is cleared
    The data passed with the event are:
      1) radioBranchId 
      2) RxPwrTpClass24HRlts2Alarm"
  ::= 1212

pmRxPwrTpClass24HRlts3AlarmSet  TRAP-TYPE
  ENTERPRISE pdh
  DESCRIPTION "
    This event is generated by  PDH-NE when  a pmRxPwrTpClass24HRlts1Alarm is set
    The data passed with the event are:
       1) radioBranchId 
       2) RxPwrTpClass24HRlts3Alarm"
  ::= 1213

pmRxPwrTpClass24HRlts3AlarmCleared  TRAP-TYPE
  ENTERPRISE pdh
  DESCRIPTION "
    This event is generated by  PDH-NE when a pmRxPwrTpClass24HRlts1Alarm is cleared
    The data passed with the event are:
      1) radioBranchId 
      2) RxPwrTpClass24HRlts3Alarm"
  ::= 1214

pmRxPwrTpClass24HRlts4AlarmSet  TRAP-TYPE
  ENTERPRISE pdh
  DESCRIPTION "
    This event is generated by  PDH-NE when  a pmRxPwrTpClass24HRlts4Alarm is set
    The data passed with the event are:
       1) radioBranchId 
       2) RxPwrTpClass24HRlts4Alarm"
  ::= 1215

pmRxPwrTpClass24HRlts4AlarmCleared  TRAP-TYPE
  ENTERPRISE pdh
  DESCRIPTION "
    This event is generated by  PDH-NE when a pmRxPwrTpClass24HRlts4Alarm is cleared
    The data passed with the event are:
      1) radioBranchId 
      2) RxPwrTpClass24HRlts4Alarm"
  ::= 1216



--  4.17 portService  Group
--

--
-- This group  describes port used as service channel in PDH radio. 

    portServiceTable  OBJECT-TYPE
        SYNTAX      SEQUENCE OF  PortServiceRecord
        ACCESS      not-accessible
        STATUS      mandatory
        DESCRIPTION
            "Table with portService records describing 64Kbit/sec and 2Mbit ports within an unit."
        ::= { portService 1 }

    portServiceRecord  OBJECT-TYPE
        SYNTAX      PortServiceRecord
        ACCESS      not-accessible
        STATUS      mandatory
        DESCRIPTION
            "portService record"
        INDEX       { portServiceUnitId, portServiceId }
        ::= { portServiceTable 1 }

    PortServiceRecord  ::=
        SEQUENCE{
            portServiceUnitId
                INTEGER,
            portServiceId
                INTEGER,
            portServiceType
                INTEGER,
    	      portServiceLabel
                DisplayString,
            portServiceEnable
                INTEGER,
            portServiceLevInPortA
                INTEGER,
            portServiceLevOutPortA
                INTEGER,
            portServiceLevInPortB
                INTEGER,
            portServiceLevOutPortB
                INTEGER,
            portServiceLosAlarm
                INTEGER,
            portServiceInternalLosAlarm
                INTEGER,
            portService64KbitAisTx
                INTEGER,
            portServiceDialNumber
                DisplayString,
            portServiceEmergencyCall
                INTEGER
        }

    portServiceUnitId  OBJECT-TYPE
        SYNTAX      INTEGER 
        ACCESS      read-only
        STATUS      mandatory
        DESCRIPTION
            "This object identifies unit where the Service port is present."
        ::= { portServiceRecord 1 }

    portServiceId  OBJECT-TYPE
        SYNTAX      INTEGER 
        ACCESS      read-only
        STATUS      mandatory
        DESCRIPTION
            "This object identifies the service port within the Unit."
        ::= { portServiceRecord 2 }

    portServiceType  OBJECT-TYPE
        SYNTAX      INTEGER{
                            service-voice             (1),
                            service-g703-Cod          (2),
                            service-g703-Contra       (3),
                            service-v11-async-1x9600  (4),
                            service-v11-async-2x4800  (5),
                            service-v28-async-1x9600  (6),
                            service-v28-async-2x4800  (7),
                            service-v11-sync-1x9600   (8),
                            service-v28-sync-1x9600   (9),
                            service-eow               (10),
                            undefined                 (11)
                           }
        ACCESS      read-write
        STATUS      mandatory
        DESCRIPTION
            "Define the type of the service  port."
        ::= { portServiceRecord 3 }

    portServiceLabel  OBJECT-TYPE
        SYNTAX      DisplayString   (SIZE(0..31))
        ACCESS      read-write
        STATUS      mandatory
        DESCRIPTION
            "ASCII string used by the operator to identify  the port service"
        ::= {portServiceRecord 4}

    portServiceEnable OBJECT-TYPE
        SYNTAX      INTEGER{
                             disable (1),
                             enable  (2)
                           }
        ACCESS      read-write
        STATUS      mandatory
        DESCRIPTION
            "Enable/disable the service port on the Unit (meaningfull when
             the port has alarms) "
        DEFVAL      { disable }
        ::= { portServiceRecord 5 }

    portServiceLevInPortA  OBJECT-TYPE
        SYNTAX      INTEGER
        ACCESS      read-write
        STATUS      mandatory
        DESCRIPTION
            "Attenuation value inserted at Port A input.
             Meaningfull only with service-voice and service-eow type"
    ::= { portServiceRecord 6 }

    portServiceLevOutPortA OBJECT-TYPE
        SYNTAX      INTEGER
        ACCESS      read-write
        STATUS      mandatory
        DESCRIPTION
            "Attenuation value inserted at Port A output 
             Meaningfull only with service-voice and service-eow type"
        ::= { portServiceRecord 7 }

    portServiceLevInPortB  OBJECT-TYPE
        SYNTAX      INTEGER
        ACCESS      read-write
        STATUS      mandatory
        DESCRIPTION
            "Attenuation value inserted at Port B input
             Meaningfull only with service-voice and service-eow type"
        ::= { portServiceRecord 8 }

    portServiceLevOutPortB  OBJECT-TYPE
        SYNTAX      INTEGER
        ACCESS      read-write
        STATUS      mandatory
        DESCRIPTION
            "Attenuation value inserted at Port B output
             Meaningfull only with service-voice and service-eow type"
        ::= { portServiceRecord 9 }

    portServiceLosAlarm  OBJECT-TYPE
        SYNTAX      INTEGER{
                            cleared (1),
                            activeReportable-Status (2),
                            activeReportable-Warning (3),
                            activeReportable-Minor (4),
                            activeReportable-Major (5),
                            activeReportable-Critical (6)
                           }
        ACCESS      read-only
        STATUS      mandatory
        DESCRIPTION
            "Service port lost of signal alarm (Probable cause = LossOf Signal) status with
             associated Severity. Meaningfull only with service-g703-Cod and service-g703-Contra type"
        ::= { portServiceRecord 10 }

    portServiceInternalLosAlarm  OBJECT-TYPE
        SYNTAX      INTEGER{
                            cleared (1),
                            activeReportable-Status (2),
                            activeReportable-Warning (3),
                            activeReportable-Minor (4),
                            activeReportable-Major (5),
                            activeReportable-Critical (6)
                           }
        ACCESS      read-only
        STATUS      mandatory
        DESCRIPTION
            "Service port lost of internal signal alarm (Probable cause = LossOf Signal) status with
             associated Severity. Meaningfull only with service-g703-Cod and service-g703-Contra type"
        ::= { portServiceRecord 11 }

    portService64KbitAisTx OBJECT-TYPE
        SYNTAX      INTEGER{
                            disable  (1),
                            enable   (2)
                           }
        ACCESS      read-write
        STATUS      mandatory
        DESCRIPTION
            "Enable/disable the AIS insetion at transmitted side for lack of the received signal.
             Meaningfull only with service-g703-Cod and service-g703-Contra type"
   ::= { portServiceRecord 12 }


    portServiceDialNumber OBJECT-TYPE
        SYNTAX      DisplayString   (SIZE(0..2))
        ACCESS      read-write
        STATUS      mandatory
        DESCRIPTION
            "Identification number of the radio terminal (1 to 99).
             Meaningfull only with service-voice type"
        ::= { portServiceRecord 13 }

    portServiceEmergencyCall OBJECT-TYPE
        SYNTAX      INTEGER{
                            enable (2)
                           }
        ACCESS      write-only
        STATUS      mandatory
        DESCRIPTION
            "This object allows to stop the selective call.
             Meaningfull only with service-voice type"
    ::= { portServiceRecord 14 }



--
-- The following objects define the profile of the portService  alarms:
--

    portServiceLosAlarmSeverityCode  OBJECT-TYPE
        SYNTAX      INTEGER{
                            disable (1),
                            status-trapEnable (2),
                            status-trapEnableWithACK (34),
                            warning-trapEnable (3),
                            warning-trapEnableWithACK (35),
                            minor-trapEnable (4),
                            minor-trapEnableWithACK (36),
                            major-trapEnable (5),
                            major-trapEnableWithACK (37),
                            critical-trapEnable (6),
                            critical-trapEnableWithACK (38),
                            status-trapDisable (18),
                            warning-trapDisable (19),
                            minor-trapDisable (20),
                            major-trapDisable (21),
                            critical-trapDisable (22)
                           }
        ACCESS      read-write
        STATUS      mandatory
        DESCRIPTION
            "Define the severity associated to the portServiceLosAlarm and enable/disable
             the trap generation on status change event."
        DEFVAL      { major-trapEnable }
        ::= { portService 2 }

    portServiceInternalLosAlarmSeverityCode  OBJECT-TYPE
        SYNTAX      INTEGER{
                            disable (1),
                            status-trapEnable (2),
                            status-trapEnableWithACK (34),
                            warning-trapEnable (3),
                            warning-trapEnableWithACK (35),
                            minor-trapEnable (4),
                            minor-trapEnableWithACK (36),
                            major-trapEnable (5),
                            major-trapEnableWithACK (37),
                            critical-trapEnable (6),
                            critical-trapEnableWithACK (38),
                            status-trapDisable (18),
                            warning-trapDisable (19),
                            minor-trapDisable (20),
                            major-trapDisable (21),
                            critical-trapDisable (22)
                           }
        ACCESS      read-write
        STATUS      mandatory
        DESCRIPTION
            "Define the severity associated to the portServiceInternalLosAlarm and enable/disable
             the trap generation on status change event."
        DEFVAL      { major-trapEnable }
        ::= { portService 3 }


--
-- The portService  Group generates the following TRAPs:
--

    portServiceLosAlarmSet  TRAP-TYPE
        ENTERPRISE pdh
        DESCRIPTION
            "This event is generated by  PDH-NE when  a portServiceLosAlarm  is set
             The data passed with the event are:
             1) portServiceId
             2) UnitId
             3) portServiceLabel
             4) portServiceLosAlarm
             5) equipTrapAcknowledge code number"
        ::= 1601

    portServiceLosAlarmCleared  TRAP-TYPE
        ENTERPRISE pdh
        DESCRIPTION
            "This event is generated by  PDH-NE when a portServiceLosAlarm is cleared
             The data passed with the event are:
             1) portServiceId
             2) UnitId
             3) portServiceLabel
             4) portServiceLosAlarm
             5) equipTrapAcknowledge code number"
        ::= 1602

    portServiceInternalLosAlarmSet  TRAP-TYPE
        ENTERPRISE pdh
        DESCRIPTION
            "This event is generated by  PDH-NE when  a portServiceInternalLosAlarm  is set
             The data passed with the event are:
             1) portServiceId
             2) UnitId
             3) portServiceLabel
             4) portServiceInternalLosAlarm
             5) equipTrapAcknowledge code number"
        ::= 1603

    portServiceInternalLosAlarmCleared  TRAP-TYPE
        ENTERPRISE pdh
        DESCRIPTION
            "This event is generated by  PDH-NE when a portServiceLosAlarm is cleared
             The data passed with the event are:
             1) portServiceId
             2) UnitId
             3) portServiceLabel
             4) portServiceInternalLosAlarm
             5) equipTrapAcknowledge code number"
        ::= 1604



END
