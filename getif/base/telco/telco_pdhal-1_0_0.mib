---------------------------------------------------------------
--
--              SM - PDH-AL - Network Element
--
--                        MIB
--
--              Management Information Base
--
---------------------------------------------------------------
-- CHANGE HISTORY
---------------------------------------------------------------
-- Revisione Interna: 01.00.00-a 
-- 11/12/2000
--    Primo rilascio per sviluppo
--
-- Revisione Interna: 01.00.00-b
-- 14/3/2001
--    added:    userInputRemoteTerminal; it is a flag selecting if the user input  
--              is local or remote
--    modified: the description of userOutputInternalStatus
--    modified: the description of radioEquipmentCapacity
--    added:    radioEquipmentLocalCapacity 
--    added:    radioBranchLocalOduAlarmSynthesis, radioBranchRemoteOduAlarmSynthesis
--    added:    radioBranchLocalOduAlarmSynthesisSeverityCode
--    added:    raioioBranchRemoteOduAlarmSynthesisSeverityCode
--    added:    radioBranchLocalRimAlarmSynthesis, radioBranchRemoteRimAlarmSynthesis
--    added:    radioBranchLocalRimAlarmSynthesisSeverityCode
--    added:    radioBranchRemoteRimAlarmSynthesisSeverityCode
--    added:    radioEquipmentLocalBBAlarm
--    added:    radioEquipmentLocalBBAlarmSynthesisSeverityCode
--    added:    radioEquipmentRemoteBBAlarm
--    added:    radioEquipmentRemoteBBAlarmSynthesisSeverityCode
--    modified: equipType (added radioPDH-AL Lc(30), 1+1(31), 1+1FD(32)      
--    modified: unitExpectedType (added Switch&Splitter , ServiceChannel)      
--    added:    radioEquipmentModulationType 
--    replaced: radioEquipmentAisTxInsertion with  radioEquipmentServiceSquelchEnable  
--    replaced: radioEquipmentHdb3CodeAlarmEnable with radioEquipmentCrcPulseRxSw  
--    modified: radioEquipment Rx(Tx)ManualSwitch to radioEquipmentRx(Tx)RevertiveSwitch 
--    modified: radioEquipmentStandbyBaseBandAlarm to radioEquipmentMainBaseBandAlarm and 
--              the related Severity code
--    added:    radioEquipmentReserveBaseBandAlarm with related Severity and trap
--    modified: radioEquipmentRxTribFailAlarm to radioEquipmentDemultiplexerFailAlarm
--              with related Severity and trap
--    added:    radioEquipment MultiplexerFailAlarm with related Severity and trap
--    added:    ppiRxAisAlarm with related Severity and trap
--    modified: radioBranchDemMantBer  to radioBranchBaseBandMantBer 
--    modified: radioBranchDemExpBer to radioBranchBaseBandExpBer
--    modified: radioBranchDemErr to radioBranchBaseBandErr
--    modified: radioBranchDemEwlAlarm  to radioBranchBaseBandEwlAlarm 
--    modified: radioBranchDemLberAlarm  to radioBranchBaseBandLberAlarm 
--    modified: radioBranchDemHberAlarm  to radioBranchBaseBandHberAlarm 
--    deleted:  radioBranchOduBncAccess
--    added:    radioBranchLoop  enumeration value iduLoop(6)
--    added:    to  radioBranchRtPsuOff
--
-- Revisione Interna: 01.00.00-c
-- 10/5/2001
--    Deleted:  radioBranchAtpcFail
--    Added:    radioBranchRtVcoFailAlarm with related Severity and trap
--    Added:    radioBranchIfVcoFailAlarm with related Severity and trap
--
-- Revisione Interna: 01.00.00-d
-- 10/9/2001
--    Added:    radioBranchRtOduIduCommAlarm and related Severity and trap
--    Added:    radioBranchAtpcBerHigh, radioBranchAtpcBerLow
--    Deleted:  radioEquipmentMainBaseBandAlarm, radioEquipmentReserveBaseBandAlarm 
--              with related severity and trap
--    Deleted:  radioBranchBaseBandTxAlarm and related severity object
--              RxAis alarm deleted in ppi group and added in radioEquipment group 
--              (alarm,severity,trap)
--    Added:    portServiceLineLoop and portServiceInternalLoop 
--    Added:    the enumeration value rFloopOn_RemTxOn (5) to radioBranchLoop object
--    Added:    equipOffLineRouteTable, equipIpPppTable
--    Added:    the values storedRouteRetrieve (7), storedRouteSave  (8)
--    Modified: radioEquipmentLocalBBAlarmSynthesis in
--              radioEquipmentLocalLimMainAlarmSynthesis (Alarm and trap)
--    Modified: radioEquipmentRemoteBBAlarmSynthesis in 
--              radioEquipmentRemoteLimMainAlarmSynthesis 
--    Added:    radioEquipmentLocalLimReserveAlarmSynthesis  (Alarm and trap)
--    Added:    radioEquipmentRemoteLimReserveAlarmSynthesis  (Alarm and trap)
--    Added:    radioEquipmentRemoteEquipmentControllerAlarm  (Alarm, Severity and trap)
--    Added:    radioEquipmentRemoteSplitterAlarm  (Alarm, Severity and trap)
--
-- Revisione Interna: 01.00.00-e
-- 11/03/2002
--    Modified: pmG826TpClass15MSesEsAlarm in pmG826TpClass15MSesAlarm
--    Modified: pmG826TpClass24HSesEsAlarm in pmG826TpClass24HSesAlarm
--    Modified: pmG826TpClass24HSesEsAlarm in pmG826TpClass24HSesAlarm
--    Modified: pmRxPwrTpClass24RltsAlarmSeverityCode in pmRxPwrTpClass24HRltsAlarmSeverityCode
--    Add:      pmRxPwrTpClassTimeStamp   
--    
-- Revisione Interna: 01.00.00-f
-- 26/06/2002
--    Modified: radioEquipmentRemoteAccessType (added dueMbit-pcm-TS0(3))
--    Added:    radioEquipment16KbitPppMap to select 16Kbit channel used by PPP
--    Modified: accessControlLoginTimeout (added range)
--    Modified: alarmLogStartHourEnable (added range)
--    Modified: alarmLogEndHourEnable (added range)
--    
-- Revisione Interna: 01.00.00-g
-- 09/07/2002
--    Modified: equipIpPppInterfaceId enumeration (added pppRemoteSpv)
--    Modified: equipPPPMode DEFVAL clause
--    Modified: equipPPPradioMode DEFVAL clause
--    Modified: unitExpectedType ACCESS clause
--    Modified: radioEquipmentCapacity enumeration (del pdh-8Mbit, pdh-2x8Mbit)
--    Modified: radioEquipmentLocalCapacity enumeration (del pdh-8Mbit, pdh-2x8Mbit)
--    Modified: radioEquipmentLinkId SYNTAX clause (added range)
--    Modified: radioEquipmentLocalLinkId SYNTAX clause (added range)
--    Modified: radioEquipmentGndRef added DEFVAL clause
--    Modified: radioEquipmentAisRxInsertion added DEFVAL clause
--    Modified: radioEquipmentServiceSquelchEnable added DEFVAL clause
--    Modified: radioEquipmentTxPwrThresh added DEFVAL clause and range in SYNTAX clause
--    Modified: radioEquipmentRxPwrThresh added DEFVAL clause and range in SYNTAX clause
--    Modified: radioEquipmentLberThresh added DEFVAL clause
--    Modified: radioEquipmentHberThresh added DEFVAL clause
--    Modified: radioEquipmentHberAisInsRxSw added DEFVAL clause
--    Modified: radioEquipmentLberRxSw added DEFVAL clause
--    Modified: radioEquipmentCrcPulseRxSw added DEFVAL clause
--    Modified: radioEquipmentPeripheralLom enumeration (added enableBB-Reserve,
--              enableService-A, enableService-B)
--    Modified: radioEquipmentLberRxSw DEFVAL clause and DESCRIPTION clause
--    Modified: radioEquipment16KbitPppMap DEFVAL clause, DESCRIPTION clause and added
--              range in SYNTAX clause
--    Added:    radioEquipment2MbPppMap
--    Added:    radioEquipmentPppRadioLinkAlarm, with related severity code and trap
--    Modified: radioEquipmentCapacity enumeration (del pdh-8Mbit)
--    Modified: radioBranchRtPsuOff ACCESS clause
--    Modified: radioBranchPrxHysteresisValue DEFVAL clause, DESCRIPTION clause
--    Modified: radioBranchPtxHysteresisValue DEFVAL clause
--    Modified: pmG826BlockFrame8x2Mbit DESCRIPTION clause
--    Modified: pmG826BlockFrame4x2Mbit DESCRIPTION clause
--    Modified: radioEquipment trap code (align with group number)
--    Modified: ppi trap code (align with group number)
--    Modified: radioBranch trap code (align with group number)
--    Modified: pmG826 trap code (align with group number)
--    
-- Revisione Interna: 01.00.00-h
-- 23/07/2002
--    Modified: radioEquipmentPeripheralLom enumeration
--
-- Revisione Interna: 01.00.00-i
-- 29/08/2002
--    Modified: radioBranchPtx ACCESS clause (in read-only)
--
-- Revisione Interna: 01.00.00-l
-- 13/09/2002
--    Added:    pmG826SEPCounter, pmG82615MSepThreshold, pmG82624HSepThreshold
--    Added:    pmG826TpClass15MSepAlarm, pmG826TpClass24HSepAlarm with related 
--              severity code and trap
--
-- Revisione Interna: 01.00.00-m
-- 03/10/2002
--    Added:    PRBS (Pseudo Random Bit Sequence) management.
--              radioEquipmentPrbsStart, radioEquipmentPrbsCheckedSignal
--              radioEquipmentPrbs2MbSelection, radioEquipmentPrbsTestPattern,
--              radioEquipmentPrbsErrorCounter
--              radioEquipmentPrbsFailAlarm with related severity code and trap
--    
-- Revisione Interna: 01.00.00-n
-- 14/10/2002
--    Added:    pmG826TpClassLabel
--    Modified: all pmG826 group, trap's varbind list
--    Modified: all pmRxPwr group, trap's varbind list (equipTrapAcknowledge code number)
--    
-- Revisione Interna: 01.00.00-o
-- 15/11/2002
--    modified: unitExpectedType, unitActualType (added backpanel)      
--    
-- Revisione Interna: 01.00.00-p
-- 16/12/2002
--    modified: portServiceType enumeration      
--    
---------------------------------------------------------------

-- Revisione Interna: 01.00.00-q
-- 10/02/2003
--    added: commandLog group      
--    
-- Revisione Interna: 01.00.00-r
-- 06/03/2003
--    Modified: the voice baseband with lim in leaf unitExpectedType in unit Group     
--    Modified: the voice baseband with lim in leaf unitActualType in unit Group
--    Modified: enumeration in leaf unitActualType in unit Group (lim and split)
--    Modified: enumeration in leaf RadioEquipmentCapacity in RadioEquipment Group (32x2)
--    Modified: enumeration in leaf RadioEquipmentLocalCapacity in RadioEquipment Group (32x2)
--    Added: leaf radioEquipment2MbG826 in RadioEquipment Group

-- Revisione Interna: 01.00.00-s
-- 03/04/2003
--    Modified: enumeration in leaf radioEquipmentRemoteAccessType in radioEquipment Group (deledet dueMbit-pcm-TS0
--    Modified: type in leaf radioEquipmentPppMap in radioEquipment Group (to integer from OCTET STRING)

-- Revisione Interna: 01.00.00-t
-- 15/04/2003
--    Modified: the comment in the leaf radioBranchRtsSetupTable in radioBranch Group
--    Modified: the size of leaf unitHwEdition in unit Group
---------------------------------------------------------------


              PDHAL-SIAE-MIB

               --FORCE-INCLUDE <envoy/h/asn1.h>
               --FORCE-INCLUDE <envoy/h/mib.h>
               --FORCE-INCLUDE <envoy/h/snmp.h>
               --FORCE-INCLUDE "../int/pdhal-profile.h"
               --FORCE-INCLUDE "../int/pdhal-mib.h"

               -- exclude all rfc1213 group not implemented
               --EXCLUDE at
               --EXCLUDE icmp
               --EXCLUDE egp


               DEFINITIONS ::= BEGIN

               IMPORTS
                       private, 
                       OBJECT-TYPE, 
                       Counter, 
                       IpAddress,
                       Opaque, 
                       TimeTicks
                           FROM RFC1155-SMI

                       TRAP-TYPE
                           FROM RFC-1215
                                                     
                       DisplayString
                           FROM RFC1213-MIB;


                enterprises         OBJECT IDENTIFIER ::= { private 1 }
                siae                OBJECT IDENTIFIER ::= { enterprises 3373 }

                pdh-al              OBJECT IDENTIFIER ::= { siae 7}
                equipment           OBJECT IDENTIFIER ::= { pdh-al  1 }
                userInput           OBJECT IDENTIFIER ::= { pdh-al  2 }
                userOutput          OBJECT IDENTIFIER ::= { pdh-al  3 }
                alarmLog            OBJECT IDENTIFIER ::= { pdh-al  4 }
                accessControl       OBJECT IDENTIFIER ::= { pdh-al  5 }
                unit                OBJECT IDENTIFIER ::= { pdh-al  6 }
                software            OBJECT IDENTIFIER ::= { pdh-al  7 }
                radioEquipment      OBJECT IDENTIFIER ::= { pdh-al  8 }
                ppi                 OBJECT IDENTIFIER ::= { pdh-al  9 }
                radioBranch         OBJECT IDENTIFIER ::= { pdh-al 10 }
                pmG826              OBJECT IDENTIFIER ::= { pdh-al 11 }
                pmRxPwr             OBJECT IDENTIFIER ::= { pdh-al 12 }
                pmTxPwr             OBJECT IDENTIFIER ::= { pdh-al 13 }
                portService         OBJECT IDENTIFIER ::= { pdh-al 14 }
                commandLog          OBJECT IDENTIFIER ::= { pdh-al 40 }



----------------------------------------------------------------------------------
--  4.2 THE  EQUIPMENT GROUP
----------------------------------------------------------------------------------
--  The following listed objects are general object common to all  SIAE  equipment .
----------------------------------------------------------------------------------

    equipCurrentTime   OBJECT-TYPE
        SYNTAX      TimeTicks
        ACCESS      read-write
     	  STATUS      mandatory
        DESCRIPTION
              "Seconds since 1/1/1970"
        ::= {equipment 1}

    equipUpTime   OBJECT-TYPE
       	SYNTAX      TimeTicks
       	ACCESS      read-only
     	  STATUS      mandatory
       	DESCRIPTION
              "The time when the system was last re-initialized (in seconds) 
               since 1/1/1970"
        ::= {equipment 2}

    equipType   OBJECT-TYPE
        SYNTAX      INTEGER {
                             radioSDH             (1),
                             pmp                  (2),
    	                       famSDH               (3),
                             commServer           (4),
                             microMux             (5),
                             admc                 (6),
                             radioPDH-SPU5-LC     (7),
                             radioPDH-SPU5-LC-A   (8),
                             radioPDH-SPU5-LC-B   (9),
                             radioPDH-SPU5-MC     (10),
                             radioPDH-SPU5-HC     (11),
                             radioPDH-SPU4-LC     (12),
                             radioPDH-SPU4-MC     (13),
                             radioPDH-SPU4-HC     (14),
                             radioPDH-SPU6-LC     (15),
                             radioPDH-SPU6-MC     (16),
                             radioPDH-SPU6-HC     (17),
                             sdhc-1-0             (18),
                             radioPDH-AL-LC       (30),
                             radioPDH-AL-1P1      (31),
                             radioPDH-AL-1P1FD    (32)
                            }
        ACCESS      read-only
        STATUS      mandatory
        DESCRIPTION
           "Type of SIAE PDH Radio Equipment:
           radioPDH-SPUx LC Low Capacity    (up to 4x2Mbit)
           radioPDH-SPUx MC Medium Capacity (8x2Mbit and 16x2Mbit)
           radioPDH-SPUx HC High Capacity   (2x8Mbit and 34Mbit)
           radioPDH-AL   LC Low Capacity    (2Mbit up to 4x2Mbit)
           radioPDH-AL   MC Medium Capacity (2x2Mbit up to 16x2Mbit)
           radioPDH-AL   HC High Capacity   (34Mbit)"
        ::= {equipment 3}

    equipIpEthOsiAddress   OBJECT-TYPE
        SYNTAX      IpAddress
        ACCESS      read-write
        STATUS      mandatory
        DESCRIPTION
            "Ip address of the equipment on Ethernet-OSI interface"
        ::=  {equipment 4}

    equipGosipAddress  OBJECT-TYPE
        SYNTAX      OCTET STRING    (SIZE(0..20))
        ACCESS      read-write
        STATUS      mandatory
        DESCRIPTION
            "GOSIP  address of the equipment"
        ::=  {equipment 5}

    equipRemoteElementTable  OBJECT-TYPE
        SYNTAX SEQUENCE OF EquipRemoteElementEntry
        ACCESS      not-accessible
        STATUS      mandatory
        DESCRIPTION
            "Table with ISO/OSI remote element that are reacheable from this NE"
        ::= {equipment 6}

    equipRemoteElementEntry  OBJECT-TYPE
        SYNTAX    EquipRemoteElementEntry
        ACCESS    not-accessible
        STATUS    mandatory
        DESCRIPTION
            "Remote element record"
        INDEX     {equipRemoteElementIpAddress}
        ::= {equipRemoteElementTable 1}

    EquipRemoteElementEntry  ::=
        SEQUENCE {
            equipRemoteElementIpAddress         IpAddress,
            equipRemoteElementGosipAddress      OCTET STRING,
            equipRemoteElementLabel             DisplayString,
            equipRemoteElementType              INTEGER
        }

    equipRemoteElementIpAddress  OBJECT-TYPE
        SYNTAX      IpAddress
        ACCESS      read-write
        STATUS      mandatory
        DESCRIPTION
            "IP address of remote element"
        ::=  {equipRemoteElementEntry 1}

    equipRemoteElementGosipAddress  OBJECT-TYPE
        SYNTAX      OCTET STRING    (SIZE(0..20))
        ACCESS      read-write
        STATUS      mandatory
        DESCRIPTION
            "Gosip address of remote element"
        ::=  {equipRemoteElementEntry 2}

    equipRemoteElementLabel  OBJECT-TYPE
        SYNTAX      DisplayString   (SIZE(0..15))
        ACCESS      read-write
        STATUS      mandatory
        DESCRIPTION
            "ASII string used for label the remote element"
        ::=  {equipRemoteElementEntry 3}

    equipRemoteElementType   OBJECT-TYPE
        SYNTAX      INTEGER {
                             elemManager (1),
    	                       external    (2),
                             remote      (3),
                             snm         (4)
                            }
        ACCESS      read-write
        STATUS      mandatory
        DESCRIPTION
            "Type of Remote Network Element:
              * Element Manager (1)
              * External: the NE is used as a gateway to connect the element
              * Remote: the equipment connected to the other end of radio link
              * SNM: equipment managed by SubNetwork Manager"
        ::= {equipRemoteElementEntry 4 }

    equipIpEthOsiNetMask   OBJECT-TYPE
        SYNTAX      IpAddress
        ACCESS      read-write
        STATUS      mandatory
        DESCRIPTION
            "The subnet Mask associated with the IP address of OSI ethernet interface.
             The value of the Mask is an IP address with all the network bits set to 1
             and all the hosts bits set to 0."
        ::=  {equipment 7}

    equipL1L2IsIsRouting   OBJECT-TYPE
        SYNTAX      INTEGER {
                             l1 (1),
    	                       l2 (2)
                            }
        ACCESS      read-write
        STATUS      mandatory
        DESCRIPTION
            "It defines the IS-IS routing type: L1 within  the same area, L2 among 
             different areas"
        DEFVAL { l1 } 
        ::= {equipment 8}

    equipStationID  OBJECT-TYPE
        SYNTAX      DisplayString   (SIZE(0..31))
        ACCESS      read-write
        STATUS      mandatory
        DESCRIPTION
            "ASCII string assigned by the operator to identify the specific equipment"
       ::= {equipment 9}

    equipPhoneNumber  OBJECT-TYPE
        SYNTAX      INTEGER
        ACCESS      read-write
        STATUS      mandatory
        DESCRIPTION
            "Phone number assigned to the equipment"
        ::= {equipment 10}

    equipTrapAckNotificationCount  OBJECT-TYPE
        SYNTAX      INTEGER     (1..5)
        ACCESS      read-write
        STATUS      mandatory
        DESCRIPTION
            "Notificatin count time before a TrapWithAck not acknowledged cause
             a forced logoff to remote user"
        DEFVAL { 3 }
        ::= {equipment 11}

    equipTrapAckNotificationTime  OBJECT-TYPE
        SYNTAX      TimeTicks   (1..60)
        ACCESS      read-write
        STATUS      mandatory
        DESCRIPTION
            "Waiting time before a new notification of a TrapWithAck not
             acknowledged"
        DEFVAL { 10 }
        ::= {equipment 12}

    equipTrapAcknowledge  OBJECT-TYPE
        SYNTAX      INTEGER
        ACCESS      write-only
        STATUS      mandatory
        DESCRIPTION
            "Code number related to the Trap to be acknowledged"
        ::= {equipment 13}

    equipAlarmSyntesysCritical  OBJECT-TYPE
       SYNTAX     INTEGER {
                           cleared (1),
                           activeReportable-Critical (6)
                          }
       ACCESS     read-only
       STATUS     mandatory
       DESCRIPTION
           "OR of all Critical Alarms"
       ::= {equipment 14}

    equipAlarmSyntesysCriticalSeverityCode  OBJECT-TYPE
        SYNTAX      INTEGER {
                             disable (1),
                             critical-trapEnable (6),
                             critical-trapEnableWithACK (38),
                             critical-trapDisable (22)
                            }
        ACCESS      read-write
        STATUS      mandatory
        DESCRIPTION
            "Define the severity associated to the EquipAlarmSyntesysCritical
             and enable/disable the trap generation on status change event."
        DEFVAL      { critical-trapEnable }
        ::= {equipment 15}

    equipAlarmSyntesysMajor OBJECT-TYPE
        SYNTAX      INTEGER {
                             cleared (1),
                             activeReportable-Major  (5)
                            }
        ACCESS      read-only
        STATUS      mandatory
        DESCRIPTION
            "OR of all Major Alarms"
        ::= {equipment  16}

    equipAlarmSyntesysMajorSeverityCode  OBJECT-TYPE
        SYNTAX      INTEGER {
                             disable (1),
                             major-trapEnable (5),
                             major-trapEnableWithACK (37),
                             major-trapDisable (21)
                            }
        ACCESS      read-write
        STATUS      mandatory
        DESCRIPTION
            "Define the severity associated to EquipAlarmSyntesysMajor
             and enable/disable the trap generation on status change event."
        DEFVAL      { major-trapEnable }
        ::= {equipment 17}

    equipAlarmSyntesysMinor  OBJECT-TYPE
        SYNTAX      INTEGER {
                             cleared (1),
                             activeReportable-Minor (4)
                            }
        ACCESS      read-only
        STATUS      mandatory
        DESCRIPTION
            "OR of all Minor Alarms"
        ::= {equipment  18}
  
    equipAlarmSyntesysMinorSeverityCode  OBJECT-TYPE
        SYNTAX      INTEGER {
                             disable (1),
                             minor-trapEnable (4),
                             minor-trapEnableWithACK (36),
                             minor-trapDisable (20)
                            }
        ACCESS      read-write
        STATUS      mandatory
        DESCRIPTION
            "Define the severity associated to EquipAlarmSyntesysMinor
             and enable/disable the trap generation on status change event."
        DEFVAL      { minor-trapEnable }
        ::= {equipment 19}

    equipAlarmSyntesysWarning  OBJECT-TYPE
        SYNTAX      INTEGER {
                             cleared (1),
                             activeReportable-Warning (3)
                            }
        ACCESS      read-only
        STATUS      mandatory
        DESCRIPTION
            "OR of all Warning Alarms"
        ::= {equipment 20} 

    equipAlarmSyntesysWarningSeverityCode  OBJECT-TYPE
        SYNTAX      INTEGER {
                             disable (1),
                             warning-trapEnable (3),
                             warning-trapEnableWithACK (35),
                             warning-trapDisable (19)
                            }
        ACCESS      read-write
        STATUS      mandatory
        DESCRIPTION
            "Define the severity associated to EquipAlarmSyntesysWarning
             and  enable/disable the trap generation on status change event."
        DEFVAL      { warning-trapEnable }
        ::= {equipment 21}

    equipLOMConfigEnable  OBJECT-TYPE
        SYNTAX      INTEGER {
                             disable (1),
                             enable  (2)
                            }
        ACCESS      read-write
        STATUS      mandatory
        DESCRIPTION
            "Enable/Disable the capabilityto connect a LOM in Configuration Mode"
        ::= {equipment 22}

    equipLOMConnected  OBJECT-TYPE
        SYNTAX    INTEGER {
                           cleared                     (1),
                           connectionAsMonitor         (2),
                           connectionAsConfig          (3)
                          }
        ACCESS      read-only
        STATUS      mandatory
        DESCRIPTION 
            "Signal when the LOM is connected to the NE and if the connection
             is for monitor or configuration"
        ::= {equipment 23}

    equipLOMConnectedTrapEnable   OBJECT-TYPE
        SYNTAX      INTEGER {
                            trapDisable        (1),
                            trapEnable         (2),
                            trapEnableWithAck  (3)
                            }
        ACCESS      read-write
        STATUS      mandatory
        DESCRIPTION
            "Enable/disable the trap generation on EquipLOMConnected status change event."
        DEFVAL      { trapEnable }
        ::= {equipment 24}

    equipManualOperation  OBJECT-TYPE
        SYNTAX      INTEGER {
                             cleared (1),
                             activeReportable-Warning (3)
                            }
        ACCESS      read-only
        STATUS      mandatory
        DESCRIPTION
            "Manual Operation active on the equipment"
        ::= {equipment 25}

    equipManualOperationSeverityCode   OBJECT-TYPE
        SYNTAX      INTEGER {
                             disable (1),
                             warning-trapEnable (3),
                             warning-trapEnableWithACK (35),
                             warning-trapDisable (19)
                            }
        ACCESS      read-write
        STATUS      mandatory
        DESCRIPTION
            "Enable/disable the trap generation on  EquipManualOperation
             status change event."
        DEFVAL      { warning-trapEnable }
        ::= {equipment 26}

    equipConfigChange  OBJECT-TYPE
        SYNTAX      OCTET STRING    (SIZE(6))
        ACCESS      read-write
        STATUS      mandatory
        DESCRIPTION
             "Set by the NE when the equipment configuration is changed by the local
              or Remote LOM. 
              The octet string is a bit stream of flags; a set bit is a change on a
              specific item. We had:
              Byte 0.7: change in configuration for equipment group
              Byte 0.6: change in configuration for userInput group
              Byte 0.5: change in configuration for userOutput group
              Byte 0.4: change in configuration for alarmLog group
              ......
              Byte 3.7: change in a severity for equipment group
              Byte 3.6: change in a severity for userInput group
              Byte 3.5: change in a severity for userOutput group
              Byte 3.4: change in a severity for alarmLog group
              CEM can reset the change condition writing one to desired bit flag
              ......
              "
        ::= {equipment 27}

    equipConfigChangeTrapEnable  OBJECT-TYPE
        SYNTAX    INTEGER {
                            trapDisable        (1),
                            trapEnable         (2),
                            trapEnableWithACK  (3)
                       }
        ACCESS      read-write
        STATUS      mandatory
        DESCRIPTION 
            "Enable/disable the trap generation on  EquipConfigChange  status 
             change event."  
        DEFVAL{ trapEnable }
    ::=  { equipment  28 }

    equipRequest   OBJECT-TYPE
        SYNTAX    INTEGER {
                            restart               (1),
                            applyIfChange         (2),
                            revertIfChange        (3),
                            configClearAndRestart (4),
                            routeTableClear       (5),
                            uploadBaseBand        (6),
                            offLineRouteRetrieve  (7),
                            offLineRouteSave      (8)
                          }
        ACCESS      write-only
        STATUS      mandatory
        DESCRIPTION 
         "Force Equipment Controller restart or change in interface properties"
        ::=  { equipment  29 }

    equipOffLineRouteTable OBJECT-TYPE
        SYNTAX  SEQUENCE OF EquipOffLineRouteEntry
        ACCESS  not-accessible
        STATUS  mandatory
        DESCRIPTION
            "Off Line editable route table. Do not affect equipment route table
             actually in use "
        ::= { equipment 30 }

    equipOffLineRouteEntry OBJECT-TYPE
        SYNTAX  EquipOffLineRouteEntry
        ACCESS  not-accessible
        STATUS  mandatory
        DESCRIPTION
            "A route to a particular destination."
        INDEX   { equipOffLineRouteDest }
        ::= { equipOffLineRouteTable 1 }

    EquipOffLineRouteEntry ::=
        SEQUENCE {
            equipOffLineRouteDest         IpAddress,
            equipOffLineRouteIfIndex      INTEGER,
            equipOffLineRouteNextHop      IpAddress,
            equipOffLineRouteMask         IpAddress
        }

    equipOffLineRouteDest OBJECT-TYPE
        SYNTAX  IpAddress
        ACCESS  read-only
        STATUS  mandatory
        DESCRIPTION
            "The destination IP address of this route"
        ::= { equipOffLineRouteEntry 1 }

    equipOffLineRouteIfIndex OBJECT-TYPE
        SYNTAX  INTEGER
        ACCESS  read-write
        STATUS  mandatory
        DESCRIPTION
            "The index value which uniquely identifies the
                local interface"
        ::= { equipOffLineRouteEntry 2 }

    equipOffLineRouteNextHop OBJECT-TYPE
        SYNTAX  IpAddress
        ACCESS  read-write
        STATUS  mandatory
        DESCRIPTION
            "The IP address of the next hop of this route"
        ::= { equipOffLineRouteEntry 3 }

    equipOffLineRouteMask OBJECT-TYPE
        SYNTAX  IpAddress
        ACCESS  read-write
        STATUS  mandatory
        DESCRIPTION
            "The subnet mask."
        ::= { equipOffLineRouteEntry 4 }

    equipIpPppTable OBJECT-TYPE
        SYNTAX SEQUENCE OF EquipIpPppRecord
        ACCESS      not-accessible
        STATUS      mandatory
        DESCRIPTION
            "Table with one record for each IP over PPP interface that is active in the NE"
        ::= { equipment 31 }        

    equipIpPppRecord  OBJECT-TYPE
        SYNTAX    EquipIpPppRecord
        ACCESS    not-accessible
        STATUS    mandatory
        DESCRIPTION
            "record defining one IP interface"
        INDEX     {equipIpPppInterfaceId}
        ::= { equipIpPppTable 1 }

    EquipIpPppRecord  ::=
        SEQUENCE {
            equipIpPppInterfaceId     INTEGER,
            equipIpPppAddress         IpAddress,
            equipIpPppNetMask         IpAddress,
            equipIpPppMode            INTEGER,
            equipIpPppSpeed           INTEGER
        }

    equipIpPppInterfaceId  OBJECT-TYPE
        SYNTAX    INTEGER {
                           pppLct             (1),
                           pppRS-232          (2),
                           pppRadio           (3),
                           pppAggWest         (4),
                           pppAggEast         (5),
                           pppAggTrib         (6),
                           pppRemoteSpv       (7)
                          }
        ACCESS    read-only
        STATUS    mandatory
        DESCRIPTION
            "This object is used as Index of equipIpPppTable and define the interface Id"
        ::= { equipIpPppRecord 1 }
        
    equipIpPppAddress   OBJECT-TYPE
        SYNTAX      IpAddress
        ACCESS      read-write
        STATUS      mandatory
        DESCRIPTION
            "Ip address of the interface"
        ::=  { equipIpPppRecord 2 }

    equipIpPppNetMask   OBJECT-TYPE
        SYNTAX      IpAddress
        ACCESS      read-write
        STATUS      mandatory
        DESCRIPTION
            "The subnet Mask associated with the IP address."
        ::=  { equipIpPppRecord 3}

    equipIpPppMode   OBJECT-TYPE
        SYNTAX      INTEGER {
                              client           (1),
    	                        server           (2),
    	                        auto             (3)
                            }
        ACCESS      read-write
        STATUS      mandatory
        DESCRIPTION
            "It defines the working mode of interface"
        DEFVAL      { auto }
        ::= { equipIpPppRecord 4 }

    equipIpPppSpeed   OBJECT-TYPE
        SYNTAX      INTEGER {
                             b9600             (1),
    	                       b19200            (2),
                             b38400		         (3),
                             b57600            (4)
                            }
        ACCESS      read-write
        STATUS      mandatory
        DESCRIPTION
            "It defines the speed of interface"
        DEFVAL      { b38400 }
        ::= { equipIpPppRecord 5 }

    equipSummaryAlarmTable  OBJECT-TYPE
        SYNTAX SEQUENCE OF EquipSummaryAlarmEntry
        ACCESS      not-accessible
        STATUS      mandatory
        DESCRIPTION
            "Table with one record for each Alarms&Controls that is active in the NE"
        ::= {equipment 36}        

    equipSummaryAlarmEntry  OBJECT-TYPE
        SYNTAX    EquipSummaryAlarmEntry
        ACCESS    not-accessible
        STATUS    mandatory
        DESCRIPTION
            "Alarms&Controls  records"
        INDEX     {equipSummaryRecordId}
        ::= {equipSummaryAlarmTable 1}

    EquipSummaryAlarmEntry  ::=
        SEQUENCE {
            equipSummaryRecordId                  INTEGER,
            equipSummaryManagedObject             OBJECT IDENTIFIER,
            equipSummaryManagedObjectInstance     OBJECT IDENTIFIER,
            equipSummaryEventDescription          DisplayString,    
            equipSummaryProbableCause             INTEGER,
            equipSummaryAlarmStatus               INTEGER,
            equipSummaryEventTime                 TimeTicks 
        }

    equipSummaryRecordId  OBJECT-TYPE
        SYNTAX    INTEGER 
        ACCESS    read-only
        STATUS    mandatory
        DESCRIPTION
            "This object  is used as Index of EquipSummaryAlarmTable"
        ::= {equipSummaryAlarmEntry 1}
        
    equipSummaryManagedObject  OBJECT-TYPE
        SYNTAX     OBJECT IDENTIFIER
        ACCESS     read-only
        STATUS     mandatory
        DESCRIPTION
            "The Object Identifier of  the Managed Object with
             Alarms or  Controls  active (not cleared Alarm Status)"
        ::= {equipSummaryAlarmEntry 2}

    equipSummaryManagedObjectInstance  OBJECT-TYPE
        SYNTAX    OBJECT IDENTIFIER
        ACCESS    read-only
        STATUS    mandatory
        DESCRIPTION
            "This object is the instance of the ManagedObject in dot notation
             (only instance part)"
        ::= {equipSummaryAlarmEntry 3}

    equipSummaryEventDescription  OBJECT-TYPE
        SYNTAX    DisplayString   (SIZE(0..80))
        ACCESS    read-only
        STATUS    mandatory
        DESCRIPTION
            "ASCII string used to describe the event"
        ::= {equipSummaryAlarmEntry 4}

    equipSummaryProbableCause  OBJECT-TYPE
        SYNTAX    INTEGER 
        ACCESS    read-only
        STATUS    mandatory
        DESCRIPTION
            "This object identifies the type of alarm"
        ::= {equipSummaryAlarmEntry  5}

    equipSummaryAlarmStatus  OBJECT-TYPE
        SYNTAX    INTEGER {
                           activeReportable-Status (2),
                           activeReportable-Warning (3),
                           activeReportable-Minor (4),
                           activeReportable-Major (5),
                           activeReportable-Critical (6)
                          }
        ACCESS    read-only
        STATUS    mandatory
        DESCRIPTION
            "Alarm Status with associated severity"
        ::= {equipSummaryAlarmEntry  6}
        
    equipSummaryEventTime  OBJECT-TYPE
        SYNTAX      TimeTicks
        ACCESS      read-only
        STATUS      mandatory
        DESCRIPTION
            "The time when the Alarm became active.
             In seconds since 01/01/70"
        ::= { equipSummaryAlarmEntry 7 }

    equipIpEthAddress   OBJECT-TYPE
        SYNTAX      IpAddress
        ACCESS      read-write
        STATUS      mandatory
        DESCRIPTION
            "Ip address of the equipment on Ethernet interface"
        ::=  {equipment 38 }

    equipIpEthNetMask   OBJECT-TYPE
        SYNTAX      IpAddress
        ACCESS      read-write
        STATUS      mandatory
        DESCRIPTION
            "The subnet Mask associated with the IP address of  ethernet interface.
             The value of the Mask is an IP address with all the network bits set to 1
             and all the hosts bits set to 0."
        ::=  {equipment 39}

    equipIpPPPAddress   OBJECT-TYPE
        SYNTAX      IpAddress
        ACCESS      read-write
        STATUS      mandatory
        DESCRIPTION
            "Ip address of the equipment on PPP interface"
        ::=  {equipment 40 }

    equipIpPPPNetMask   OBJECT-TYPE
        SYNTAX      IpAddress
        ACCESS      read-write
        STATUS      mandatory
        DESCRIPTION
            "The subnet Mask associated with the IP address of  PPP interface.
             The value of the Mask is an IP address with all the network bits set to 1
             and all the hosts bits set to 0."
        ::=  {equipment 41 }
        
    equipPPPMode   OBJECT-TYPE
        SYNTAX      INTEGER {
                             client           (1),
    	                       server           (2)
                            }
        ACCESS      read-write
        STATUS      mandatory
        DESCRIPTION
            "It defines  the working mode of PPP protocol"
        DEFVAL      { client }
        ::= {equipment 42}

    equipPPPBaudRate   OBJECT-TYPE
        SYNTAX      INTEGER {
                             b9600             (1),
    	                       b19200            (2),
                             b38400		         (3),
                             b57600            (4)
                            }
        ACCESS      read-write
        STATUS      mandatory
        DESCRIPTION
            "It defines the baud rate of  PPP port"
        DEFVAL      { b38400 }
        ::= {equipment 43}

    equipLctPPPBaudRate   OBJECT-TYPE
        SYNTAX      INTEGER {
                             b9600             (1),
    	                       b19200            (2),
                             b38400		         (3),
                             b57600            (4)
                            }
        ACCESS      read-write
        STATUS      mandatory
        DESCRIPTION
            "It defines the baud rate of  LCT-PPP port"
        DEFVAL      { b38400 }
        ::= {equipment 44}

    equipOsiamParameter   OBJECT-TYPE
        SYNTAX      Opaque
        ACCESS      read-write
        STATUS      mandatory
        DESCRIPTION
            "It defines the set-up  parameter for OSI stack "
        ::= {equipment 45}

    equipAlarmAlign   OBJECT-TYPE
        SYNTAX      INTEGER {
                             align           (1)
                            }
        ACCESS      write-only
        STATUS      mandatory
        DESCRIPTION
            "Force equipment to re-send all trap of active alarm"
        ::= {equipment 46}
        
    equipIpPPPradioAddress   OBJECT-TYPE
        SYNTAX      IpAddress
        ACCESS      read-write
        STATUS      mandatory
        DESCRIPTION
            "Ip address of the PPP radio interface"
        ::=  {equipment 47 }

    equipIpPPPradioNetMask   OBJECT-TYPE
        SYNTAX      IpAddress
        ACCESS      read-write
        STATUS      mandatory
        DESCRIPTION
            "The subnet Mask associated with the IP address of PPP radio interface.
             The value of the Mask is an IP address with all the network bits set to 1
             and all the hosts bits set to 0."
        ::=  {equipment 48 }
        
    equipPPPradioMode   OBJECT-TYPE
        SYNTAX      INTEGER {
                             client           (1),
    	                       server           (2)
                            }
        ACCESS      read-write
        STATUS      mandatory
        DESCRIPTION
            "It defines the working mode of PPP radio protocol"
        DEFVAL      { client }
        ::= {equipment 49}

    equipIpLctPPPAddress   OBJECT-TYPE
        SYNTAX      IpAddress
        ACCESS      read-write
        STATUS      mandatory
        DESCRIPTION
            "Ip address of the LCT interface"
        ::=  {equipment 50 }

    equipIpLctPPPNetMask   OBJECT-TYPE
        SYNTAX      IpAddress
        ACCESS      read-write
        STATUS      mandatory
        DESCRIPTION
            "The subnet Mask associated with the IP address of PPP Lct interface.
             The value of the Mask is an IP address with all the network bits set to 1
             and all the hosts bits set to 0."
        ::=  {equipment 51 }

    equipIpSnmpAgentAddress   OBJECT-TYPE
        SYNTAX      IpAddress
        ACCESS      read-write
        STATUS      mandatory
        DESCRIPTION
            "Ip address used by SNMP Agent for mark generated TRAP"
        ::=  {equipment 52 }

    equipManOpTable  OBJECT-TYPE
        SYNTAX SEQUENCE OF EquipManOpRecord
        ACCESS      not-accessible
        STATUS      mandatory
        DESCRIPTION
            "Table with manual operation record"
        ::= {equipment 53}

    equipManOpRecord  OBJECT-TYPE
        SYNTAX    EquipManOpRecord
        ACCESS    not-accessible
        STATUS    mandatory
        DESCRIPTION
            "manual operation record"
        INDEX     {equipManOpId}
        ::= {equipManOpTable 1}

    EquipManOpRecord  ::=
        SEQUENCE {
            equipManOpId            INTEGER,
            equipManOpObjectId      OBJECT IDENTIFIER,
            equipManOpInstanceId    OBJECT IDENTIFIER
        }

    equipManOpId  OBJECT-TYPE
        SYNTAX      INTEGER
        ACCESS      read-only
        STATUS      mandatory
        DESCRIPTION
            "manual operation index"
        ::=  {equipManOpRecord 1}

    equipManOpObjectId  OBJECT-TYPE
        SYNTAX      OBJECT IDENTIFIER
        ACCESS      read-only
        STATUS      mandatory
        DESCRIPTION
            "object identifier of the manual operation active element"
        ::=  {equipManOpRecord 2}

    equipManOpInstanceId  OBJECT-TYPE
        SYNTAX      OBJECT IDENTIFIER
        ACCESS      read-only
        STATUS      mandatory
        DESCRIPTION
            "instance of the manual operation active element"
        ::=  {equipManOpRecord 3}

    equipManOpTimeOut  OBJECT-TYPE
        SYNTAX      INTEGER   (0..172800)
        ACCESS      read-write
        STATUS      mandatory
        DESCRIPTION
            "this object defines the time (in seconds) after wich the manual
             operations are cleared. The maximium value is equivalent to 48 hours.
             A zero means no Time-out"
        DEFVAL      { 2 }
        ::=  {equipment 54}
        
    equipManager1IpAddr   OBJECT-TYPE
        SYNTAX      IpAddress
        ACCESS      read-write
        STATUS      mandatory
        DESCRIPTION
            "First IP address of a SNMP Manager always logged to this equipment.
             The address 0.0.0.0 mean that manager is not present"
        ::=  {equipment 55 }

    equipManager2IpAddr   OBJECT-TYPE
        SYNTAX      IpAddress
        ACCESS      read-write
        STATUS      mandatory
        DESCRIPTION
            "Second IP address of a SNMP Manager always logged to this equipment.
             The address 0.0.0.0 mean that manager is not present"
        ::=  {equipment 56 }


-----------------------------------------------------------------------------------
---  The Equipment  Group generates the following TRAPs:
-----------------------------------------------------------------------------------

    equipAlarmSyntesysCriticalSet TRAP-TYPE
        ENTERPRISE pdh-al 
        DESCRIPTION
            "This event is generated by NE when equipAlarmSyntesysCritical is set
             The data passed with the event are:
                1) equipAlarmSyntesysCritical
                2) equipTrapAcknowledge code number"
    ::= 101

    equipAlarmSyntesysCriticalCleared TRAP-TYPE
        ENTERPRISE pdh-al 
        DESCRIPTION
            "This event is generated by NE when equipAlarmSyntesysCritical is cleared
             The data passed with the event are:
                1) equipAlarmSyntesysCritical
                2) equipTrapAcknowledge code number"
    ::= 102

    equipAlarmSyntesysMajorSet TRAP-TYPE
        ENTERPRISE pdh-al 
        DESCRIPTION
            "This event is generated by NE when equipAlarmSyntesysMajor is set
             The data passed with the event are:
                1) equipAlarmSyntesysMajor
                2) equipTrapAcknowledge code number"

    ::= 103

    equipAlarmSyntesysMajorCleared  TRAP-TYPE
        ENTERPRISE pdh-al 
        DESCRIPTION
            "This event is generated by NE when EquipAlarmSyntesysMajor is cleared
             The data passed with the event are:
                1) equipAlarmSyntesysMajor
                2) equipTrapAcknowledge code number"
    ::= 104

    equipAlarmSyntesysMinorSet  TRAP-TYPE
        ENTERPRISE pdh-al 
        DESCRIPTION
            "This event is generated by NE when EquipAlarmSyntesysMinor is set
             The data passed with the event are:
                1) EquipAlarmSyntesysMinor
                2) equipTrapAcknowledge code number"
    ::= 105

    equipAlarmSyntesysMinorCleared  TRAP-TYPE
        ENTERPRISE pdh-al 
        DESCRIPTION
            "This event is generated by NE when EquipAlarmSyntesysMinor is cleared
             The data passed with the event are:
                1) EquipAlarmSyntesysMinor
                2) equipTrapAcknowledge code number"
    ::= 106

    equipAlarmSyntesysWarningSet  TRAP-TYPE
        ENTERPRISE pdh-al 
        DESCRIPTION
            "This event is generated by NE when EquipAlarmSyntesysWarning is set
             The data passed with the event are:
                1) EquipAlarmSyntesysWarning
                2) equipTrapAcknowledge code number"
    ::= 107

    equipAlarmSyntesysWarningCleared  TRAP-TYPE
        ENTERPRISE pdh-al 
        DESCRIPTION
            "This event is generated by NE when EquipAlarmSyntesysWarning is cleared
             The data passed with the event are:
                1) EquipAlarmSynthesisWarning
                2) equipTrapAcknowledge code number"
    ::= 108

    equipLOMConnectedMonitor  TRAP-TYPE
        ENTERPRISE pdh-al 
        DESCRIPTION
            "This event is generated by NE when equipLOMConnected is set to Monitor mode
             The data passed with the event are:
                1) equipLOMConnected
                2) equipTrapAcknowledge code number"
    ::= 109

    equipLOMConnectedConfig  TRAP-TYPE
        ENTERPRISE pdh-al 
        DESCRIPTION
            "This event is generated by NE when equipLOMConnected is set to Configuration  mode
             The data passed with the event are:
                1) equipLOMConnected
                2) equipTrapAcknowledge code number"
    ::= 110

    equipLOMDisconnected  TRAP-TYPE
        ENTERPRISE pdh-al 
        DESCRIPTION
            "This event is generated by NE when LOMConnected is cleared
             The data passed with the event are:
                1) equipLOMConnected
                2) equipTrapAcknowledge code number"
    ::= 111

    equipManualOperationSet  TRAP-TYPE
        ENTERPRISE pdh-al 
        DESCRIPTION
            "This event is generated by NE when equipManualOperation is set
             The data passed with the event are:
                1) equipManualOperation
                2) equipTrapAcknowledge code number"
    ::= 112

    equipManualOperationCleared  TRAP-TYPE
        ENTERPRISE pdh-al 
        DESCRIPTION
            "This event is generated by  NE when EquipManualOperation is cleared
             The data passed with the event are:
                1) equipManualOperation
                2) equipTrapAcknowledge code number"
    ::= 113

    equipConfigChangeStatus  TRAP-TYPE
        ENTERPRISE pdh-al 
        DESCRIPTION
            "This event is generated by NE when equipConfigChange is changed
             The data passed with the event are:
                1) equipConfigChange
                2) equipTrapAcknowledge code number"
    ::= 114


--
--  4.3 User Input Group
--  This group is used to describe the user inputs available on the equipment.
--  It is a table with a row for each equipped user input.
--

    userInputTable  OBJECT-TYPE
        SYNTAX      SEQUENCE OF UserInputEntry
        ACCESS      not-accessible
        STATUS      mandatory
        DESCRIPTION
            "Table with User Input records"
        ::= {userInput 1}

    userInputEntry  OBJECT-TYPE
        SYNTAX      UserInputEntry
        ACCESS      not-accessible
        STATUS      mandatory
        DESCRIPTION

            "User Input records"
        INDEX       {userInputNumber}
        ::= {userInputTable 1}

    UserInputEntry  ::=
        SEQUENCE  {
            userInputNumber               INTEGER,
            userInputLabel                DisplayString,
            userInputActiveState          INTEGER,
            userInputAlarmStatus          INTEGER,
            userInputAlarmSeverityCode    INTEGER,
            userInputRemoteTerminal       INTEGER
        }

    userInputNumber  OBJECT-TYPE
        SYNTAX      INTEGER
        ACCESS      read-only
        STATUS      mandatory
        DESCRIPTION
            "User Input number is used as the index for the user input table"
        ::= {userInputEntry 1}

    userInputLabel  OBJECT-TYPE
        SYNTAX      DisplayString   (SIZE(0..31))
        ACCESS      read-write
        STATUS      mandatory
        DESCRIPTION
            "ASCII string used by the operator to identify  the user input"
        DEFVAL      {"USER INPUT CH." }
        ::= {userInputEntry 2}

    userInputActiveState  OBJECT-TYPE
        SYNTAX      INTEGER {
                        open (1),
                        closed (2)
                    }
        ACCESS      read-write
        STATUS      mandatory
        DESCRIPTION
            "User Input Active State (meaningless for remote user inputs)"
        DEFVAL      {closed}
        ::= {userInputEntry 3}
      
    userInputAlarmStatus  OBJECT-TYPE
        SYNTAX      INTEGER {
                        cleared (1),
                        activeReportable-Status (2),
                        activeReportable-Warning (3),
                        activeReportable-Minor (4),
                        activeReportable-Major (5),
                        activeReportable-Critical (6)
                    }
        ACCESS      read-only
        STATUS      mandatory
        DESCRIPTION
            "User Input status with associated Severity"
        ::= {userInputEntry 4}

    userInputAlarmSeverityCode  OBJECT-TYPE
        SYNTAX      INTEGER {
                              disable (1),
                              status-trapEnable (2),
                              status-trapEnableWithACK (34),
                              warning-trapEnable (3),
                              warning-trapEnableWithACK (35),
                              minor-trapEnable (4),
                              minor-trapEnableWithACK (36),
                              major-trapEnable (5),
                              major-trapEnableWithACK (37),
                              critical-trapEnable (6),
                              critical-trapEnableWithACK (38),
                              status-trapDisable (18),
                              warning-trapDisable (19),
                              minor-trapDisable (20),
                              major-trapDisable (21),
                              critical-trapDisable (22)
                    }
        ACCESS      read-write
        STATUS      mandatory
        DESCRIPTION
            "Define the severity associated to the user input active state and
             enable/disable the trap generation on status change event."
        DEFVAL      { major-trapEnable }
        ::= {userInputEntry 5}

    userInputRemoteTerminal  OBJECT-TYPE
        SYNTAX      INTEGER {
                        local   (1),
                        remote  (2)
                    }
        ACCESS      read-only
        STATUS      mandatory
        DESCRIPTION
          "it is a flag selecting if the user input is local or remote"
        ::= {userInputEntry 6}


--
--The User Input Group generates the following TRAP:
--

    userInputAlarmStatusSet  TRAP-TYPE
        ENTERPRISE pdh-al 
        DESCRIPTION
            "This event is generated by  NE when an User Input is set
             The data passed with the event are:
                1) UserInputNumber
                2) UserInputLabel
                3) UserInputAlarmStatus
                4) equipTrapAcknowledge code number"
        ::= 201

    userInputAlarmStatusCleared TRAP-TYPE
        ENTERPRISE pdh-al 
        DESCRIPTION
            "This event is generated by  NE when an User Input is set
             The data passed with the event are:
               1) UserInputNumber
               2) UserInputLabel
               3) UserInputAlarmStatus
               4) equipTrapAcknowledge code number"
        ::= 202



--
--  4.4 User Output Group
--  This group is used to describe the User Outputs (relay) available on the equipment.
--  It is a table  with a row for each equipped User Output.
--

    userOutputTable  OBJECT-TYPE
        SYNTAX      SEQUENCE OF UserOutputEntry
        ACCESS      not-accessible
        STATUS      mandatory
        DESCRIPTION
            "Table with User Output records"
        ::= {userOutput 1}

    userOutputEntry  OBJECT-TYPE
        SYNTAX      UserOutputEntry
        ACCESS      not-accessible
        STATUS      mandatory
        DESCRIPTION
            "User Output records"
        INDEX       {userOutputNumber}
        ::= {userOutputTable 1}

    UserOutputEntry  ::=
        SEQUENCE  {
            userOutputNumber                  INTEGER,
            userOutputLabel                   DisplayString,
            userOutputActiveState             INTEGER,
            userOutputStatus                  INTEGER,
            userOutputForcedOperatorStatus    INTEGER,
            userOutputInternalStatus          OBJECT IDENTIFIER
        }

    userOutputNumber  OBJECT-TYPE
        SYNTAX      INTEGER
        ACCESS      read-only
        STATUS      mandatory
        DESCRIPTION
            "User Output number is used as the index for the User Output table"
        ::= {userOutputEntry 1}

    userOutputLabel  OBJECT-TYPE
        SYNTAX      DisplayString   (SIZE(0..31))
        ACCESS      read-write
        STATUS      mandatory
        DESCRIPTION
            "ASCII string used by the operator to identify the User Output"
        DEFVAL      {"USER OUTPUT CH." }
        ::= {userOutputEntry 2}

    userOutputActiveState  OBJECT-TYPE
        SYNTAX    INTEGER {
                           open   (1),
                           closed (2)
                          }
        ACCESS      read-write
        STATUS      mandatory
        DESCRIPTION
            "Define the Active State of User Output"
        DEFVAL      {closed}
        ::= {userOutputEntry 3}

    userOutputStatus  OBJECT-TYPE
        SYNTAX    INTEGER {
                           notActive (1),
                           active    (2)
                          }
        ACCESS      read-only
        STATUS      mandatory
        DESCRIPTION
            "User Output status."
        ::= {userOutputEntry 4}

    userOutputForcedOperatorStatus OBJECT-TYPE
        SYNTAX    INTEGER {
                           notActive (1),
                           active    (2)
                          }
        ACCESS      read-write
        STATUS      mandatory
        DESCRIPTION
           "User Output status forced by the operator."
        DEFVAL      {notActive}
        ::= {userOutputEntry 5}

    userOutputInternalStatus OBJECT-TYPE
        SYNTAX      OBJECT IDENTIFIER
        ACCESS      read-write
        STATUS      mandatory
        DESCRIPTION
            "User Output status connected to internal condition. Legal object 
             are:
                 - Equipment synthesis alarms: included Local and remote IDU/ODU
                 - Local User inputs
                 - Remote User inputs
                 - Forced by operator"
        DEFVAL      {userOutputForcedOperatorStatus}
        ::= {userOutputEntry 6}


----------------------------------------------------------------------------------
--  4.5 ALARM LOG GROUP
--  This group is used to manage the alarm log.
----------------------------------------------------------------------------------

    alarmLogTable  OBJECT-TYPE
        SYNTAX      SEQUENCE OF AlarmRecord
        ACCESS      not-accessible
        STATUS      mandatory
        DESCRIPTION 
            "Table with Alarm  records."
        ::=  { alarmLog 1 }


    alarmLogRecord  OBJECT-TYPE
        SYNTAX      AlarmRecord
        ACCESS      not-accessible
        STATUS      mandatory
        DESCRIPTION 
            "Alarm  records"
        INDEX { alarmLogRecordId }
        ::=  { alarmLogTable 1 }

    AlarmRecord  ::=
        SEQUENCE {
            alarmLogRecordId                  INTEGER,
            alarmLogManagedObject             OBJECT IDENTIFIER,
            alarmLogManagedObjectInstance     OBJECT IDENTIFIER,
            alarmLogEventDescription          DisplayString,
            alarmLogProbableCause             INTEGER,
            alarmLogAlarmStatus               INTEGER,
            alarmLogEventTime                 TimeTicks
        }

    alarmLogRecordId  OBJECT-TYPE
        SYNTAX      INTEGER
        ACCESS      read-only
        STATUS      mandatory
        DESCRIPTION 
            "This object  is used as Index of AlarmLogTable."
        ::=  { alarmLogRecord  1 }

    alarmLogManagedObject  OBJECT-TYPE
        SYNTAX      OBJECT IDENTIFIER
        ACCESS      read-only
        STATUS      mandatory
        DESCRIPTION 
            "The Object Identifier of  the Managed Object."
        ::=  { alarmLogRecord 2 }

    alarmLogManagedObjectInstance  OBJECT-TYPE
        SYNTAX      OBJECT IDENTIFIER
        ACCESS      read-only
        STATUS      mandatory
        DESCRIPTION 
            "This object  is the instance of the ManagedObject."
        ::=  { alarmLogRecord  3 }

    alarmLogEventDescription  OBJECT-TYPE
        SYNTAX      DisplayString   (SIZE(0..80))
        ACCESS      read-only
        STATUS      mandatory
        DESCRIPTION 
            "ASCII string used to describe the event (can be an empty string)."
        ::=  { alarmLogRecord  4 }

    alarmLogProbableCause  OBJECT-TYPE
        SYNTAX      INTEGER
        ACCESS      read-only
        STATUS      mandatory
        DESCRIPTION 
            "This object  identifies the type of alarm."
        ::=  { alarmLogRecord  5 }

    alarmLogAlarmStatus OBJECT-TYPE
        SYNTAX    INTEGER {
                           cleared                        (1),
                           activeReportable-Status        (2),
                           activeReportable-Warning       (3),
                           activeReportable-Minor         (4),
                           activeReportable-Major         (5),
                           activeReportable-Critical      (6)
                          }
        ACCESS      read-only
        STATUS      mandatory
        DESCRIPTION 
            "Alarm statuswith associated severity"
        ::=  { alarmLogRecord  6 }

    alarmLogEventTime  OBJECT-TYPE
        SYNTAX      TimeTicks
        ACCESS      read-only
        STATUS      mandatory
        DESCRIPTION 
            "The time (in secs ) when the event was registered in the Log since 1/1/1970"
        ::=  { alarmLogRecord  7 }


----------------------------------------------------------------------------------
-- The following objects are used  to map the "action"
-- (delete record , transfer the log using NFS ...):
----------------------------------------------------------------------------------

    alarmLogActionRequest  OBJECT-TYPE
        SYNTAX    INTEGER {
                           delete (1),
                           read   (2)
                          }
        ACCESS      write-only
        STATUS      mandatory
        DESCRIPTION 
            "This object is used to delete or  to read the LOG  using Ftp (file transfer)"
        ::=  { alarmLog  2 }

    alarmLogFTPfile OBJECT-TYPE
        SYNTAX      DisplayString   (SIZE(0..255))
        ACCESS      read-write
        STATUS      mandatory
        DESCRIPTION 
            "Path and file name used when  the log is transferred  using Ftp (action =  read)"
        ::=  { alarmLog  3 }

----------------------------------------------------------------------------------
--  The following objects are used  to enable/disable  the event
--  record write in the Log.
----------------------------------------------------------------------------------

    alarmLogAlarmSeverityEnable  OBJECT-TYPE
        SYNTAX      INTEGER
        ACCESS      read-write
        STATUS      mandatory
        DESCRIPTION 
            "This object  enables the event record write in the log according to the severity:
             Bit0 = Status
             Bit1 = Warning
             Bit2 = Minor
             Bit3 = Major
             Bit4 = Critical"
        DEFVAL{  '1f'h  }
        ::= { alarmLog  4 }

    alarmLogStartHourEnable  OBJECT-TYPE
        SYNTAX      INTEGER   (0..23)
        ACCESS      read-write
        STATUS      mandatory
        DESCRIPTION 
            "This object  defines  whit AlarmLogEndHourEnable the period during a day 
             when the alarm records must be written in the log."
        DEFVAL{  0  }
        ::=  { alarmLog  5 }

    alarmLogEndHourEnable  OBJECT-TYPE
        SYNTAX      INTEGER   (0..23)
        ACCESS      read-write
        STATUS      mandatory
        DESCRIPTION 
            "This object  defines  whit AlarmLogStartHourEnable the period during a day 
             when the alarm records must be written in the log."
        DEFVAL{  23  }
        ::=  { alarmLog  6 }

----------------------------------------------------------------------------------
--  The following objects are used  as filters  when the manager reads or
--  deletes the events in the LOG.
----------------------------------------------------------------------------------

    alarmLogStartTimeFilter  OBJECT-TYPE
        SYNTAX      TimeTicks
        ACCESS      read-write
        STATUS      mandatory
        DESCRIPTION 
            "The events with EventTime greater than this object are read/delete from the log.
             Null value means no filter"
        DEFVAL{  0  }
        ::=  { alarmLog  7 }

    alarmLogEndTimeFilter  OBJECT-TYPE
        SYNTAX      TimeTicks
        ACCESS      read-write
        STATUS      mandatory
        DESCRIPTION 
            "The events with EventTime less than this object are read/delete from the log. 
             Null value means no filter"
        DEFVAL{  0  }
        ::=  { alarmLog  8 }

    alarmLogManagedObjectFilter OBJECT-TYPE
        SYNTAX      OBJECT IDENTIFIER
        ACCESS      read-write
        STATUS      mandatory
        DESCRIPTION 
            "The Object Identifier of  the Managed Object that  has to be read/delete from the log.
             Null value means no filter"
        DEFVAL{  pdh-al  }
        ::=  { alarmLog  9 }

    alarmLogAlarmSeverityFilter  OBJECT-TYPE
        SYNTAX    INTEGER
        ACCESS      read-write
        STATUS      mandatory
        DESCRIPTION 
            "This object defines the alarm severity of the records that must be read/delete from the log.
             Bit0 = Status
             Bit1 = Warning
             Bit2 = Minor
             Bit3 = Major
             Bit4 = Critical"
        DEFVAL{  '1f'h  }
        ::=  { alarmLog  10 }


    alarmLogProbableCauseFilter  OBJECT-TYPE
        SYNTAX    INTEGER
        ACCESS      read-write
        STATUS      mandatory
        DESCRIPTION 
            "This object defines the Probable Cause of the records that must be read/delete from the log. 
             Null value means no filter"
        DEFVAL{  0  }
        ::=  { alarmLog  11 }


--
-- The following objects are used as status indicator of FTP transfer
--

    alarmLogFTPStatus OBJECT-TYPE
        SYNTAX      INTEGER{
                            transferring (1),
                            completed    (2),
                            interrupted  (3),
                            empty        (4)
                           }
        ACCESS      read-only
        STATUS      mandatory
        DESCRIPTION
            "Status of alarm logger Ftp transfer operation"
        DEFVAL      { completed }
        ::= { alarmLog 12 }

    alarmLogFTPStatusTrapNotification OBJECT-TYPE
        SYNTAX      INTEGER {
                             trapDisable (1),
                             trapEnable (2),
                             trapEnableWithACK (34)
                            }
        ACCESS      read-write
        STATUS      mandatory
        DESCRIPTION
            "Enable/disable the trap generation on FTP tranfer operation."
        DEFVAL      { trapEnable }
        ::= { alarmLog 13 }


--
-- The Alarm Log generates the following TRAP:
--

    alarmLogFTPStatusTrap  TRAP-TYPE
        ENTERPRISE pdh-al 
        DESCRIPTION
            "This event is generated by NE when the status of FTP transfer is changed
             The data passed with the event are
             1) alarmLogFTPStatus
             2) accessControlLoginIpAddress
             3) equipTrapAcknowledge code number"
        ::= 401



----------------------------------------------------------------------------------
-- 4.6 ACCESS CONTROL GROUP
--
-- This table defines the users allowed to access the system.
-- The maximum number of user (number of records) is 13.
----------------------------------------------------------------------------------

    accessControlUserTable  OBJECT-TYPE
        SYNTAX      SEQUENCE OF AccessControlUserRecord
        ACCESS      not-accessible
        STATUS      mandatory
        DESCRIPTION 
            "Table with User  records"
        ::=  { accessControl 1 }

    accessControlUserRecord  OBJECT-TYPE
        SYNTAX      AccessControlUserRecord
        ACCESS      not-accessible
        STATUS      mandatory
        DESCRIPTION 
            "Alarm  records"
        INDEX { accessControlUsername }
        ::=  { accessControlUserTable 1 }

    AccessControlUserRecord  ::=
        SEQUENCE {
            accessControlUsername         DisplayString,
            accessControlPassword         DisplayString,
            accessControlUserProfile      INTEGER,
            accessControlLoginTimeout     INTEGER
        }

    accessControlUsername  OBJECT-TYPE
        SYNTAX      DisplayString   (SIZE(0..8))
        ACCESS      read-write
        STATUS      mandatory
        DESCRIPTION 
            "ASCII string identifying the user, it is used as Index for the table.
             The write of a not existing Username  is used to create, a new user,
             the write of a Null string to a specific (UserId) record  is used to delete an user."
        ::=  { accessControlUserRecord  1 }

    accessControlPassword  OBJECT-TYPE
        SYNTAX      DisplayString   (SIZE(0..8))
        ACCESS      write-only
        STATUS      mandatory
        DESCRIPTION 
            "ASCII string used as password."
        ::=  { accessControlUserRecord  2 }

    accessControlUserProfile OBJECT-TYPE
        SYNTAX INTEGER {
                           system                (1),
                           stationOperator       (2),
                           maintenanceOperatorA  (3),
                           maintenanceOperatorB  (4)
                       }
        ACCESS      read-write
        STATUS      mandatory
        DESCRIPTION 
            "This object defines the user  access privilege. It's not possible to change
             profile into system (1)."
        ::=  { accessControlUserRecord  3 }

    accessControlLoginTimeout  OBJECT-TYPE
        SYNTAX      INTEGER   (0..65535)
        ACCESS      read-write
        STATUS      mandatory
        DESCRIPTION 
            "This object defines the  time (seconds) after wich the login session is closed
             if no messages are received from the manager.
             The value is from 1 to 0xFFFF, 0 means no time out."
       ::=  { accessControlUserRecord  4 }


----------------------------------------------------------------------------------
-- The following table  is used to manage the user login,
-- up to four logins are possible (1 CEM  + 3 LOM).
----------------------------------------------------------------------------------

    accessControlLoginTable  OBJECT-TYPE
        SYNTAX      SEQUENCE OF AccessControlLoginRecord
        ACCESS      not-accessible
        STATUS      mandatory
        DESCRIPTION 
            "Table with Login  records. Max. number of Login equal 4."
        ::=  {accessControl 2 }

    accessControlLoginRecord  OBJECT-TYPE
        SYNTAX      AccessControlLoginRecord
        ACCESS      not-accessible
        STATUS      mandatory
        DESCRIPTION 
            "Alarm  records"
        INDEX { accessControlLoginIpAddress, accessControlLoginUsername }
        ::=  {accessControlLoginTable 1 }

    AccessControlLoginRecord  ::=
        SEQUENCE {
            accessControlLoginUsername      DisplayString,
            accessControlLoginPassword      DisplayString,
            accessControlLoginRequest       INTEGER,
            accessControlLoginIpAddress     IpAddress,
            accessControlTrapEnable         INTEGER
        }

    accessControlLoginUsername  OBJECT-TYPE
        SYNTAX      DisplayString   (SIZE(0..8))
        ACCESS      read-write
        STATUS      mandatory
        DESCRIPTION 
            "ASCII string identifying the user."
        ::=  { accessControlLoginRecord  1 }

    accessControlLoginPassword  OBJECT-TYPE
        SYNTAX      DisplayString   (SIZE(0..8))
        ACCESS      write-only
        STATUS      mandatory
        DESCRIPTION 
            "ASCII string used to verify if the user can access the system."
        ::=  { accessControlLoginRecord  2 }

    accessControlLoginRequest  OBJECT-TYPE
        SYNTAX  INTEGER {
                           login  (1),
                           logout (2)
                        }

        ACCESS      write-only
        STATUS      mandatory
        DESCRIPTION 
            "This object is used to request the login/logout of the user."
        ::=  { accessControlLoginRecord  3 }

    accessControlLoginIpAddress  OBJECT-TYPE
        SYNTAX  IpAddress
        ACCESS      read-write
        STATUS      mandatory
        DESCRIPTION 
            "It is the IP address of the logged user."
        ::=  { accessControlLoginRecord  4 }

    accessControlTrapEnable  OBJECT-TYPE
        SYNTAX  INTEGER {
                           trapDisable          (1),
                           trapEnableWithAck    (2),
                           trapEnableWithoutAck (3)
                        }
        ACCESS      read-write
        STATUS      mandatory
        DESCRIPTION 
            "Enable/disable of the trap toward the element defined by the IP address. 
             The trap can be with or without acknowledge from  the receiving entity"
        ::=  { accessControlLoginRecord  5 }



----------------------------------------------------------------------------------
-- 4.7 UNIT  GROUP
----------------------------------------------------------------------------------
-- This group is used to manage the units  (board and in general replaceable part) present in the equipment.
----------------------------------------------------------------------------------

    unitTable  OBJECT-TYPE
        SYNTAX      SEQUENCE OF UnitRecord
        ACCESS      not-accessible
        STATUS      mandatory
        DESCRIPTION 
          "Table with Unit  records."
        ::=  { unit 1 }

    unitRecord  OBJECT-TYPE
        SYNTAX      UnitRecord
        ACCESS      not-accessible
        STATUS      mandatory
        DESCRIPTION 
            "Unit record"
        INDEX { unitId }
        ::=  { unitTable 1 }

    UnitRecord  ::=
        SEQUENCE {
            unitId                    INTEGER,
            unitExpectedType          INTEGER,
            unitActualType            INTEGER,
            unitLabel                 DisplayString,
            unitFailAlarm             INTEGER,
            unitMissingAlarm          INTEGER,
            unitNotRespondingAlarm    INTEGER,
            unitHwMismatchAlarm       INTEGER,
            unitSwMismatchAlarm       INTEGER,
            unitHwEdition             DisplayString,
            unitPartNumber            DisplayString,
            unitParentPartNumber      DisplayString,
            unitParentSerialNumber    DisplayString
        }

    unitId  OBJECT-TYPE
        SYNTAX      INTEGER
        ACCESS      read-only
        STATUS      mandatory
        DESCRIPTION 
            "This object  is used as Index of the Unit Table."
        ::=  { unitRecord 1 }

    unitExpectedType  OBJECT-TYPE
        SYNTAX      INTEGER{
                            unequipped          (1),
                            eqController        (2),
                            lim                 (3),
                            rim                 (4),
                            radio               (5),
                            switchAndSplitter   (6),
                            serviceChannel1     (7),
                            serviceChannel2     (8),
                            serviceChannel3     (9),
                            serviceCnannel4     (10),
                            backpanel           (11)
                           }
        ACCESS      read-only
        STATUS      mandatory
        DESCRIPTION
            "Define the expected unit type"
        ::= { unitRecord 2 }

    unitActualType  OBJECT-TYPE
        SYNTAX      INTEGER{
                             unequipped                (1),
                            eqController              (2),
                            lim                       (3),
                            rim                       (4),
                            radio                     (5),
                            switchAndSplitter         (6),
                            serviceChannel1           (7),
                            serviceChannel2           (8),
                            serviceChannel3           (9),
                            serviceCnannel4           (10),
                            backpanel                 (11),
                            lim2x2-16x2-75ohm         (12),
                            lim2x2-16x2-120ohm        (13),
                            lim2x2-16x2-Coax          (14),
                            lim34M                    (15),
                            limEthernet               (16),
                            switchAndSplitter75ohm    (17),
                            switchAndSplitter120ohm   (18),
                            switchAndSplitterCoax     (19),
                            switchAndSplitter34M      (20)
                           }
        ACCESS      read-only
        STATUS      mandatory
        DESCRIPTION
            "Define the real unit type actually configurated"
        ::= { unitRecord 3 }

    unitLabel  OBJECT-TYPE
        SYNTAX      DisplayString (SIZE (0..30))
        ACCESS      read-only
        STATUS      mandatory
        DESCRIPTION
            "ASCII string used to assign a name to the unit"
        ::= { unitRecord 4 }

    unitFailAlarm  OBJECT-TYPE
        SYNTAX      INTEGER{
                            cleared (1),
                            activeReportable-Status (2),
                            activeReportable-Warning (3),
                            activeReportable-Minor (4),
                            activeReportable-Major (5),
                            activeReportable-Critical (6)
                           }
        ACCESS      read-only
        STATUS      mandatory
        DESCRIPTION
            "Unit Fail alarm status status with associated Severity"
        ::= { unitRecord 5 }

    unitMissingAlarm  OBJECT-TYPE
        SYNTAX      INTEGER{
                            cleared (1),
                            activeReportable-Status (2),
                            activeReportable-Warning (3),
                            activeReportable-Minor (4),
                            activeReportable-Major (5),
                            activeReportable-Critical (6)
                           }

        ACCESS      read-only
        STATUS      mandatory
        DESCRIPTION
            "Unit Missing alarm status  with associated Severity"
        ::= { unitRecord 6 }

    unitNotRespondingAlarm  OBJECT-TYPE
        SYNTAX      INTEGER{
                            cleared (1),
                            activeReportable-Status (2),
                            activeReportable-Warning (3),
                            activeReportable-Minor (4),
                            activeReportable-Major (5),
                            activeReportable-Critical (6)

                           }

        ACCESS      read-only
        STATUS      mandatory
        DESCRIPTION
            "Unit Not Responding alarm status with associated Severity"
        ::= { unitRecord 7 }

    unitHwMismatchAlarm  OBJECT-TYPE
        SYNTAX      INTEGER{
                            cleared (1),
                            activeReportable-Status (2),
                            activeReportable-Warning (3),
                            activeReportable-Minor (4),
                            activeReportable-Major (5),
                            activeReportable-Critical (6)
                           }
        ACCESS      read-only
        STATUS      mandatory
        DESCRIPTION
            "Unit type Mismatch alarm status with associated Severity"
        ::= { unitRecord 8 }

    unitSwMismatchAlarm  OBJECT-TYPE
        SYNTAX      INTEGER{
                            cleared (1),
                            activeReportable-Status (2),
                            activeReportable-Warning (3),
                            activeReportable-Minor (4),
                            activeReportable-Major (5),
                            activeReportable-Critical (6)
                           }
        ACCESS      read-only
        STATUS      mandatory
        DESCRIPTION
            "Unit  with Sw Release  Mismatch alarm status with associated Severity"
        ::= { unitRecord 9 }

    unitHwEdition  OBJECT-TYPE
        SYNTAX      DisplayString (SIZE (0..20))
        ACCESS      read-only
        STATUS      mandatory
        DESCRIPTION
            "ASCII string used to identify Hw edition of the unit."
        ::= { unitRecord 10 }

    unitPartNumber  OBJECT-TYPE
        SYNTAX      DisplayString (SIZE (0..30))
        ACCESS      read-only
        STATUS      mandatory
        DESCRIPTION
            "ASCII string to identify the Part Number of the unit"
        ::= { unitRecord 11 }

    unitParentPartNumber  OBJECT-TYPE
        SYNTAX      DisplayString (SIZE (0..30))
        ACCESS      read-write
        STATUS      mandatory
        DESCRIPTION
            "ASCII string to identify the parent Part Number of the unit"
        ::= { unitRecord 12 }

    unitParentSerialNumber  OBJECT-TYPE
        SYNTAX      DisplayString (SIZE (0..30))
        ACCESS      read-write
        STATUS      mandatory
        DESCRIPTION
            "ASCII string to identify parent Serial Number of the unit"
        ::= { unitRecord 13 }



----------------------------------------------------------------------------------
--  The following objects define the profile of the unit alarms:
----------------------------------------------------------------------------------

    unitFailAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
        ACCESS      read-write
        STATUS      mandatory
        DESCRIPTION 
            "Define the severity associated to the Unit Fail Alarm and enable/disable 
             the trap generation on status change event."
        DEFVAL{ major-trapEnable }
        ::=  { unit 2 }

    unitMissingAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                       }
        ACCESS      read-write
        STATUS      mandatory
        DESCRIPTION 
            "Define the severity associated to the Unit Missing Alarm and enable/disable 
             the trap generation on status change event."
        DEFVAL{ major-trapEnable }
        ::=  { unit  3}

    unitNotRespondingAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the Unit Not Responding Alarm 
             and enable/disable the trap generation on status change event."
        DEFVAL{ major-trapEnable }
        ::=  { unit  4}

    unitHwMismatchAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the UnitHwMismatchAlarm Alarm 
             and  enable/disable the trap generation on status change event."
        DEFVAL{ major-trapEnable }
        ::=  { unit 5 }

    unitSwMismatchAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the Sw Release mismatch Alarm 
             and enable/disable the trap generation on status change event."
        DEFVAL{ major-trapEnable }
        ::=  { unit  6 }


----------------------------------------------------------------------------------
--  The Unit Group generates the following TRAP:
----------------------------------------------------------------------------------

    unitFailAlarmSet  TRAP-TYPE
        ENTERPRISE pdh-al 
        DESCRIPTION
            "This event is generated by NE when an Unit Fail Alarm is set
             The data passed with the event are
             1) UnitId
             2) UnitLabel
             3) UnitFailAlarm
             4) equipTrapAcknowledge code number"
        ::= 601

    unitFailAlarmCleared  TRAP-TYPE
        ENTERPRISE pdh-al 
        DESCRIPTION
            "This event is generated by NE when an Unit Fail Alarm is cleared
             The data passed with the event are
             1) UnitId
             2) UnitLabel
             3) UnitFailAlarm
             4) equipTrapAcknowledge code number"
        ::= 602

    unitMissingAlarmSet  TRAP-TYPE
        ENTERPRISE pdh-al 
        DESCRIPTION
            "This event is generated by NE when an Unit Missing Alarm is set
             The data passed with the event are
             1) UnitId
             2) UnitLabel
             3) UnitMissingAlarm
             4) equipTrapAcknowledge code number"
        ::= 603

    unitMissingAlarmCleared  TRAP-TYPE
        ENTERPRISE pdh-al 
        DESCRIPTION
            "This event is generated by NE when an Unit Missing Alarm is cleared
             The data passed with the event are
             1) UnitId
             2) UnitLabel
             3) UnitMissingAlarm
             4) equipTrapAcknowledge code number"
        ::= 604

    unitNotRespondingAlarmSet  TRAP-TYPE
        ENTERPRISE pdh-al 
        DESCRIPTION
            "This event is generated by NE when an Unit Not Responding Alarm is set
             The data passed with the event are
             1) UnitId
             2) UnitLabel
             3) UnitNotRespondingAlarm
             4) equipTrapAcknowledge code number"
        ::= 605

    unitNotRespondingAlarmCleared  TRAP-TYPE
        ENTERPRISE pdh-al 
        DESCRIPTION
            "This event is generated by NE when an Unit Not Responding Alarm  is cleared
             The data passed with the event are
             1) UnitId
             2) UnitLabel
             3) UnitNotRespondingAlarm
             4) equipTrapAcknowledge code number"
        ::= 606

    unitHwMismatchAlarmSet  TRAP-TYPE
        ENTERPRISE pdh-al 
        DESCRIPTION
            "This event is generated by NE when an Unit Hw Mismatch Alarm is set
             The data passed with the event are
             1) UnitId
             2) UnitLabel
             3) Unit HwMismatch Alarm
             4) equipTrapAcknowledge code number"
        ::= 607

    unitHwMismatchAlarmCleared  TRAP-TYPE
        ENTERPRISE pdh-al 
        DESCRIPTION
            "This event is generated by NE when an Unit Hw Mismatch Alarm is cleared
             The data passed with the event are
             1) UnitId
             2) UnitLabel
             3) Unit HwMismatchAlarm
             4) equipTrapAcknowledge code number"
        ::= 608

    unitSwMismatchAlarmSet  TRAP-TYPE
        ENTERPRISE pdh-al 
        DESCRIPTION
            "This event is generated by NE when an Unit Hw Mismatch Alarm is set
             The data passed with the event are
             1) UnitId
             2) UnitLabel
             3) Unit HwMismatch Alarm
             4) equipTrapAcknowledge code number"
        ::= 609

    unitSwMismatchAlarmCleared  TRAP-TYPE
        ENTERPRISE pdh-al 
        DESCRIPTION
            "This event is generated by NE when an Unit Hw Mismatch Alarm is cleared
             The data passed with the event are
             1) UnitId
             2) UnitLabel
             3) Unit HwMismatchAlarm
             4) equipTrapAcknowledge code number"
        ::= 610



--------------
--  4.8 Software Group
--  This group is used to manage the Sw present in the  equipment units.
--

    softwareEquipmentReleaseBench1   OBJECT-TYPE
        SYNTAX      DisplayString   (SIZE(0..15))
        ACCESS      read-only
        STATUS      mandatory
        DESCRIPTION
            "ASCII string identifying the equipment release present in Bench1"
        ::= { software 1 }

    softwareEquipmentReleaseBench1Status  OBJECT-TYPE
        SYNTAX      INTEGER{
                            notLoaded (1),
                            loaded   (2),
                            running (3)
                           }
        ACCESS      read-only
        STATUS      mandatory
        DESCRIPTION
            "Status of the bench 1 software"
        ::= { software 2 }

    softwareEquipmentReleaseBench2   OBJECT-TYPE
        SYNTAX      DisplayString   (SIZE(0..15))
        ACCESS      read-only
        STATUS      mandatory
        DESCRIPTION
            "ASCII string identifying the equipment release present in Bench2"
        ::= { software 3 }

    softwareEquipmentReleaseBench2Status  OBJECT-TYPE
        SYNTAX      INTEGER{
                            notLoaded (1),
                            loaded   (2),
                            running (3)
                           }
        ACCESS      read-only
        STATUS      mandatory
        DESCRIPTION
            "Status of the bench 2 software"
        ::= { software 4 }

    softwareIpAddressDwlServer  OBJECT-TYPE
        SYNTAX      IpAddress
        ACCESS      read-write
        STATUS      mandatory
        DESCRIPTION
            "Ip address of the remote element from which the Software is downloaded"
        ::= { software  5 }

    softwareGosipAddressDwlServer  OBJECT-TYPE
        SYNTAX      OCTET STRING    (SIZE(0..31))
        ACCESS      read-write
        STATUS      mandatory
        DESCRIPTION
            "GOSIP address of the remote element from which the Software is downloaded"
        ::= { software 6 }

    softwareDownloadfile   OBJECT-TYPE
        SYNTAX      DisplayString   (SIZE(0..255))
        ACCESS      read-write
        STATUS      mandatory
        DESCRIPTION
            "CEM or LOM Directory and name of the descriptor file. The files
             with the SW code must be present in the same directory"
        ::= { software 7 }

    softwareActionRequest   OBJECT-TYPE
        SYNTAX      INTEGER
        ACCESS      write-only
        STATUS      mandatory
        DESCRIPTION
            "This Integer is a bit string  with each bit when set has the following meaning:
             BIT 0   -    Download  request
             BIT 1   -    Abort Download  request
             BIT 2   -    Bench switch   request
             BIT 4   -    Partial download
             BIT 5   -    Forced Download 
             BIT 6   -    Implicit Activation
             The bit 4...6  enable/disable the different options on download request."
        ::= { software 8 }

    softwareDownloadStatus  OBJECT-TYPE
        SYNTAX      INTEGER{
                            downloading       (1),
                            completed         (2),
                            interrupted       (3),
                            perif-downloading (4)
                           }
        ACCESS      read-only
        STATUS      mandatory
        DESCRIPTION
            "Status of SW download operation"
        ::= { software 9 }

    softwareUnitTable  OBJECT-TYPE
        SYNTAX      SEQUENCE OF SoftwareUnitRecord
        ACCESS      not-accessible
        STATUS      mandatory
        DESCRIPTION
            "Table with Software records concerning units within the equipment"
        ::= { software 10 }

    softwareUnitRecord  OBJECT-TYPE
        SYNTAX      SoftwareUnitRecord
        ACCESS      not-accessible
        STATUS      mandatory
        DESCRIPTION
            "Software record"
        INDEX  { softwareUnitId, 
                 softwareElementId }
        ::= { softwareUnitTable 1 }

    SoftwareUnitRecord  ::=
        SEQUENCE{
            softwareUnitId                INTEGER,
            softwareElementId             INTEGER,
            softwareType                  INTEGER,
            softwareUnitReleaseBench1     DisplayString,
            softwareUnitReleaseBench2     DisplayString,
            softwareUnitActualRelease     DisplayString
        }

    softwareUnitId  OBJECT-TYPE
        SYNTAX      INTEGER 
        ACCESS      read-only
        STATUS      mandatory
        DESCRIPTION
            "This object is used as Index of the softwareUnit Table and also identifies
             the unit in the equipment."
        ::= { softwareUnitRecord 1 }

    softwareElementId  OBJECT-TYPE
        SYNTAX      INTEGER 
        ACCESS      read-only
        STATUS      mandatory
        DESCRIPTION
            "This object is used as Index of the softwareUnit Table and also identifies
             the SW programmable element in the specified unit."
        ::= { softwareUnitRecord 2 }

    softwareType  OBJECT-TYPE
        SYNTAX      INTEGER {
                              s-record    (1),
                              image-FPGA  (2),
                              volatile    (3)
                            }
        ACCESS      read-only
        STATUS      mandatory
        DESCRIPTION
            "Format type"
        ::= { softwareUnitRecord 3 }

    softwareUnitReleaseBench1   OBJECT-TYPE
        SYNTAX      DisplayString   (SIZE(0..8))
        ACCESS      read-only
        STATUS      mandatory
        DESCRIPTION
            "ASCII string identifying the software release present
             in the programmable element of specified unit bench 1."
        ::= { softwareUnitRecord 4 }

    softwareUnitReleaseBench2   OBJECT-TYPE
        SYNTAX      DisplayString   (SIZE(0..8))
        ACCESS      read-only
        STATUS      mandatory
        DESCRIPTION
            "ASCII string identifying the software release present
             in the programmable element of specified unit bench 2"
        ::= { softwareUnitRecord 5 }

    softwareUnitActualRelease   OBJECT-TYPE
        SYNTAX      DisplayString   (SIZE(0..33))
        ACCESS      read-only
        STATUS      mandatory
        DESCRIPTION
            "ASCII string identifying the software release actually present
             in the programmable element of specified unit"
        ::= { softwareUnitRecord 6 }

    softwareDownloadStatusTrapNotification OBJECT-TYPE
        SYNTAX      INTEGER {
                             trapDisable (1),
                             trapEnable (2),
                             trapEnableWithACK (34)
                            }
        ACCESS      read-write
        STATUS      mandatory
        DESCRIPTION
            "Enable/disable the trap generation on download status change."
        DEFVAL      { trapEnable }
        ::= { software 11 }


--
-- The Software Group generates the following TRAP:
--

    softwareDownloadStatusTrap  TRAP-TYPE
        ENTERPRISE pdh-al 
        DESCRIPTION
            "This event is generated by NE when the status of download is changed
             The data passed with the event are
             1) softwareDownloadStatus
             2) equipTrapAcknowledge code number"
        ::= 701



----------------------------------------------------------------------------------
--  4.9 RADIO EQUIPMENT GROUP
--  This group contains all the objects  that are specific of  the radio equipment.
----------------------------------------------------------------------------------

    radioEquipmentRadioConfig OBJECT-TYPE
        SYNTAX    INTEGER {
                           normal-1-0 (1),
                           hetero-1-1 (2),
                           iso-1-1    (3)
                          }
        ACCESS      read-write
        STATUS      mandatory
        DESCRIPTION 
            "The object describes the equipment  configuration for radio part:
             not protected
             protected hetero frequency
             protected iso frequency"
        ::=  { radioEquipment  1 }

    radioEquipmentBaseBandConfig OBJECT-TYPE
        SYNTAX    INTEGER {
                           notprotected-1-0 (1),
                           protected-1-1    (2)
                          }
        ACCESS      read-write
        STATUS      mandatory
        DESCRIPTION 
            "The object describes the equipment  configuration for Base Band part:
             not protected
             protected"
        ::=  { radioEquipment  2 }

    radioEquipmentCapacity OBJECT-TYPE
        SYNTAX    INTEGER {
                           pdh-2Mbit    (1),
                           pdh-2x2Mbit  (2),
                           pdh-4x2Mbit  (3),
                           pdh-8x2Mbit  (4),
                           pdh-16x2Mbit (5),
                           pdh-32x2Mbit (6),
                           pdh-34Mbit   (8)
                          }
        ACCESS      read-write
        STATUS      mandatory
        DESCRIPTION 
            "Radio equipment capacity: the update of this object causes the 
             update of the local and the remote radio equipment capacity"
        ::=  { radioEquipment  3}

    radioEquipmentLocalCapacity OBJECT-TYPE
        SYNTAX    INTEGER {
                           pdh-2Mbit    (1),
                           pdh-2x2Mbit  (2),
                           pdh-4x2Mbit  (3),
                           pdh-8x2Mbit  (4),
                           pdh-16x2Mbit (5),
                           pdh-32x2Mbit (6),
                           pdh-34Mbit   (8)
                          }
        ACCESS      read-write
        STATUS      mandatory
        DESCRIPTION 
            "Radio equipment capacity: the update of this object causes the 
            update of the local radio equipment capacity"
        ::=  { radioEquipment  4}

    radioEquipmentLinkId OBJECT-TYPE
        SYNTAX      INTEGER     (0..255)
        ACCESS      read-write
        STATUS      mandatory
        DESCRIPTION 
            "Link Identification (value 0..255)"
        ::=  { radioEquipment  5 }

    radioEquipmentLocalLinkId OBJECT-TYPE
        SYNTAX      INTEGER     (0..255)
        ACCESS      read-write
        STATUS      mandatory
        DESCRIPTION 
            "Link Identification (value 0..255) for local terminal"
        ::=  { radioEquipment 6 } 

    radioEquipmentRFLoopPresence OBJECT-TYPE
        SYNTAX      INTEGER
        ACCESS      read-only
        STATUS      mandatory
        DESCRIPTION
            "RF loop presence (0 = Present, 1 = Not present)"
        ::= { radioEquipment 7 }

    radioEquipmentGndRef  OBJECT-TYPE
        SYNTAX    INTEGER {
                            gnd    (1),
                            float  (2)
                          }
        ACCESS      read-write
        STATUS      mandatory
        DESCRIPTION 
            "Tributary  ports  ground reference"
        DEFVAL      { gnd }
        ::=  { radioEquipment  8 }

    radioEquipmentAisRxInsertion  OBJECT-TYPE
        SYNTAX    INTEGER {
                            disable (1),
                            enable  (2)
                          }
        ACCESS      read-write
        STATUS      mandatory
        DESCRIPTION 
            "AIS insertion receiver side enable"
        DEFVAL      { enable }
        ::=  { radioEquipment  9 }

    radioEquipmentServiceSquelchEnable  OBJECT-TYPE
        SYNTAX    INTEGER {
                            disable (1),
                            enable  (2)
                          }
        ACCESS      read-write
        STATUS      mandatory
        DESCRIPTION 
            "Service Squelch  enable"
        DEFVAL      { enable }
        ::=  { radioEquipment  10 }

    radioEquipmentTxPwrThresh  OBJECT-TYPE
        SYNTAX      INTEGER       (3..15)
        ACCESS      read-write
        STATUS      mandatory
        DESCRIPTION
            "Threshold (value +3 to +15 dB) relative to nominal value of the TX 
             power below wich the related alarm is set."
        DEFVAL  { 3 }
        ::=  { radioEquipment  11}

    radioEquipmentRxPwrThresh  OBJECT-TYPE
        SYNTAX      INTEGER     (-99..-40)
        ACCESS      read-write
        STATUS      mandatory
        DESCRIPTION 
            "Threshold (value -40 to -99 dBm) for RX power below wich the related 
             alarm is set."
        DEFVAL  {-80}
        ::=  { radioEquipment  12}

    radioEquipmentEarlyWarningThresh  OBJECT-TYPE
        SYNTAX      INTEGER {
                            e-9  (-9),
                            e-10 (-10),
                            e-11 (-11),
                            e-12 (-12)
                          }
        ACCESS      read-write
        STATUS      mandatory
        DESCRIPTION
            "Threshold for Early Warning Alarm"
        DEFVAL      { e-9 }
        ::={ radioEquipment 13 }

    radioEquipmentLberThresh  OBJECT-TYPE
        SYNTAX    INTEGER {
                            e-6  (1),
                            e-7  (2),
                            e-8  (3)
                          }
        ACCESS      read-write
        STATUS      mandatory
        DESCRIPTION 
            "Threshold for LBER alarm"
        DEFVAL      { e-6 }
        ::=  { radioEquipment  14 }

    radioEquipmentHberThresh  OBJECT-TYPE
        SYNTAX    INTEGER {
                            e-3  (1),
                            e-4  (2),
                            e-5  (3)
                          }
        ACCESS      read-write
        STATUS      mandatory
        DESCRIPTION 
            "Threshold for HBER alarm"
        DEFVAL      { e-3 }
        ::=  { radioEquipment  15}

    radioEquipmentHberAisInsRxSw  OBJECT-TYPE
        SYNTAX    INTEGER {
                            disable (1),
                            enable  (2)
                          }
        ACCESS      read-write
        STATUS      mandatory
        DESCRIPTION 
            "Enable HBER alarm as switching criterion (1+1 configuration) and for RX AIS insertion"
        DEFVAL      { enable }
        ::=  { radioEquipment  16}

    radioEquipmentLberRxSw  OBJECT-TYPE
        SYNTAX    INTEGER {
                            disable (1),
                            enable  (2)
                          }
        ACCESS      read-write
        STATUS      mandatory
        DESCRIPTION 
            "Enable LBER alarm as switching criterion (1+1 configuration)."
        DEFVAL      { enable }
        ::=  { radioEquipment  17}

    radioEquipmentEarlyWarningRxSw  OBJECT-TYPE
        SYNTAX    INTEGER {
                            disable (1),
                            enable  (2)
                          }
        ACCESS      read-write
        STATUS      mandatory
        DESCRIPTION 
            "Enable EarlyWarning  alarm as switching criterion (1+1 configuration).  "  
        DEFVAL      { enable }
        ::=  { radioEquipment 18 }

    radioEquipmentCrcPulseRxSw  OBJECT-TYPE
        SYNTAX    INTEGER {
                            disable (1),
                            enable  (2)
                          }
        ACCESS      read-write
        STATUS      mandatory
        DESCRIPTION 
            "Enable the CRC errors reported by the FEC as switching criterion
             (1+1 configuration)"
        DEFVAL      { enable }
        ::=  { radioEquipment  19}

    radioEquipmentModulationType  OBJECT-TYPE
        SYNTAX    INTEGER {
                            qAM4   (1),
                            qAM16  (2)
                          }
        ACCESS      read-write
        STATUS      mandatory
        DESCRIPTION 
            "Modulation type: 4QAM or 16 QAM  " 
        DEFVAL      { qAM4 }
        ::=  { radioEquipment  20}

    radioEquipmentRxForcedSwitch  OBJECT-TYPE
        SYNTAX      INTEGER{
                              auto (1),
                              branch-1 (2),
                              branch-2 (3)
                           }
        ACCESS      read-write
        STATUS      mandatory
        DESCRIPTION
            "Receiver Forced switch enable (only if 1+1 configuration)"
        DEFVAL      { auto }
        ::= { radioEquipment 21 }

    radioEquipmentTxForcedSwitch  OBJECT-TYPE
        SYNTAX      INTEGER{
                              auto (1),
                              branch-1 (2),
                              branch-2 (3)
                           }
        ACCESS      read-write
        STATUS      mandatory
        DESCRIPTION
            "Transmitter Forced switch enable (only if 1+1 configuration and ISO system)"
        DEFVAL      { auto }
        ::= { radioEquipment 22 }

    radioEquipmentRxRevertiveSwitch  OBJECT-TYPE
        SYNTAX      INTEGER{
                              auto (1),
                              branch-1 (2),
                              branch-2 (3)
                           }
        ACCESS      read-write
        STATUS      mandatory
        DESCRIPTION
            "Receiver Revertive switch enable (only if Radio 1+1 configuration)"
        DEFVAL      { auto }
        ::= { radioEquipment 23 }

    radioEquipmentTxRevertiveSwitch  OBJECT-TYPE
        SYNTAX      INTEGER{
                              auto (1),
                              branch-1 (2),
                              branch-2 (3)
                           }
        ACCESS      read-write
        STATUS      mandatory
        DESCRIPTION
            "Transmitter revertive switch enable (only if 1+1 Iso-Frequency configuration)"
    DEFVAL      { auto }
    ::= { radioEquipment 24 }

    radioEquipmentBaseBandForcedSwitch  OBJECT-TYPE
        SYNTAX      INTEGER{
                              auto (1),
                              baseBand-1 (2),
                              baseBand-2 (3)
                           }
        ACCESS      read-write
        STATUS      mandatory
        DESCRIPTION
            "Base Band  Forced switch enable (only if Base Band 1+1 configuration)"
        DEFVAL      { auto }
        ::= { radioEquipment 25 }

    radioEquipmentBaseBand1ActiveStatus OBJECT-TYPE
        SYNTAX    INTEGER {
                            cleared (1),
                            active (2)
                          }
        ACCESS      read-only
        STATUS      mandatory
        DESCRIPTION 
            "Base Band 1 Active    status with associated Severity 
             (meaningfull in Base Band protected configuration)"
        ::=  { radioEquipment  26 }

    radioEquipmentBaseBand2ActiveStatus OBJECT-TYPE
        SYNTAX    INTEGER {
                            cleared (1),
                            active (2)
                          }
        ACCESS      read-only
        STATUS      mandatory
        DESCRIPTION 
            "Base Band 2 Active    status with associated Severity 
             (meaningfull in Base Band protected configuration)"
        ::=  { radioEquipment  27 }


    radioEquipmentPeripheralLom  OBJECT-TYPE
        SYNTAX    INTEGER {
                            disable           (1),
                            enableBaseBand    (2),
                            enableRadio1      (3),
                            enableRadio2      (4),
                            enableBB-Reserve  (5),
                            enableService-A   (6),
                            enableService-B   (7)
                          }
        ACCESS      read-write
        STATUS      mandatory
        DESCRIPTION
          "Peripheral LOM Enable. If enable the  LOM is connected to the Base Band
           or to the Radio microcontrollers"
        DEFVAL      { disable }
        ::= { radioEquipment 28 }

    radioEquipmentRemoteTxSwitchControl  OBJECT-TYPE
        SYNTAX    INTEGER {
                            disable  (1),
                            enable   (2)
                          }
        ACCESS      read-write
        STATUS      mandatory
        DESCRIPTION 
            "It enables the Tx switch from remote equipment" 
        DEFVAL      { enable }
        ::=  { radioEquipment  29}

    radioEquipmentRemoteAccessType    OBJECT-TYPE
        SYNTAX    INTEGER {
                            serialrs232         (1),
                            dueMbit-pcm-TSn	(2)
                          }
        ACCESS      read-write
        STATUS      mandatory
        DESCRIPTION 
            "Define the remote access interface:
             - RS232 serial interface
             - 2Mbit-PCM time slot. "
        DEFVAL      { 1 }
        ::=  { radioEquipment  30 }

    radioEquipmentPppMap   OBJECT-TYPE
        SYNTAX      OCTET STRING (SIZE(4))
        ACCESS      read-write
        STATUS      mandatory
        DESCRIPTION 
            "Bit map to define the timeslots (0..31) used in PCM frame by  PPP.
             The bit 0 (LSB) corresponds to the timeslot 0"
        ::=  { radioEquipment 31 }

    radioEquipmentLinkIdAlarm  OBJECT-TYPE
        SYNTAX    INTEGER {
                            cleared                    (1),
                            activeReportable-Status    (2),
                            activeReportable-Warning   (3),
                            activeReportable-Minor     (4),
                            activeReportable-Major     (5),
                            activeReportable-Critical  (6)
                          }
        ACCESS      read-only
        STATUS      mandatory
        DESCRIPTION 
            "Link Identification Alarm  with associated Severity"
        ::=  { radioEquipment  32}

    radioEquipmentLinkTelemetryFailAlarm  OBJECT-TYPE
        SYNTAX    INTEGER {
                            cleared                    (1),
                            activeReportable-Status    (2),
                            activeReportable-Warning   (3),
                            activeReportable-Minor     (4),
                            activeReportable-Major     (5),
                            activeReportable-Critical  (6)
                          }
        ACCESS      read-only
        STATUS      mandatory
        DESCRIPTION 
            "Fail of link telemetry communication channel with associated Severity"
        ::=  { radioEquipment  33}

    radioEquipmentRxAisAlarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "Ais insertion on all RX tributary signal  with associated Severity"
        ::=  { radioEquipment  34}

    radioEquipmentDemultiplexerFailAlarm  OBJECT-TYPE
        SYNTAX    INTEGER {
                            cleared                    (1),
                            activeReportable-Status    (2),
                            activeReportable-Warning   (3),
                            activeReportable-Minor     (4),
                            activeReportable-Major     (5),
                            activeReportable-Critical  (6)
                          }
        ACCESS      read-only
        STATUS      mandatory
        DESCRIPTION 
            "Fail of Demultiplexer  with associated Severity"  
        ::=  { radioEquipment  35 }

    radioEquipmentMultiplexerFailAlarm  OBJECT-TYPE
        SYNTAX    INTEGER {
                            cleared                    (1),
                            activeReportable-Status    (2),
                            activeReportable-Warning   (3),
                            activeReportable-Minor     (4),
                            activeReportable-Major     (5),
                            activeReportable-Critical  (6)
                          }
        ACCESS      read-only
        STATUS      mandatory
        DESCRIPTION 
            "Fail of Multiplexer  with associated Severity"  
        ::=  { radioEquipment  36 }

    radioEquipmentLocalLimMainAlarmSynthesis  OBJECT-TYPE
        SYNTAX    INTEGER {
                            cleared                    (1),
                            activeReportable-Status    (2),
                            activeReportable-Warning   (3),
                            activeReportable-Minor     (4),
                            activeReportable-Major     (5),
                            activeReportable-Critical  (6)
                          }
        ACCESS      read-only
        STATUS      mandatory
        DESCRIPTION 
            "Synthesis of the local LIM main alarms"  
        ::=  { radioEquipment  37 }


    radioEquipmentRemoteLimMainAlarmSynthesis  OBJECT-TYPE
        SYNTAX    INTEGER {
                            cleared                    (1),
                            activeReportable-Status    (2),
                            activeReportable-Warning   (3),
                            activeReportable-Minor     (4),
                            activeReportable-Major     (5),
                            activeReportable-Critical  (6)
                          }
        ACCESS      read-only
        STATUS      mandatory
        DESCRIPTION 
            "Synthesis of the remote LIM main alarms"  
        ::=  { radioEquipment  38 }

    radioEquipmentLocalLimReserveAlarmSynthesis  OBJECT-TYPE
        SYNTAX    INTEGER {
                            cleared                    (1),
                            activeReportable-Status    (2),
                            activeReportable-Warning   (3),
                            activeReportable-Minor     (4),
                            activeReportable-Major     (5),
                            activeReportable-Critical  (6)
                          }
        ACCESS      read-only
        STATUS      mandatory
        DESCRIPTION 
            "Synthesis of the local LIM Reserve alarms"  
        ::=  { radioEquipment  39 }

    radioEquipmentRemoteLimReserveAlarmSynthesis  OBJECT-TYPE
        SYNTAX    INTEGER {
                            cleared                    (1),
                            activeReportable-Status    (2),
                            activeReportable-Warning   (3),
                            activeReportable-Minor     (4),
                            activeReportable-Major     (5),
                            activeReportable-Critical  (6)
                          }
        ACCESS      read-only
        STATUS      mandatory
        DESCRIPTION 
            "Synthesis of the remote LIM reserve alarms"  
        ::=  { radioEquipment  40 }

    radioEquipmentRemoteEquipmentControllerAlarm  OBJECT-TYPE
        SYNTAX    INTEGER {
                            cleared                    (1),
                            activeReportable-Status    (2),
                            activeReportable-Warning   (3),
                            activeReportable-Minor     (4),
                            activeReportable-Major     (5),
                            activeReportable-Critical  (6)
                          }
        ACCESS      read-only
        STATUS      mandatory
        DESCRIPTION 
            "It reports at the local terminal the fault of the remote equipment 
             controller"  
        ::=  { radioEquipment  41 }

    radioEquipmentRemoteSplitterAlarm  OBJECT-TYPE
        SYNTAX    INTEGER {
                            cleared                    (1),
                            activeReportable-Status    (2),
                            activeReportable-Warning   (3),
                            activeReportable-Minor     (4),
                            activeReportable-Major     (5),
                            activeReportable-Critical  (6)
                          }
        ACCESS      read-only
        STATUS      mandatory
        DESCRIPTION 
            "It reports to "  
        ::=  { radioEquipment  42 }

    radioEquipmentLinkIdAlarmSeverityCode  OBJECT-TYPE
        SYNTAX    INTEGER {
                            disable                       (1),
                            status-trapEnable             (2),
                            status-trapEnableWithACK      (34),
                            warning-trapEnable            (3),
                            warning-trapEnableWithACK     (35),
                            minor-trapEnable              (4),
                            minor-trapEnableWithACK       (36),
                            major-trapEnable              (5),
                            major-trapEnableWithACK       (37),
                            critical-trapEnable           (6),
                            critical-trapEnableWithACK    (38),
                            status-trapDisable            (18),
                            warning-trapDisable           (19),
                            minor-trapDisable             (20),
                            major-trapDisable             (21),
                            critical-trapDisable          (22)
                          }
        ACCESS      read-write
        STATUS      mandatory
        DESCRIPTION 
            "Define the severity associated to theLink Id Fail Alarm 
             and  enable/disable the trap generation on status change event."
        DEFVAL{ major-trapEnable }
        ::=  { radioEquipment 43 }

    radioEquipmentLinkTelemetryFailAlarmSeverityCode  OBJECT-TYPE
        SYNTAX    INTEGER {
                            disable                       (1),
                            status-trapEnable             (2),
                            status-trapEnableWithACK      (34),
                            warning-trapEnable            (3),
                            warning-trapEnableWithACK     (35),
                            minor-trapEnable              (4),
                            minor-trapEnableWithACK       (36),
                            major-trapEnable              (5),
                            major-trapEnableWithACK       (37),
                            critical-trapEnable           (6),
                            critical-trapEnableWithACK    (38),
                            status-trapDisable            (18),
                            warning-trapDisable           (19),
                            minor-trapDisable             (20),
                            major-trapDisable             (21),
                            critical-trapDisable          (22)
                          }
        ACCESS      read-write
        STATUS      mandatory
        DESCRIPTION 
            "Define the severity associated to the LinkTelemetryFailAlarm 
             and  enable/disable the trap generation on status change event."
        DEFVAL{ major-trapEnable }
        ::=  { radioEquipment 44 }

    radioEquipmentAisAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the  RxAIsAlarm  and  
             enable/disable the trap generation on status change event."
        DEFVAL{ warning-trapEnable }
        ::=  { radioEquipment  45 }

    radioEquipmentDemultiplexerFailAlarmSeverityCode  OBJECT-TYPE
        SYNTAX    INTEGER {
                            disable                       (1),
                            status-trapEnable             (2),
                            status-trapEnableWithACK      (34),
                            warning-trapEnable            (3),
                            warning-trapEnableWithACK     (35),
                            minor-trapEnable              (4),
                            minor-trapEnableWithACK       (36),
                            major-trapEnable              (5),
                            major-trapEnableWithACK       (37),
                            critical-trapEnable           (6),
                            critical-trapEnableWithACK    (38),
                            status-trapDisable            (18),
                            warning-trapDisable           (19),
                            minor-trapDisable             (20),
                            major-trapDisable             (21),
                            critical-trapDisable          (22)
                          }
        ACCESS      read-write
        STATUS      mandatory
        DESCRIPTION 
            "Define the severity associated to the DemultiplexerFailAlarm  and  
             enable/disable the trap generation on status change event."  
        DEFVAL{ major-trapEnable }
        ::=  { radioEquipment 46 }

    radioEquipmentMultiplexerFailAlarmSeverityCode  OBJECT-TYPE
        SYNTAX    INTEGER {
                            disable                       (1),
                            status-trapEnable             (2),
                            status-trapEnableWithACK      (34),
                            warning-trapEnable            (3),
                            warning-trapEnableWithACK     (35),
                            minor-trapEnable              (4),
                            minor-trapEnableWithACK       (36),
                            major-trapEnable              (5),
                            major-trapEnableWithACK       (37),
                            critical-trapEnable           (6),
                            critical-trapEnableWithACK    (38),
                            status-trapDisable            (18),
                            warning-trapDisable           (19),
                            minor-trapDisable             (20),
                            major-trapDisable             (21),
                            critical-trapDisable          (22)
                          }
        ACCESS      read-write
        STATUS      mandatory
        DESCRIPTION 
            "Define the severity associated to the MultiplexerFailAlarm  and  
             enable/disable the trap generation on status change event."  
        DEFVAL{ major-trapEnable }
        ::=  { radioEquipment 47 }

    radioEquipmentLocalLimAlarmSynthesisSeverityCode  OBJECT-TYPE
        SYNTAX    INTEGER {
                            disable                       (1),
                            status-trapEnable             (2),
                            status-trapEnableWithACK      (34),
                            warning-trapEnable            (3),
                            warning-trapEnableWithACK     (35),
                            minor-trapEnable              (4),
                            minor-trapEnableWithACK       (36),
                            major-trapEnable              (5),
                            major-trapEnableWithACK       (37),
                            critical-trapEnable           (6),
                            critical-trapEnableWithACK    (38),
                            status-trapDisable            (18),
                            warning-trapDisable           (19),
                            minor-trapDisable             (20),
                            major-trapDisable             (21),
                            critical-trapDisable          (22)
                          }
        ACCESS      read-write
        STATUS      mandatory
        DESCRIPTION 
           "Define the severity associated to the LocalLimMainAlarmSynthesis
            and to the LocalLimReserveAlarmSynthesis 
            and enable/disable the trap generation on status change event."  
        DEFVAL{ major-trapEnable }
        ::=  { radioEquipment 48 }

    radioEquipmentRemoteLimAlarmSynthesisSeverityCode  OBJECT-TYPE
        SYNTAX    INTEGER {
                            disable                       (1),
                            status-trapEnable             (2),
                            status-trapEnableWithACK      (34),
                            warning-trapEnable            (3),
                            warning-trapEnableWithACK     (35),
                            minor-trapEnable              (4),
                            minor-trapEnableWithACK       (36),
                            major-trapEnable              (5),
                            major-trapEnableWithACK       (37),
                            critical-trapEnable           (6),
                            critical-trapEnableWithACK    (38),
                            status-trapDisable            (18),
                            warning-trapDisable           (19),
                            minor-trapDisable             (20),
                            major-trapDisable             (21),
                            critical-trapDisable          (22)
                          }
        ACCESS      read-write
        STATUS      mandatory
        DESCRIPTION 
           "Define the severity associated to the remoteLimMainAlarmSynthesis
            and to the RemoteLimReserveAlarmSynthesis 
            and enable/disable the trap generation on status change event."  
        DEFVAL{ warning-trapEnable }
        ::=  { radioEquipment 49 }

    radioEquipmentBaseBandActiveStatusSeverityCode  OBJECT-TYPE
        SYNTAX    INTEGER {
                            trapDisable (1),
                            trapEnable (2),
                            trapEnableWithACK (34)
                          }
        ACCESS      read-write
        STATUS      mandatory
        DESCRIPTION 
            "Define the severity associated to the 
             radioEquipmentBaseBandActivestatus  and  enable/disable the trap 
             generation  on status change   event."
        DEFVAL{ trapEnable }
        ::=  { radioEquipment  50 }

    radioEquipmentRemoteEquipmentControllerAlarmSeverityCode  OBJECT-TYPE
        SYNTAX    INTEGER {
                            disable                       (1),
                            status-trapEnable             (2),
                            status-trapEnableWithACK      (34),
                            warning-trapEnable            (3),
                            warning-trapEnableWithACK     (35),
                            minor-trapEnable              (4),
                            minor-trapEnableWithACK       (36),
                            major-trapEnable              (5),
                            major-trapEnableWithACK       (37),
                            critical-trapEnable           (6),
                            critical-trapEnableWithACK    (38),
                            status-trapDisable            (18),
                            warning-trapDisable           (19),
                            minor-trapDisable             (20),
                            major-trapDisable             (21),
                            critical-trapDisable          (22)
                          }
        ACCESS      read-write
        STATUS      mandatory
        DESCRIPTION 
           "Define the severity associated to the remoteEquipmentControllerAlarm
            and enable/disable the trap generation on status change event."  
        DEFVAL{ warning-trapEnable }
        ::=  { radioEquipment 51 }

    radioEquipmentRemoteSplitterAlarmSeverityCode  OBJECT-TYPE
        SYNTAX    INTEGER {
                            disable                       (1),
                            status-trapEnable             (2),
                            status-trapEnableWithACK      (34),
                            warning-trapEnable            (3),
                            warning-trapEnableWithACK     (35),
                            minor-trapEnable              (4),
                            minor-trapEnableWithACK       (36),
                            major-trapEnable              (5),
                            major-trapEnableWithACK       (37),
                            critical-trapEnable           (6),
                            critical-trapEnableWithACK    (38),
                            status-trapDisable            (18),
                            warning-trapDisable           (19),
                            minor-trapDisable             (20),
                            major-trapDisable             (21),
                            critical-trapDisable          (22)
                          }
        ACCESS      read-write
        STATUS      mandatory
        DESCRIPTION 
           "Define the severity associated to the remoteSplitterAlarm 
            and enable/disable the trap generation on status change event."  
        DEFVAL      { warning-trapEnable }
        ::=  { radioEquipment 52 }

    radioEquipment16KbitPppMap    OBJECT-TYPE
        SYNTAX      INTEGER      (0..15)
        ACCESS      read-write
        STATUS      mandatory
        DESCRIPTION 
            "Bit map to define the 16Kb/s channels (1...4) within the 64Kbit Time 
           Slot selected by radioEquipmentPppMap (valid only from TS1 to TS31)
           The bit 0 (LSB) correspond to the channel 1 "
        DEFVAL      { 1 }
        ::=  { radioEquipment 53 }

    radioEquipment2MbPppMap    OBJECT-TYPE
        SYNTAX      INTEGER    
        ACCESS      read-write
        STATUS      mandatory
        DESCRIPTION 
            "object to define the 2Mb tributary used to carry EOC 
             zero means no 2Mb used"
        DEFVAL      { 0 }
        ::=  { radioEquipment 54 }

    radioEquipmentPppRadioLinkAlarm  OBJECT-TYPE
        SYNTAX    INTEGER {
                            cleared                    (1),
                            activeReportable-Status    (2),
                            activeReportable-Warning   (3),
                            activeReportable-Minor     (4),
                            activeReportable-Major     (5),
                            activeReportable-Critical  (6)
                          }
        ACCESS      read-only
        STATUS      mandatory
        DESCRIPTION 
            "Fail of PPP Radio link communication channel with associated Severity"
        ::=  { radioEquipment  55}

    radioEquipmentPppRadioLinkAlarmSeverityCode  OBJECT-TYPE
        SYNTAX    INTEGER {
                            disable                       (1),
                            status-trapEnable             (2),
                            status-trapEnableWithACK      (34),
                            warning-trapEnable            (3),
                            warning-trapEnableWithACK     (35),
                            minor-trapEnable              (4),
                            minor-trapEnableWithACK       (36),
                            major-trapEnable              (5),
                            major-trapEnableWithACK       (37),
                            critical-trapEnable           (6),
                            critical-trapEnableWithACK    (38),
                            status-trapDisable            (18),
                            warning-trapDisable           (19),
                            minor-trapDisable             (20),
                            major-trapDisable             (21),
                            critical-trapDisable          (22)
                          }
        ACCESS      read-write
        STATUS      mandatory
        DESCRIPTION 
           "Define the severity associated to the PppRadioLinkAlarm 
            and enable/disable the trap generation on status change event."  
        DEFVAL      { major-trapEnable }
        ::=  { radioEquipment 56 }

    radioEquipmentPrbsStart  OBJECT-TYPE
        SYNTAX    INTEGER {
                            start-reset                   (1),
                            stop                          (2)
                          }
        ACCESS      read-write
        STATUS      mandatory
        DESCRIPTION 
            "Stop, Start (resetting errors and counters) the pattern"  
        DEFVAL  { stop }
        ::= { radioEquipment 57 }

    radioEquipmentPrbsCheckedSignal  OBJECT-TYPE
        SYNTAX    INTEGER {
                            signal-2Mb                    (1),
                            signal-64Kb-extA              (2),
                            signal-64Kb-extB               (3)
                          }
        ACCESS    read-write
        STATUS    mandatory
        DESCRIPTION 
            "The signal checked by the pattern"  
        DEFVAL{ signal-64Kb-extA }
        ::= { radioEquipment 58 }

    radioEquipmentPrbs2MbSelection    OBJECT-TYPE
        SYNTAX      INTEGER    (1..16)
        ACCESS      read-write
        STATUS      mandatory
        DESCRIPTION 
            "Select the 2Mb/s signal to be checked"
        DEFVAL  { 1 }
        ::= { radioEquipment 59 }

    radioEquipmentPrbsTestPattern  OBJECT-TYPE
        SYNTAX      INTEGER {
                              base2exp23                  (0),
                              base2exp15                  (1),
                              fixed-word                  (3)
                            }
        ACCESS      read-write
        STATUS      mandatory
        DESCRIPTION 
            "The test patter used by Prbs"  
        DEFVAL{ base2exp23 }
        ::=  { radioEquipment 60 }

    radioEquipmentPrbsErrorCounter  OBJECT-TYPE
        SYNTAX      Counter
        ACCESS      read-only
        STATUS      mandatory
        DESCRIPTION 
            "PRBS Error counter"
        ::= { radioEquipment 61 }

    radioEquipmentPrbsFailAlarm    OBJECT-TYPE
        SYNTAX    INTEGER {
                           cleared                   (1),
                           activeReportable-Status   (2),
                           activeReportable-Warning  (3),
                           activeReportable-Minor    (4),
                           activeReportable-Major    (5),
                           activeReportable-Critical (6)
                       }
        ACCESS      read-only
        STATUS      mandatory
        DESCRIPTION 
            "Prbs alarm"
        ::= { radioEquipment 62 }

    radioEquipmentPrbsFailAlarmSeverityCode  OBJECT-TYPE
        SYNTAX      INTEGER {
                              disable (1),
                              status-trapEnable (2),
                              status-trapEnableWithACK (34),
                              warning-trapEnable (3),
                              warning-trapEnableWithACK (35),
                              minor-trapEnable (4),
                              minor-trapEnableWithACK (36),
                              major-trapEnable (5),
                              major-trapEnableWithACK (37),
                              critical-trapEnable (6),
                              critical-trapEnableWithACK (38),
                              status-trapDisable (18),
                              warning-trapDisable (19),
                              minor-trapDisable (20),
                              major-trapDisable (21),
                              critical-trapDisable (22)
                            }
        ACCESS      read-write
        STATUS      mandatory
        DESCRIPTION 
            "Define the severity associated to the PrbsFailAlarm 
             and enable/disable the trap generation on status change event."  
        DEFVAL  { warning-trapEnable }
        ::= { radioEquipment 63 }


    radioEquipment2MbG826    OBJECT-TYPE
        SYNTAX      INTEGER    
        ACCESS      read-write
        STATUS      mandatory
        DESCRIPTION 
            "object to define the 2Mb tributary used to performs the G826 
             meaningfull only if 'radioEquipment2MbPppPap' is zero"
        DEFVAL      { 1 }
        ::=  { radioEquipment 64 }




----------------------------------------------------------------------------------
--  The Radio Equipment group generates the following TRAPs:
----------------------------------------------------------------------------------

    radioEquipmentLinkIdAlarmSet   TRAP-TYPE
        ENTERPRISE pdh-al 
        DESCRIPTION
            "This event is generated by  NE when an 
              radioEquipmentLinkIdAlarm is set
             1) radioEquipmentLinkIdAlarm
             2) equipTrapAcknowledge code number"
        ::= 801

    radioEquipmentLinkIdAlarmCleared   TRAP-TYPE
        ENTERPRISE pdh-al 
        DESCRIPTION
            "This event is generated by  NE when a RadioEquipmentLinkIdAlarm 
             is cleared
             1) radioEquipmentLinkIdAlarm
             2) equipTrapAcknowledge code number"
        ::= 802

    radioEquipmentLinkTelemetryFailAlarmSet   TRAP-TYPE
        ENTERPRISE pdh-al 
        DESCRIPTION
            "This event is generated by  NE when an 
             radioEquipmentLinkTelemetryFailAlarm is set
             1) radioEquipmentLinkTelemetryFailAlarm
             2) equipTrapAcknowledge code number"
        ::= 803

    radioEquipmentLinkTelemetryFailAlarmCleared   TRAP-TYPE
        ENTERPRISE pdh-al 
        DESCRIPTION
            "This event is generated by  NE when an 
             radioEquipmentLinkTelemetryFailAlarm is cleared
             1) radioEquipmentLinkTelemetryFailAlarm
             2) equipTrapAcknowledge code number"
        ::= 804

    radioEquipmentDemultiplexerFailAlarmSet   TRAP-TYPE
        ENTERPRISE pdh-al 
        DESCRIPTION
            "This event is generated by  NE when an 
             radioEquipmentDemultiplexerFailAlarm  is set
             1) radioEquipmentDemultiplexerFailAlarm   
             2) equipTrapAcknowledge code number"
        ::= 805

    radioEquipmentDemultiplexerFailAlarmCleared   TRAP-TYPE
        ENTERPRISE pdh-al 
        DESCRIPTION
            "This event is generated by  NE when an 
             radioEquipmentDemultiplexerFailAlarm  is cleared
             1) radioEquipmentDemultiplexerFailAlarm   
             2) equipTrapAcknowledge code number"
        ::= 806

    radioEquipmentMultiplexerFailAlarmSet   TRAP-TYPE
        ENTERPRISE pdh-al 
        DESCRIPTION
            "This event is generated by  NE when an 
             radioEquipmentMultiplexerFailAlarm  is set
             1) radioEquipmentMultiplexerFailAlarm   
             2) equipTrapAcknowledge code number"
        ::= 807

    radioEquipmentMultiplexerFailAlarmCleared   TRAP-TYPE
        ENTERPRISE pdh-al 
        DESCRIPTION
            "This event is generated by  NE when an 
             radioEquipmentMultiplexerFailAlarm  is cleared
             1) radioEquipmentDemultiplexerFailAlarm   
             2) equipTrapAcknowledge code number"
        ::= 808

    radioEquipmentAisAlarmSet   TRAP-TYPE
        ENTERPRISE pdh-al 
        DESCRIPTION
            "This event is generated by  NE when an 
              radioEquipmentAisAlarm is set
             1) radioEquipmentAisAlarm
             2) equipTrapAcknowledge code number"
        ::= 809

    radioEquipmentAisAlarmCleared   TRAP-TYPE
        ENTERPRISE pdh-al 
        DESCRIPTION
            "This event is generated by  NE when an 
              radioEquipmentAisAlarm is cleared
             1) radioEquipmentAisAlarm
             2) equipTrapAcknowledge code number"
        ::= 810

    radioEquipmentLocalLimMainAlarmSynthesisSet   TRAP-TYPE
        ENTERPRISE pdh-al 
        DESCRIPTION
            "This event is generated by  NE when an 
              radioEquipmentLocalLimMainAlarmSynthesis is set
             1) radioEquipmentLocalLimMainAlarmSynthesis
             2) equipTrapAcknowledge code number"
        ::= 811

    radioEquipmentLocalLimMainAlarmSynthesisCleared   TRAP-TYPE
        ENTERPRISE pdh-al 
        DESCRIPTION
            "This event is generated by  NE when an 
              radioEquipmentLocalLimMainAlarmSynthesis is cleared
             1) radioEquipmentLocalLimMainAlarmSynthesis
             2) equipTrapAcknowledge code number"
        ::= 812

    radioEquipmentRemoteLimMainAlarmSynthesisSet   TRAP-TYPE
        ENTERPRISE pdh-al 
        DESCRIPTION
            "This event is generated by  NE when an 
              radioEquipmentRemoteLimMainAlarmSynthesis is set
             1) radioEquipmentRemoteLimMainAlarmSynthesis
             2) equipTrapAcknowledge code number"
        ::= 813

    radioEquipmentRemoteLimMainAlarmSynthesisCleared   TRAP-TYPE
        ENTERPRISE pdh-al 
        DESCRIPTION
            "This event is generated by  NE when an 
              radioEquipmentRemoteLimMainAlarmSynthesis is cleared
             1) radioEquipmentRemoteLimMainAlarmSynthesis
             2) equipTrapAcknowledge code number"
        ::= 814

    radioEquipmentLocalLimReserveAlarmSynthesisSet   TRAP-TYPE
        ENTERPRISE pdh-al 
        DESCRIPTION
            "This event is generated by  NE when an 
              radioEquipmentLocalLimReserveAlarmSynthesis is set
             1) radioEquipmentLocalLimReserveAlarmSynthesis
             2) equipTrapAcknowledge code number"
        ::= 815

    radioEquipmentLocalLimReserveAlarmSynthesisCleared   TRAP-TYPE
        ENTERPRISE pdh-al 
        DESCRIPTION
            "This event is generated by  NE when an 
              radioEquipmentLocalLimReserveAlarmSynthesis is cleared
             1) radioEquipmentLocalLimReserveAlarmSynthesis
             2) equipTrapAcknowledge code number"
        ::= 816

    radioEquipmentRemoteLimReserveAlarmSynthesisSet   TRAP-TYPE
        ENTERPRISE pdh-al 
        DESCRIPTION
            "This event is generated by  NE when an 
              radioEquipmentRemoteLimReserveAlarmSynthesis is set
             1) radioEquipmentRemoteLimReserveAlarmSynthesis
             2) equipTrapAcknowledge code number"
        ::= 817

    radioEquipmentRemoteLimReserveAlarmSynthesisCleared   TRAP-TYPE
        ENTERPRISE pdh-al 
        DESCRIPTION
            "This event is generated by  NE when an 
              radioEquipmentRemoteLimReserveAlarmSynthesis is cleared
             1) radioEquipmentRemoteLimReserveAlarmSynthesis
             2) equipTrapAcknowledge code number"
        ::= 818

     radioEquipmentBaseBand1ActiveStatusSet  TRAP-TYPE
         ENTERPRISE pdh-al 
         DESCRIPTION "
            This event is generated by  NE when  the
            radioEquipmentBaseBand1ActiveStatus is set (2).
           The data passed with the event are:
           1) radioEquipmentBaseBand1ActiveStatus
           2) equipTrapAcknowledge code number"
        ::= 819

     radioEquipmentBaseBand1ActiveStatusCleared  TRAP-TYPE
         ENTERPRISE pdh-al 
         DESCRIPTION "
            This event is generated by  NE when  the
            radioEquipmentBaseBand1ActiveStatus is  cleared(1).
           The data passed with the event are:
           1) radioEquipmentBaseBand1ActiveStatus
           2) equipTrapAcknowledge code number"
        ::= 820

     radioEquipmentBaseBand2ActiveStatusSet  TRAP-TYPE
         ENTERPRISE pdh-al 
         DESCRIPTION "
            This event is generated by  NE when  the
            RadioEquipmentBaseBand2ActiveStatus is set (2).
           The data passed with the event are:
           1) radioEquipmentBaseBand2ActiveStatus
           2) equipTrapAcknowledge code number"
        ::= 821

     radioEquipmentBaseBand2ActiveStatusCleared  TRAP-TYPE
         ENTERPRISE pdh-al 
         DESCRIPTION "
            This event is generated by  NE when  the
            RadioEquipmentBaseBand2ActiveStatus is cleared (1).
           The data passed with the event are:
           1) radioEquipmentBaseBand2ActiveStatus
           2) equipTrapAcknowledge code number"
        ::= 822

    radioEquipmentRemoteEquipmentControllerAlarmSet   TRAP-TYPE
        ENTERPRISE pdh-al 
        DESCRIPTION
            "This event is generated by  NE when an 
              radioEquipmentRemoteEquipmentControllerAlarm is set
             1) radioEquipmentRemoteEquipmentControllerAlarmAlarm
             2) equipTrapAcknowledge code number"
        ::= 823

    radioEquipmentRemoteEquipmentControllerAlarmCleared   TRAP-TYPE
        ENTERPRISE pdh-al 
        DESCRIPTION
            "This event is generated by  NE when an 
              radioEquipmentRemoteEquipmentControllerAlarm is cleared
             1) radioEquipmentRemoteEquipmentControllerAlarm
             2) equipTrapAcknowledge code number"
        ::= 824

    radioEquipmentRemoteSplitterAlarmSet   TRAP-TYPE
        ENTERPRISE pdh-al 
        DESCRIPTION
            "This event is generated by  NE when an 
              radioEquipmentRemoteSplitterAlarm is set
             1) radioEquipmentRemoteSplitterAlarm
             2) equipTrapAcknowledge code number"
        ::= 825

    radioEquipmentRemoteSplitterAlarmCleared   TRAP-TYPE
        ENTERPRISE pdh-al 
        DESCRIPTION
            "This event is generated by  NE when an 
              radioEquipmentRemoteSplitterAlarm is cleared
             1) radioEquipmentRemoteSplitterAlarm
             2) equipTrapAcknowledge code number"
        ::= 826

    radioEquipmentPppRadioLinkAlarmSet   TRAP-TYPE
        ENTERPRISE pdh-al 
        DESCRIPTION
            "This event is generated by NE when an 
              radioEquipmentPppRadioLinkAlarm is set
             1) radioEquipmentPppRadioLinkAlarm
             2) equipTrapAcknowledge code number"
        ::= 827

    radioEquipmentPppRadioLinkAlarmCleared   TRAP-TYPE
        ENTERPRISE pdh-al 
        DESCRIPTION
            "This event is generated by NE when an 
              radioEquipmentPppRadioLinkAlarm is cleared
             1) radioEquipmentPppRadioLinkAlarm
             2) equipTrapAcknowledge code number"
        ::= 828

    radioEquipmentPrbsFailAlarmSet   TRAP-TYPE
        ENTERPRISE pdh-al 
        DESCRIPTION
            "This event is generated by NE when an 
              radioEquipmentPrbsFailAlarm is set
             1) radioEquipmentPrbsFailAlarm 
             2) equipTrapAcknowledge code number"
        ::= 829


    radioEquipmentPrbsFailAlarmCleared   TRAP-TYPE
        ENTERPRISE pdh-al 
        DESCRIPTION
            "This event is generated by NE when an 
              radioEquipmentPrbsFailAlarm is cleared
             1) radioEquipmentPrbsFailAlarm 
             2) equipTrapAcknowledge code number"
        ::= 830



----------------------------------------------------------------------
--  4.10 PPI (PDH PHYSICAL INTERFACE) GROUP
----------------------------------------------------------------------------------
--  This object is associated to  the "Unit" object  and describes one of   the Pdh port.
----------------------------------------------------------------------------------

    ppiTable  OBJECT-TYPE
        SYNTAX      SEQUENCE OF  PpiRecord
        ACCESS      not-accessible
        STATUS      mandatory
        DESCRIPTION 
            "Table with PPI records describing Pdh  ports  within an unit."
        ::=  { ppi  1 }

    ppiRecord  OBJECT-TYPE
        SYNTAX      PpiRecord
        ACCESS      not-accessible
        STATUS      mandatory
        DESCRIPTION 
            "PPI  record"
        INDEX { ppiUnitId,  
                ppiId }
        ::=  { ppiTable 1 }

    PpiRecord  ::=
        SEQUENCE {
            ppiUnitId         INTEGER,
            ppiId             INTEGER,
            ppiType           INTEGER,
            ppiEnable         INTEGER,
            ppiLosAlarm       INTEGER,
            ppiLineLoop       INTEGER,
            ppiInternalLoop   INTEGER
      }

    ppiUnitId  OBJECT-TYPE
        SYNTAX    INTEGER
        ACCESS      read-only
        STATUS      mandatory
        DESCRIPTION 
            "This object  identifies unit  where the PPI is  present."
        ::=  { ppiRecord  1}

    ppiId  OBJECT-TYPE
        SYNTAX    INTEGER
        ACCESS      read-only
        STATUS      mandatory
        DESCRIPTION 
            "This object  identifies  the PPI  within the Unit."
        ::=  { ppiRecord  2 }

    ppiType  OBJECT-TYPE
        SYNTAX    INTEGER {
                            pdh-2Mbit  (1),
                            pdh-34Mbit (3)
                          }
        ACCESS      read-only
        STATUS      mandatory
        DESCRIPTION 
            "Define the  type of the PDH signal"
        ::=  { ppiRecord  3 }

    ppiEnable OBJECT-TYPE
        SYNTAX    INTEGER {
                            off (1),
                            on  (2)
                          }
        ACCESS      read-write
        STATUS      mandatory
        DESCRIPTION 
            "Enable/disable the Pdh port on the Unit "
        DEFVAL{ off }
        ::=  { ppiRecord  4 }

    ppiLosAlarm  OBJECT-TYPE
        SYNTAX    INTEGER {
                           cleared                   (1),
                           activeReportable-Status   (2),
                           activeReportable-Warning  (3),
                           activeReportable-Minor    (4),
                           activeReportable-Major    (5),
                           activeReportable-Critical (6)
                          }
        ACCESS      read-only
        STATUS      mandatory
        DESCRIPTION 
            "PPI Loss of signal alarm status with associated Severity"
        ::=  { ppiRecord  5}

    ppiLineLoop OBJECT-TYPE
        SYNTAX    INTEGER {
                            loopOff (1),
                            loopOn  (2)
                          }
        ACCESS      read-write
        STATUS      mandatory
        DESCRIPTION 
            "Enable/disable the line loop on Pdh tributary."
        DEFVAL{ loopOff }
        ::=  { ppiRecord  6 }

    ppiInternalLoop OBJECT-TYPE
        SYNTAX    INTEGER {
                            loopOff (1),
                            loopOn  (2)
                          }
        ACCESS      read-write
        STATUS      mandatory
        DESCRIPTION 
            "Enable/disable the internal loop on PDH tributary."
        DEFVAL{ loopOff }
        ::=  { ppiRecord  7 }

----------------------------------------------------------------------------------
-- The following objects define the profile of the Pdh Phisycal Interface alarms:
----------------------------------------------------------------------------------

    ppiLosSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the PPI Loss of  signal  and  
             enable/disable the trap generation on status change event."
        DEFVAL{ major-trapEnable }
        ::=  { ppi  2 }


----------------------------------------------------------------------------------
--  The Ppi  Group generates the following TRAPs:
----------------------------------------------------------------------------------

    ppiLosAlarmSet  TRAP-TYPE
        ENTERPRISE pdh-al 
        DESCRIPTION 
            "This event is generated by  NE when  a ppiLosAlarm  is set
             The data passed with the event are:
             1) ppiId
             2) UnitId
             3) UnitLabel
             4) ppiLosAlarm
             5) equipTrapAcknowledge code number"
    ::= 901

    ppiLosAlarmCleared  TRAP-TYPE
        ENTERPRISE pdh-al 
        DESCRIPTION "
            This event is generated by  NE when a ppiLosAlarm is cleared
            The data passed with the event are:
            1) ppiId
            2) UnitId
            3) UnitLabel
            4) ppiLosAlarm
            5) equipTrapAcknowledge code number"
        ::= 902



----------------------------------------------------------------------------------
--  4.11 RADIO BRANCH GROUP
----------------------------------------------------------------------------------
--  This object  describes a  Radio Branch (Modulator/Demodulator and Tranceiver units).
----------------------------------------------------------------------------------

    radioBranchTable  OBJECT-TYPE
        SYNTAX      SEQUENCE OF  RadioBranchRecord
        ACCESS      not-accessible
        STATUS      mandatory
        DESCRIPTION 
            "Table with RadioBranch records: one record for 1+0 configuration and 
             two record for 1+1 configuration."
        ::=  { radioBranch  1 }

    radioBranchRecord  OBJECT-TYPE
        SYNTAX     RadioBranchRecord
        ACCESS      not-accessible
        STATUS      mandatory
        DESCRIPTION 
            "RadioBranch  record"
        INDEX { radioBranchId }
        ::=  { radioBranchTable 1 }

    RadioBranchRecord  ::=
        SEQUENCE {
            radioBranchId                         INTEGER,
            radioBranchLinkChNum                  INTEGER,
            radioBranchLocalChNum                 INTEGER,
            radioBranchAtpcManual                 INTEGER,
            radioBranchPtxSetValue                INTEGER,
            radioBranchAtpcPwrHigh                INTEGER,
            radioBranchAtpcPwrLow                 INTEGER,
            radioBranchAtpcBerHigh                INTEGER,
            radioBranchAtpcBerLow                 INTEGER,
            radioBranchTxStatus                   INTEGER,
            radioBranchCarrierOnly                INTEGER,
            radioBranchPrx                        INTEGER,
            radioBranchPtx                        INTEGER, 
            radioBranchLoop                       INTEGER, 
            radioBranchRxActiveStatus             INTEGER,
            radioBranchTxActiveStatus             INTEGER,
            radioBranchBaseBandMantBer            INTEGER,
            radioBranchBaseBandExpBer             INTEGER,
            radioBranchBaseBandErr                INTEGER,
            radioBranchTimeBer                    INTEGER,
            radioBranchStartBer                   INTEGER,
            radioBranchRtPsuOff                   INTEGER,
            radioBranchFrequencyTable             Opaque,
            radioBranchFrequencyJumpsTable        Opaque,
            radioBranchRtSetupTable               Opaque,
            radioBranchRimPsuFailAlarm            INTEGER,
            radioBranchRtPsuFailAlarm             INTEGER,
            radioBranchRxPowerLowAlarm            INTEGER,
            radioBranchTxPowerLowAlarm            INTEGER,
            radioBranchModulatorFailAlarm         INTEGER,
            radioBranchDemodulatorFailAlarm       INTEGER,
            radioBranchBaseBandEwlAlarm           INTEGER,
            radioBranchBaseBandLberAlarm          INTEGER,
            radioBranchBaseBandHberAlarm          INTEGER,
            radioBranchCableOpenAlarm             INTEGER,
            radioBranchCableShortAlarm            INTEGER,
            radioBranchBaseBandRxAlarm            INTEGER,
            radioBranchBaseBandIduOduCommAlarm    INTEGER,
            radioBranchRtVcoFailAlarm             INTEGER,
            radioBranchRtIfFailAlarm              INTEGER,
            radioBranchLocalOduAlarmSynthesis     INTEGER,
            radioBranchRemoteOduAlarmSynthesis    INTEGER,
            radioBranchLocalRimAlarmSynthesis     INTEGER,
            radioBranchRemoteRimAlarmSynthesis    INTEGER,
            radioBranchRtOduIduCommAlarm          INTEGER
        }

    radioBranchId  OBJECT-TYPE
        SYNTAX    INTEGER
        ACCESS      read-only
        STATUS      mandatory
        DESCRIPTION 
            "This object  identifies  the  Radio Branch."
        ::=  { radioBranchRecord  1 }

    radioBranchLinkChNum  OBJECT-TYPE
        SYNTAX    INTEGER
        ACCESS      read-write
        STATUS      mandatory
        DESCRIPTION 
            "The radio link channel number"
        ::=  { radioBranchRecord  2 }

    radioBranchLocalChNum  OBJECT-TYPE
        SYNTAX    INTEGER
        ACCESS      read-write
        STATUS      mandatory
        DESCRIPTION 
            "Number of the radio channel (assigned to the local terminal)"
        ::=  { radioBranchRecord 3 }

      radioBranchAtpcManual  OBJECT-TYPE
          SYNTAX    INTEGER {
                              disable (1),
                              enable (2)
                            }
        ACCESS      read-write
        STATUS      mandatory
        DESCRIPTION
            "Atpc Manual operation"
        DEFVAL      { disable }
      ::= { radioBranchRecord 4 }

    radioBranchPtxSetValue  OBJECT-TYPE
        SYNTAX      INTEGER
        ACCESS      read-write
        STATUS      mandatory
        DESCRIPTION
            "Transmitter Power set value (dBm)"
        DEFVAL      { 20 }
        ::= { radioBranchRecord 5 }

    radioBranchAtpcPwrHigh  OBJECT-TYPE
        SYNTAX      INTEGER
        ACCESS      read-write
        STATUS      mandatory
        DESCRIPTION
            "ATPC Control - Local Rx Power High (dBm range -20 to -80)"
        DEFVAL      { -40 }
        ::= { radioBranchRecord 6 }

    radioBranchAtpcPwrLow  OBJECT-TYPE
        SYNTAX      INTEGER
        ACCESS      read-write
        STATUS      mandatory
        DESCRIPTION
            "ATPC Control - Local Rx Power Low (dBm range -20 to -80)"
        DEFVAL      { -60 }
        ::= { radioBranchRecord 7 }

    radioBranchAtpcBerHigh  OBJECT-TYPE
        SYNTAX    INTEGER {
                            e-6 (-6),
                            e-7 (-7),
                            e-8 (-8),
                            e-9 (-9),
                            e-10 (-10)
                          }
        ACCESS      read-write
        STATUS      mandatory
        DESCRIPTION
            "Threshold (high) for the BER used by the ATPC"
        DEFVAL      { e-9 }
        ::={ radioBranchRecord  8 }

    radioBranchAtpcBerLow  OBJECT-TYPE
        SYNTAX    INTEGER {
                            e-6 (-6),
                            e-7 (-7),
                            e-8 (-8),
                            e-9 (-9),
                            e-10 (-10)
                          }
        ACCESS      read-write
        STATUS      mandatory
        DESCRIPTION
            "Threshold (Low) for the BER used by the ATPC"
        DEFVAL      { e-7 }
        ::={ radioBranchRecord  9 }

    radioBranchTxStatus OBJECT-TYPE
        SYNTAX    INTEGER {
                            transmitterOff (1),
                            transmitterOn  (2)
                           }
        ACCESS      read-write
        STATUS      mandatory
        DESCRIPTION 
            "Transmitter status control."
        DEFVAL{ transmitterOn }
        ::=  { radioBranchRecord  10 }

    radioBranchCarrierOnly  OBJECT-TYPE
        SYNTAX    INTEGER {
                            carrierOnlyOff (1),
                            carrierOnlyOn  (2)
                          }
        ACCESS      read-write
        STATUS      mandatory
        DESCRIPTION 
            "Carrier only transmission  control."
        DEFVAL{ carrierOnlyOff }
        ::=  { radioBranchRecord  11 }
    
    radioBranchPrx  OBJECT-TYPE
        SYNTAX      INTEGER
        ACCESS      read-only
        STATUS      mandatory
        DESCRIPTION
            "Received power level (dBm)"
        ::=  { radioBranchRecord  12 }    
    
    
    radioBranchPtx  OBJECT-TYPE
        SYNTAX      INTEGER
        ACCESS      read-only
        STATUS      mandatory
        DESCRIPTION
            " transmitted power level (dBm)"
        ::=  { radioBranchRecord  13 }   

    radioBranchLoop OBJECT-TYPE
        SYNTAX    INTEGER {
                            loopOff (1),
                            rFloopOn-RemTxOff (2),
                            iduLoop  (3),
                            baseBandUnitloop (4),
                            rFloopOn-RemTxOn (5)
                          }
        ACCESS      read-write
        STATUS      mandatory
        DESCRIPTION 
            "Enable/disable the  Radio Branch  loops."
        DEFVAL{ loopOff }
        ::=  { radioBranchRecord  14 }

    radioBranchRxActiveStatus OBJECT-TYPE
        SYNTAX    INTEGER {
                            cleared (1),
                            active (2)
                          }
        ACCESS      read-only
        STATUS      mandatory
        DESCRIPTION 
            "Receiver Active  status    status with associated Severity 
             (meaningfull in 1+1 configuration)"
        ::=  { radioBranchRecord  15 }

    radioBranchTxActiveStatus OBJECT-TYPE
        SYNTAX    INTEGER {
                            cleared (1),
                            active (2)
                          }
        ACCESS      read-only
        STATUS      mandatory
        DESCRIPTION 
            "Transmitter Active status with associated Severity (1+1 ISO sistem only)"
        ::=  { radioBranchRecord  16 }

    radioBranchBaseBandMantBer OBJECT-TYPE
        SYNTAX      INTEGER
        ACCESS      read-only
        STATUS      mandatory
        DESCRIPTION
            "Mantissa of Measured BER (n*10-x)"
        ::= { radioBranchRecord 17 }

    radioBranchBaseBandExpBer  OBJECT-TYPE
        SYNTAX      INTEGER
        ACCESS      read-only
        STATUS      mandatory
        DESCRIPTION
            "Exponent of Measured BER (n*10-x)"
        ::= { radioBranchRecord 18 }

    radioBranchBaseBandErr  OBJECT-TYPE
        SYNTAX      INTEGER
        ACCESS      read-only
        STATUS      mandatory
        DESCRIPTION
            "Number of error"
        ::= { radioBranchRecord 19 }

    radioBranchTimeBer OBJECT-TYPE
        SYNTAX      INTEGER
        ACCESS      read-only
        STATUS      mandatory
        DESCRIPTION
            "Elapsed time since the start of Ber evaluation command"
        ::= { radioBranchRecord 20 }

    radioBranchStartBer  OBJECT-TYPE
        SYNTAX    INTEGER {
                            on (2)
                          }
        ACCESS      write-only
        STATUS      mandatory
        DESCRIPTION
            "Reset BER and Start BER evaluation"
        ::= { radioBranchRecord 21 }

    radioBranchRtPsuOff OBJECT-TYPE
        SYNTAX    INTEGER {
                            rtPsuOn (1),
                            rtPsuOff (2)
                          }
        ACCESS      read-write
        STATUS      mandatory
        DESCRIPTION 
            "It switches on/off the Rt power supply"
        DEFVAL{ rtPsuOn }
        ::=  { radioBranchRecord  22 }

    radioBranchFrequencyTable  OBJECT-TYPE
        SYNTAX      Opaque
        ACCESS      read-only
        STATUS      mandatory
        DESCRIPTION
            "Table (32 Bytes) used to evaluate the channel frequency 
            (Ref. SP.SDHRTPR):
             Type                - channeling type: 
              (1 Byte)             0 = fixed step
                                   1 = variable step
                                   2 = continous
                                   3 = undefined
             TableId             - Frequency Table Identifier
             (1 Byte)
             Rep                 - if fixed step channeling:
             (2 Bytes)              step number  between two adjacent channels
                                    (Rep x Step = frequency spacing) 
                                   if variable step channeling,
                                    step value (Rep x Step) used to evaluate 
                                    variable frequency spacing between two 
                                    adjacent channels 
                                   (ref. radioBranch frequency jump)
             RasterNumber        - Band number
             (1 Byte)
             Spare               - 
             (1 Byte)              
             Step                - Frequency step(Hertz)
             (4 Bytes)
             ChannelNumber       - Number of channels (1 ÷  65.535)
             (2 Bytes)
             FirstChanFreq_Low   - First Channel Frequency
             (4 Bytes)             of Lower half of the band
             FirstChanFrequ_Up   - First Channel Frequency 
             (4 Bytes)             of Upper half of the band
             First Channel       - First channel of the band
             (2 Bytes)
             Spares              - Reserved for future use
             (10 Bytes)
            "
        ::= { radioBranchRecord 23 }

    radioBranchFrequencyJumpsTable  OBJECT-TYPE
        SYNTAX      Opaque
        ACCESS      read-only
        STATUS      mandatory
        DESCRIPTION
            "256 Bytes (128 x 2 bytes variable) Array used if variable step
             frequency spacing is set. [n-2] variable is the number of steps 
             ( each step = Rep x Step Hertz) required to go from channel n-1
              to channel n). Not used bytes are set to 0xFF"
        ::= { radioBranchRecord 24 }

    radioBranchRtSetupTable  OBJECT-TYPE
        SYNTAX      Opaque
        ACCESS      read-write
        STATUS      mandatory
        DESCRIPTION
            "Table (32 Bytes)used to set the radio parameter (used only by the 
             Lab. and by the Test departement)(Ref. SP.SDHRTPR):
                             ErrorCode           (1 Byte)     (usato dal LOM)
                             MinPtxNominalLevel  (1 Byte)     (PtxMin in dBm)
                             MaxPtxNominalLevel  (1 Byte)     (PtxMax in dBm)
                             RfSubBand           (1 Byte)     (Used band: 0low, 1 high)
                             Spare (28 Bytes) (Reserved).                    
             The table is used in GET to read  Max transmitted power (dBm) and 
             if low band (0) or the high band is (1) used"
        ::= { radioBranchRecord 25 }
    
    radioBranchRimPsuFailAlarm OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "RIM power supply alarm status with associated Severity."
        ::=  { radioBranchRecord  26 }

    radioBranchRtPsuFailAlarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "Tranceiver power supply alarm  status with associated Severity."
        ::=  { radioBranchRecord  27 }

    radioBranchRxPowerLowAlarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "Receiver power low alarm status with associated Severity."
        ::=  { radioBranchRecord  28 }

    radioBranchTxPowerLowAlarm  OBJECT-TYPE
        SYNTAX    INTEGER {            
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "Transmitter power low alarm status with associated Severity."
        ::=  { radioBranchRecord 29 }

    radioBranchModulatorFailAlarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "Modulator Fail Alarm status with associated Severity."
        ::=  { radioBranchRecord  30 }

    radioBranchDemodulatorFailAlarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "Demodulator Fail Alarm status with associated Severity."
        ::=  { radioBranchRecord  31 }

    radioBranchBaseBandEwlAlarm OBJECT-TYPE
        SYNTAX    INTEGER {
                            cleared (1),
                            activeReportable-Status (2),
                            activeReportable-Warning (3),
                            activeReportable-Minor (4),
                            activeReportable-Major (5),
                            activeReportable-Critical (6)
                          }
        ACCESS      read-only
        STATUS      mandatory
        DESCRIPTION
            "Early Warning low alarm status with associated Severity."
        ::= { radioBranchRecord 32 }

    radioBranchBaseBandLberAlarm OBJECT-TYPE
        SYNTAX    INTEGER {
                            cleared                   (1),
                            activeReportable-Status   (2),
                            activeReportable-Warning  (3),
                            activeReportable-Minor    (4),
                            activeReportable-Major    (5),
                            activeReportable-Critical (6)
                          }
       ACCESS      read-only
       STATUS      mandatory
       DESCRIPTION 
          "Low BER Alarm status with associated Severity."
       ::=  { radioBranchRecord  33 }

    radioBranchBaseBandHberAlarm OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "High BER Alarm"
       ::=  { radioBranchRecord  34 }

    radioBranchCableOpenAlarm OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "The cable between IDU and ODU is open (SPU5 only) with associated Severity."
        ::=  { radioBranchRecord  35 }

    radioBranchCableShortAlarm OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "A short circuit is present in the cable between IDU and ODU (SPU5 only)      
             with associated  Severity."
        ::=  { radioBranchRecord  36 }

    radioBranchBaseBandRxAlarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "Base Band Rx alarm status with associated Severity."
        ::=  { radioBranchRecord  37 }

    radioBranchBaseBandIduOduCommAlarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "IDU ODU Communication channel alarm status with associated Severity."
        ::=  { radioBranchRecord  38 }

    radioBranchRtVcoFailAlarm  OBJECT-TYPE
        SYNTAX    INTEGER {
                            cleared (1),
                            activeReportable-Status (2),
                            activeReportable-Warning (3),
                            activeReportable-Minor (4),
                            activeReportable-Major (5),
                            activeReportable-Critical (6)
                          }
        ACCESS      read-only
        STATUS      mandatory
        DESCRIPTION
            "RT VCO fail  alarm status with associated  Severity."
        ::= { radioBranchRecord 39 }

    radioBranchRtIfFailAlarm  OBJECT-TYPE
        SYNTAX    INTEGER {
                            cleared (1),
                            activeReportable-Status (2),
                            activeReportable-Warning (3),
                            activeReportable-Minor (4),
                            activeReportable-Major (5),
                            activeReportable-Critical (6)
                          }
        ACCESS      read-only
        STATUS      mandatory
        DESCRIPTION
            "RT IF fail  alarm status with associated  Severity."
        ::= { radioBranchRecord 40 }

    radioBranchLocalOduAlarmSynthesis  OBJECT-TYPE
        SYNTAX    INTEGER {
                            cleared                    (1),
                            activeReportable-Status    (2),
                            activeReportable-Warning   (3),
                            activeReportable-Minor     (4),
                            activeReportable-Major     (5),
                            activeReportable-Critical  (6)
                          }
        ACCESS      read-only
        STATUS      mandatory
        DESCRIPTION 
            "Synthesis of the local Odu alarms"  
        ::=  { radioBranchRecord  41 }

    radioBranchRemoteOduAlarmSynthesis  OBJECT-TYPE
        SYNTAX    INTEGER {
                            cleared                    (1),
                            activeReportable-Status    (2),
                            activeReportable-Warning   (3),
                            activeReportable-Minor     (4),
                            activeReportable-Major     (5),
                            activeReportable-Critical  (6)
                          }
        ACCESS      read-only
        STATUS      mandatory
        DESCRIPTION 
            "Synthesis of the remote Odu alarms"  
        ::=  { radioBranchRecord  42 }

    radioBranchLocalRimAlarmSynthesis  OBJECT-TYPE
        SYNTAX    INTEGER {
                            cleared                    (1),
                            activeReportable-Status    (2),
                            activeReportable-Warning   (3),
                            activeReportable-Minor     (4),
                            activeReportable-Major     (5),
                            activeReportable-Critical  (6)
                          }
        ACCESS      read-only
        STATUS      mandatory
        DESCRIPTION 
            "Synthesis of the local RIM alarms"  
        ::=  { radioBranchRecord  43 }

    radioBranchRemoteRimAlarmSynthesis  OBJECT-TYPE
        SYNTAX    INTEGER {
                            cleared                    (1),
                            activeReportable-Status    (2),
                            activeReportable-Warning   (3),
                            activeReportable-Minor     (4),
                            activeReportable-Major     (5),
                            activeReportable-Critical  (6)
                          }
        ACCESS      read-only
        STATUS      mandatory
        DESCRIPTION 
            "Synthesis of the remote RIM alarms"  
        ::=  { radioBranchRecord  44 }

    radioBranchRtOduIduCommAlarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "IDU ODU Communication channel alarm status with associated 
             Severity (Set by Rt controller)."
        ::=  { radioBranchRecord  45 }



----------------------------------------------------------------------------------
--  The following objects define the profile of the RadioBranch  alarms:
--
--  The general stucture of the object is the following:
--

-- radioBranch<AlarmName>SeverityCode  OBJECT-TYPE
--     SYNTAX    INTEGER {
--                            disable                    (1),
--                            status-trapEnable          (2),
--                            status-trapEnableWithACK   (34),
--                            warning-trapEnable         (3),
--                            warning-trapEnableWithACK  (35),
--                            minor-trapEnable           (4),
--                            minor-trapEnableWithACK    (36),
--                            major-trapEnable           (5),
--                            major-trapEnableWithACK    (37),
--                            critical-trapEnable        (6),
--                            critical-trapEnableWithACK (38),
--                            status-trapDisable         (18),
--                            warning-trapDisable        (19),
--                            minor-trapDisable          (20),
--                            major-trapDisable          (21),
--                            critical-trapDisable       (22)
--                       }
--     ACCESS      read-write
--     STATUS      mandatory
--     DESCRIPTION "
--           Define the severity associated to the  <alarm name>  and 
--           enable/disable the trap generation on status
--           change   event.
--     "  DEFVAL{ x }
--    ::=  {radioBranch  y }
----------------------------------------------------------------------------------

    radioBranchRimPsuFailAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the RadioBranchRimPsuFailAlarm and  
             enable/disable the trap generation on status change event."
        DEFVAL  { major-trapEnable }
        ::=  { radioBranch  2 }

    radioBranchRtPsuFailAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the RadioBranchRtPsuFailAlarm and  
             enable/disable the trap generation on status change event."
        DEFVAL  { major-trapEnable }
        ::=  { radioBranch  3 }

    radioBranchRxPowerLowAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the RadioBranchRxPowerLowAlarm and  
             enable/disable the trap generation on status change event."
        DEFVAL  { major-trapEnable }
        ::=  { radioBranch  4 }

    radioBranchTxPowerLowAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the radioBranchTxPowerLowAlarm and  
             enable/disable the trap generation on status  change event."
        DEFVAL  { major-trapEnable }
        ::=  { radioBranch  5 }

    radioBranchModulatorFailAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the radioBranchModulatorFailAlarm  
             and  enable/disable the trap generation on status change event."
        DEFVAL  { major-trapEnable }
        ::=  { radioBranch  6 }

    radioBranchDemodulatorFailAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the radioBranchDemodulatorFailAlarm  
             and  enable/disable the trap generation on status  change event."
        DEFVAL  { major-trapEnable }
        ::=  { radioBranch  7 }

    radioBranchBaseBandEwlAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the radioBranchDBaseBandEwlAlarm and  
             enable/disable the trap generation on status change event."
        DEFVAL  { warning-trapEnable }
        ::=  { radioBranch  8 }

    radioBranchBaseBandLberAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the radioBranchBaseBandLberAlarm and  
             enable/disable the trap generation on status change event."
        DEFVAL  { minor-trapEnable }
        ::=  { radioBranch  9 }

    radioBranchBaseBandHberAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                        }
        ACCESS      read-write
        STATUS      mandatory
        DESCRIPTION 
            "Define the severity associated to the radioBranchBaseBandHberAlarm and  
             enable/disable the trap generation on status change event."
        DEFVAL  { major-trapEnable }
        ::=  { radioBranch  10 }

    radioBranchCableOpenAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the radioBranchCableOpenAlarm and  
             enable/disable the trap generation on status change event."
        DEFVAL{ major-trapEnable }
        ::=  { radioBranch  11 }

    radioBranchCableShortAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the radioBranchCableShortAlarm and  
             enable/disable the trap generation on status change event."
        DEFVAL  { major-trapEnable }
        ::=  { radioBranch  12 }

    radioBranchBaseBandRxAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the radioBranchBaseBandRxAlarm and  
             enable/disable the trap generation on status change event."
        DEFVAL  { major-trapEnable }
        ::=  { radioBranch  13 }

    radioBranchBaseBandIduOduCommAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the radioBranchBaseBandIduOduCommAlarm 
             and enable/disable the trap generation on status change event."
        DEFVAL  { major-trapEnable }
        ::=  { radioBranch  14 }

    radioBranchRtVcoFailAlarmSeverityCode  OBJECT-TYPE
        SYNTAX    INTEGER {
                            disable (1),
                            status-trapEnable (2),
                            status-trapEnableWithACK (34),
                            warning-trapEnable (3),
                            warning-trapEnableWithACK (35),
                            minor-trapEnable (4),
                            minor-trapEnableWithACK (36),
                            major-trapEnable (5),
                            major-trapEnableWithACK (37),
                            critical-trapEnable (6),
                            critical-trapEnableWithACK (38),
                            status-trapDisable (18),
                            warning-trapDisable (19),
                            minor-trapDisable (20),
                            major-trapDisable (21),
                            critical-trapDisable (22)
                          }
        ACCESS      read-write
        STATUS      mandatory
        DESCRIPTION
            "Define the severity associated to the RadioBranchRtVcoFailAlarm and 
             enable/disable the trap generation on status change event."
        DEFVAL  { major-trapEnable }
        ::= { radioBranch 15 }

    radioBranchRtIfFailAlarmSeverityCode  OBJECT-TYPE
        SYNTAX    INTEGER {
                            disable (1),
                            status-trapEnable (2),
                            status-trapEnableWithACK (34),
                            warning-trapEnable (3),
                            warning-trapEnableWithACK (35),
                            minor-trapEnable (4),
                            minor-trapEnableWithACK (36),
                            major-trapEnable (5),
                            major-trapEnableWithACK (37),
                            critical-trapEnable (6),
                            critical-trapEnableWithACK (38),
                            status-trapDisable (18),
                            warning-trapDisable (19),
                            minor-trapDisable (20),
                            major-trapDisable (21),
                            critical-trapDisable (22)
                          }
        ACCESS      read-write
        STATUS      mandatory
        DESCRIPTION
            "Define the severity associated to the RadioBranchRtIfFailAlarm and 
             enable/disable the trap generation on status change event."
        DEFVAL  { major-trapEnable }
        ::= { radioBranch 16 }

    radioBranchLocalOduAlarmSynthesisSeverityCode  OBJECT-TYPE
        SYNTAX    INTEGER {
                            disable (1),
                            status-trapEnable (2),
                            status-trapEnableWithACK (34),
                            warning-trapEnable (3),
                            warning-trapEnableWithACK (35),
                            minor-trapEnable (4),
                            minor-trapEnableWithACK (36),
                            major-trapEnable (5),
                            major-trapEnableWithACK (37),
                            critical-trapEnable (6),
                            critical-trapEnableWithACK (38),
                            status-trapDisable (18),
                            warning-trapDisable (19),
                            minor-trapDisable (20),
                            major-trapDisable (21),
                            critical-trapDisable (22)
                          }
        ACCESS      read-write
        STATUS      mandatory
        DESCRIPTION
            "Define the severity associated to the radioBranchLocalOduAlarmSynthesis 
             and enable/disable the trap generation on status change event."
        DEFVAL      { major-trapEnable }
        ::= { radioBranch 17 }

    radioBranchRemoteOduAlarmSynthesisSeverityCode  OBJECT-TYPE
        SYNTAX    INTEGER {
                            disable (1),
                            status-trapEnable (2),
                            status-trapEnableWithACK (34),
                            warning-trapEnable (3),
                            warning-trapEnableWithACK (35),
                            minor-trapEnable (4),
                            minor-trapEnableWithACK (36),
                            major-trapEnable (5),
                            major-trapEnableWithACK (37),
                            critical-trapEnable (6),
                            critical-trapEnableWithACK (38),
                            status-trapDisable (18),
                            warning-trapDisable (19),
                            minor-trapDisable (20),
                            major-trapDisable (21),
                            critical-trapDisable (22)
                          }
        ACCESS      read-write
        STATUS      mandatory
        DESCRIPTION
            "Define the severity associated to the 
             radioBranchRemoteOduAlarmSynthesis and   enable/disable 
             the trap generation on status change event."
        DEFVAL      { major-trapEnable }
        ::= { radioBranch 18 }

    radioBranchLocalRimAlarmSynthesisSeverityCode  OBJECT-TYPE
        SYNTAX    INTEGER {
                            disable (1),
                            status-trapEnable (2),
                            status-trapEnableWithACK (34),
                            warning-trapEnable (3),
                            warning-trapEnableWithACK (35),
                            minor-trapEnable (4),
                            minor-trapEnableWithACK (36),
                            major-trapEnable (5),
                            major-trapEnableWithACK (37),
                            critical-trapEnable (6),
                            critical-trapEnableWithACK (38),
                            status-trapDisable (18),
                            warning-trapDisable (19),
                            minor-trapDisable (20),
                            major-trapDisable (21),
                            critical-trapDisable (22)
                          }
        ACCESS      read-write
        STATUS      mandatory
        DESCRIPTION
            "Define the severity associated to the 
             radioBranchLocalRimAlarmSynthesis and   enable/disable 
             the trap generation on status change event."
        DEFVAL      { major-trapEnable }
        ::= { radioBranch 19 }

    radioBranchRemoteRimAlarmSynthesisSeverityCode  OBJECT-TYPE
        SYNTAX    INTEGER {
                            disable (1),
                            status-trapEnable (2),
                            status-trapEnableWithACK (34),
                            warning-trapEnable (3),
                            warning-trapEnableWithACK (35),
                            minor-trapEnable (4),
                            minor-trapEnableWithACK (36),
                            major-trapEnable (5),
                            major-trapEnableWithACK (37),
                            critical-trapEnable (6),
                            critical-trapEnableWithACK (38),
                            status-trapDisable (18),
                            warning-trapDisable (19),
                            minor-trapDisable (20),
                            major-trapDisable (21),
                            critical-trapDisable (22)
                          }
        ACCESS      read-write
        STATUS      mandatory
        DESCRIPTION
            "Define the severity associated to the 
             radioBranchRemoteRimAlarmSynthesis and   enable/disable 
             the trap generation on status change event."
        DEFVAL      { major-trapEnable }
        ::= { radioBranch 20 }

    radioBranchRxActiveStatusSeverityCode  OBJECT-TYPE
        SYNTAX    INTEGER {
                            trapDisable (1),
                            trapEnable (2),
                            trapEnableWithACK (34)
                          }
        ACCESS      read-write
        STATUS      mandatory
        DESCRIPTION 
            "Define the severity associated to the radioBranchRxActivestatus and  
             enable/disable the trap generation on status change event."
        DEFVAL{ trapEnable }
        ::=  { radioBranch  21 }

    radioBranchTxActiveStatusSeverityCode  OBJECT-TYPE
        SYNTAX    INTEGER {
                            trapDisable (1),
                            trapEnable (2),
                            trapEnableWithACK (34)
                          }
        ACCESS      read-write
        STATUS      mandatory
        DESCRIPTION 
            "Define the severity associated to the radioBranchTxActivestatus and  
             enable/disable the trap generation on status change event."
        DEFVAL{ trapEnable }
        ::=  { radioBranch  22 }
    
    radioBranchPrxHysteresisValue  OBJECT-TYPE
        SYNTAX      INTEGER
        ACCESS      read-write
        STATUS      mandatory
        DESCRIPTION
            "Define the delta value associated to the RadioBranchPrx before
             having a new trap generation. The zero value is not allowed"
        DEFVAL      { 3 }
        ::= { radioBranch 23 }

    radioBranchPtxHysteresisValue  OBJECT-TYPE
        SYNTAX      INTEGER
        ACCESS      read-write
        STATUS      mandatory
        DESCRIPTION
            "Define the delta value associated to the RadioBranchPtx before 
             having a new trap generation. The zero value is not allowed"
        DEFVAL      { 3 }
        ::= { radioBranch 24 }

    radioBranchPrxHysteresisValueTrapNotification OBJECT-TYPE
        SYNTAX    INTEGER {
                            trapDisable        (1),
                            trapEnable         (2),
                            trapEnableWithACK  (34)
                          }
        ACCESS      read-write
        STATUS      mandatory
        DESCRIPTION
            "Enable/disable the Rx change trap generation on status change
             event."
        DEFVAL      { trapEnable }
        ::= { radioBranch 25 }

    radioBranchPtxHysteresisValueTrapNotification OBJECT-TYPE
        SYNTAX    INTEGER {
                            trapDisable        (1),
                            trapEnable         (2),
                            trapEnableWithACK  (34)
                          }
        ACCESS      read-write
        STATUS      mandatory
        DESCRIPTION
            "Enable/disable the Tx change trap generation on status change event."
        DEFVAL      { trapEnable }
        ::= { radioBranch 26 }

    radioBranchRtOduIduCommAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the 
             radioBranchRtOduIduCommAlarm and enable/disable the trap 
             generation on status change event."
        DEFVAL    { major-trapEnable }
        ::=  { radioBranch  27 }


     
----------------------------------------------------------------------------------
--  The RadioBranch  Group generates the following TRAPs:
---------------------------------------------------------------------------------- 
  
    radioBranchRimPsuFailAlarmSet  TRAP-TYPE
        ENTERPRISE pdh-al 
        DESCRIPTION "
            This event is generated by  NE when  a radioBranchRimPsuFailAlarm  is 
            set The data passed with the event are:
            1) radioBranchId 
            2) RimPsuFailAlarm
            3) equipTrapAcknowledge code number"
        ::= 1001
  
    radioBranchRimPsuFailAlarmCleared  TRAP-TYPE
        ENTERPRISE pdh-al 
        DESCRIPTION "
            This event is generated by  NE when a radioBranchRimPsuFailAlarm is 
            cleared The data passed with the event are:
            1) radioBranchId 
            2) RimPsuFailAlarm
            3) equipTrapAcknowledge code number"
        ::= 1002

    radioBranchRtPsuFailAlarmSet  TRAP-TYPE
        ENTERPRISE pdh-al 
        DESCRIPTION "
            This event is generated by  NE when  a  radioBranchRtPsuFailAlarm  is 
            set  The data passed with the event are:
            1) radioBranchId 
            2) RtPsuFailAlarm
            3) equipTrapAcknowledge code number"
        ::= 1003

    radioBranchRtPsuFailAlarmCleared  TRAP-TYPE
        ENTERPRISE pdh-al 
        DESCRIPTION "
            This event is generated by  NE when a radioBranchRtPsuFailAlarm is 
            cleared  The data passed with the event are:
            1) radioBranchId 
            2) RtPsuFailAlarm
            3) equipTrapAcknowledge code number"
        ::= 1004

    radioBranchRxPowerLowAlarmSet  TRAP-TYPE
        ENTERPRISE pdh-al 
        DESCRIPTION "
            This event is generated by  NE when  a radioBranchRxPowerLowAlarm  is 
            set  The data passed with the event are:
            1) radioBranchId 
            2) RxPowerLowAlarm
            3) equipTrapAcknowledge code number"
        ::= 1005

    radioBranchRxPowerLowAlarmCleared  TRAP-TYPE
        ENTERPRISE pdh-al 
        DESCRIPTION "
            This event is generated by  NE when a radioBranchRxPowerLowAlarm is 
            cleared The data passed with the event are:
            1) radioBranchId 
            2) RxPowerLowAlarm
            3) equipTrapAcknowledge code number"
        ::= 1006

    radioBranchTxPowerLowAlarmSet  TRAP-TYPE
        ENTERPRISE pdh-al 
        DESCRIPTION "
            This event is generated by  NE when  a radioBranchTxPowerLowAlarm  is 
            set  The data passed with the event are:
            1) radioBranchId 
            2) TxPowerLowAlarm
            3) equipTrapAcknowledge code number"
        ::= 1007

    radioBranchTxPowerLowAlarmCleared  TRAP-TYPE
        ENTERPRISE pdh-al 
        DESCRIPTION "
            This event is generated by  NE when a radioBranchTxPowerLowAlarm  is 
            cleared  The data passed with the event are:
            1) radioBranchId 
            2) TxPowerLowAlarm
            3) equipTrapAcknowledge code number"
        ::= 1008

    radioBranchModulatorFailAlarmSet  TRAP-TYPE
        ENTERPRISE pdh-al 
        DESCRIPTION "
            This event is generated by  NE when  a radioBranchModulatorFailAlarm  is 
            set  The data passed with the event are:
            1) radioBranchId 
            2) ModulatorFailAlarm
            3) equipTrapAcknowledge code number"
        ::= 1009

    radioBranchModulatorFailAlarmCleared  TRAP-TYPE
        ENTERPRISE pdh-al 
        DESCRIPTION "
            This event is generated by  NE when a radioBranchModulatorFailAlarm   is 
            cleared   The data passed with the event are:
            1) radioBranchId 
            2) ModulatorFailAlarm
            3) equipTrapAcknowledge code number"
        ::= 1010

    radioBranchDemodulatorFailAlarmSet  TRAP-TYPE
        ENTERPRISE pdh-al 
        DESCRIPTION "
            This event is generated by  NE when  a radioBranchDemodulatorFailAlarm     
            is set The data passed with the event are:
            1) radioBranchId 
            2) DemodulatorFailAlarm
            3) equipTrapAcknowledge code number"
        ::= 1011

    radioBranchDemodulatorFailAlarmCleared  TRAP-TYPE
        ENTERPRISE pdh-al 
        DESCRIPTION "
            This event is generated by  NE when a radioBranchDemodulatorFailAlarm  
            is cleared The data passed with the event are:
            1) radioBranchId 
            2) DemodulatorFailAlarm
            3) equipTrapAcknowledge code number"
        ::= 1012

    radioBranchBaseBandLberAlarmSet  TRAP-TYPE
        ENTERPRISE pdh-al 
        DESCRIPTION "
            This event is generated by  NE when  a radioBranchBaseBandLberAlarm is set
            The data passed with the event are:
            1) radioBranchId
            2) BaseBandLberAlarm 
            3) equipTrapAcknowledge code number"
        ::= 1013

    radioBranchBaseBandLberAlarmCleared  TRAP-TYPE
        ENTERPRISE pdh-al 
        DESCRIPTION "
            This event is generated by  NE when a radioBranchBaseBandLberAlarm is cleared
            The data passed with the event are:
            1) radioBranchId 
            2) BaseBandLberAlarm
            3) equipTrapAcknowledge code number"
        ::= 1014

    radioBranchBaseBandHberAlarmSet  TRAP-TYPE
        ENTERPRISE pdh-al 
        DESCRIPTION "
            This event is generated by  NE when  a radioBranchBaseBandHberAlarm is set
            The data passed with the event are:
            1) radioBranchId 
            2) BaseBandHberAlarm
            3) equipTrapAcknowledge code number"
        ::= 1015

    radioBranchBaseBandHberAlarmCleared  TRAP-TYPE
        ENTERPRISE pdh-al 
        DESCRIPTION "
            This event is generated by  NE when a radioBranchBaseBandHberAlarm  is 
            cleared The data passed with the event are:
            1) radioBranchId 
            2) BaseBandHberAlarm
            3) equipTrapAcknowledge code number"
        ::= 1016

    radioBranchCableOpenAlarmSet  TRAP-TYPE
        ENTERPRISE pdh-al 
        DESCRIPTION "
            This event is generated by  NE when  a radioBranchCableOpenAlarm is set
            The data passed with the event are:
            1) radioBranchId 
            2) CableOpenAlarm
            3) equipTrapAcknowledge code number"
        ::= 1017

    radioBranchCableOpenAlarmCleared  TRAP-TYPE
        ENTERPRISE pdh-al 
        DESCRIPTION "
            This event is generated by  NE when a radioBranchCableOpenAlarm is 
            cleared The data passed with the event are:
            1) radioBranchId 
            2) CableOpenAlarm
            3) equipTrapAcknowledge code number"
        ::= 1018

    radioBranchCableShortAlarmSet  TRAP-TYPE
        ENTERPRISE pdh-al 
        DESCRIPTION "
            This event is generated by  NE when  a radioBranchCableShortAlarm is set
            The data passed with the event are:
            1) radioBranchId 
            2) CableShortAlarm
            3) equipTrapAcknowledge code number"
        ::= 1019

    radioBranchCableShortAlarmCleared  TRAP-TYPE
        ENTERPRISE pdh-al 
        DESCRIPTION "
            This event is generated by  NE when a radioBranchCableShortAlarm is 
            cleared  The data passed with the event are:
            1) radioBranchId 
            2) CableShortAlarm
            3) equipTrapAcknowledge code number"
        ::= 1020

    radioBranchBaseBandRxAlarmSet  TRAP-TYPE
        ENTERPRISE pdh-al 
        DESCRIPTION "
            This event is generated by  NE when  a radioBranchBaseBandRxAlarm is set
            The data passed with the event are:
            1) radioBranchId 
            2) BaseBandRxAlarm
            3) equipTrapAcknowledge code number"
        ::= 1021

    radioBranchBaseBandRxAlarmCleared  TRAP-TYPE
        ENTERPRISE pdh-al 
        DESCRIPTION "
            This event is generated by  NE when a radioBranchBaseBandRxAlarm  is 
            cleared  The data passed with the event are:
            1) radioBranchId 
            2) BaseBandRxAlarm
            3) equipTrapAcknowledge code number"
        ::= 1022

    radioBranchBaseBandIduOduCommAlarmSet TRAP-TYPE
        ENTERPRISE pdh-al 
        DESCRIPTION "
            This event is generated by  NE when a 
            radioBranchBaseBandIduOduCommAlarm is set
            The data passed with the event are:
            1) radioBranchId 
            2) IduOduCommunicationAlarm
            3) equipTrapAcknowledge code number"
        ::= 1023

    radioBranchBaseBandIduOduCommAlarmCleared  TRAP-TYPE
        ENTERPRISE pdh-al 
        DESCRIPTION "
            This event is generated by  NE when a 
            radioBranchBaseBandIduOduCommAlarm is cleared
            The data passed with the event are:
            1) radioBranchId 
            2) BaseBandIduOduCommAlarm
            3) equipTrapAcknowledge code number"
        ::= 1024

    radioBranchBaseBandEwlSet TRAP-TYPE
        ENTERPRISE pdh-al 
        DESCRIPTION "
            This event is generated by  NE when a radioBranchBaseBandEwlAlarm is set
            The data passed with the event are:
            1) radioBranchId 
            2) radioBranchBaseBandEwlAlarm
            3) equipTrapAcknowledge code number"
        ::= 1025

    radioBranchBaseBandEwlCleared TRAP-TYPE
        ENTERPRISE pdh-al 
        DESCRIPTION "
            This event is generated by  NE when a radioBranchBaseBandEwlAlarm is cleared
            The data passed with the event are:
            1) radioBranchId 
            2) radioBranchBaseBandEwlAlarm
            3) equipTrapAcknowledge code number"
        ::= 1026

    radioBranchRtVcoFailSet TRAP-TYPE
        ENTERPRISE pdh-al 
        DESCRIPTION "
            This event is generated by  NE when a radioBranchRtVcoFailAlarm is set
            The data passed with the event are:
            1) radioBranchId 
            2) radioBranchRtVcoFaillAlarm
            3) equipTrapAcknowledge code number"
        ::= 1027

    radioBranchRtVcoFailCleared TRAP-TYPE
        ENTERPRISE pdh-al 
        DESCRIPTION "
            This event is generated by  NE when a radioBranchRtVcoFailAlarm is cleared
            The data passed with the event are:
            1) radioBranchId 
            2) radioBranchRtVcoFaillAlarm
            3) equipTrapAcknowledge code number"
        ::= 1028

    radioBranchRtIfFailSet TRAP-TYPE
        ENTERPRISE pdh-al 
        DESCRIPTION "
            This event is generated by  NE when a radioBranchRtIfFailAlarm is set
            The data passed with the event are:
            1) radioBranchId 
            2) radioBranchRtIfFaillAlarm
            3) equipTrapAcknowledge code number"
        ::= 1029

    radioBranchRtIfFailCleared TRAP-TYPE
        ENTERPRISE pdh-al 
        DESCRIPTION "
            This event is generated by  NE when a radioBranchRtIfFailAlarm is cleared
            The data passed with the event are:
            1) radioBranchId 
            2) radioBranchRtIfFaillAlarm
            3) equipTrapAcknowledge code number"
        ::= 1030

    radioBranchLocalOduAlarmSynthesisSet TRAP-TYPE
        ENTERPRISE pdh-al 
        DESCRIPTION "
            This event is generated by  NE when a radioBranchLocalOduAlarmSynthesis 
            Alarm is set
            The data passed with the event are:
            1) radioBranchId 
            2) radioBranchLocalOduAlarmSynthesis
            3) equipTrapAcknowledge code number"
        ::= 1031

    radioBranchLocalOduAlarmSynthesisCleared TRAP-TYPE
        ENTERPRISE pdh-al 
        DESCRIPTION "
            This event is generated by  NE when a radioBranchLocalOduAlarmSynthesis 
            Alarm is cleared
            The data passed with the event are:
            1) radioBranchId 
            2) radioBranchLocalOduAlarmSynthesis
            3) equipTrapAcknowledge code number"
        ::= 1032

    radioBranchRemoteOduAlarmSynthesisSet TRAP-TYPE
        ENTERPRISE pdh-al 
        DESCRIPTION "
            This event is generated by  NE when a radioBranchRemoteOduAlarmSynthesis 
            Alarm is set
            The data passed with the event are:
            1) radioBranchId 
            2) radioBranchRemoteOduAlarmSynthesis
            3) equipTrapAcknowledge code number"
        ::= 1033

    radioBranchRemoteOduAlarmSynthesisCleared TRAP-TYPE
        ENTERPRISE pdh-al 
        DESCRIPTION "
            This event is generated by  NE when a radioBranchRemoteOduAlarmSynthesis 
            Alarm is cleared
            The data passed with the event are:
            1) radioBranchId 
            2) radioBranchRemoteOduAlarmSynthesis
            3) equipTrapAcknowledge code number"
        ::= 1034

    radioBranchLocalRimAlarmSynthesisSet TRAP-TYPE
        ENTERPRISE pdh-al 
        DESCRIPTION "
            This event is generated by  NE when a radioBranchLocalRimAlarmSynthesis 
            Alarm is set
            The data passed with the event are:
            1) radioBranchId 
            2) radioBranchLocalRimAlarmSynthesis
            3) equipTrapAcknowledge code number"
        ::= 1035

    radioBranchLocalRimAlarmSynthesisCleared TRAP-TYPE
        ENTERPRISE pdh-al 
        DESCRIPTION "
            This event is generated by  NE when a radioBranchLocalRimAlarmSynthesis 
            Alarm is cleared
            The data passed with the event are:
            1) radioBranchId 
            2) radioBranchLocalRimAlarmSynthesis
            3) equipTrapAcknowledge code number"
        ::= 1036

    radioBranchRemoteRimAlarmSynthesisSet TRAP-TYPE
        ENTERPRISE pdh-al 
        DESCRIPTION "
            This event is generated by  NE when a radioBranchRemoteRimAlarmSynthesis 
            Alarm is set
            The data passed with the event are:
            1) radioBranchId 
            2) radioBranchRemoteRimAlarmSynthesis
            3) equipTrapAcknowledge code number"
        ::= 1037

    radioBranchRemoteRimAlarmSynthesisCleared TRAP-TYPE
        ENTERPRISE pdh-al 
        DESCRIPTION "
            This event is generated by  NE when a radioBranchRemoteOduAlarmSynthesis 
            Alarm is cleared
            The data passed with the event are:
            1) radioBranchId 
            2) radioBranchRemoteRimAlarmSynthesis
            3) equipTrapAcknowledge code number"
        ::= 1038

    radioBranchRxActiveStatusSet  TRAP-TYPE
        ENTERPRISE  pdh-al
        DESCRIPTION
            "This event is generated by  NE when  a RadioBranchRxActiveStatus  is 
             set The data passed with the event are:
             1) RadioBranchId
             2) radioBranchRxActiveStatus
             3) equipTrapAcknowledge code number"
        ::= 1039

    radioBranchRxActiveStatusClear  TRAP-TYPE
        ENTERPRISE  pdh-al
        DESCRIPTION
           "This event is generated by  NE when  a RadioBranchRxActiveStatus  is 
            cleared  The data passed with the event are:
            1) RadioBranchId
            2) radioBranchRxActiveStatus
            3) equipTrapAcknowledge code number"
        ::= 1040

    radioBranchTxActiveStatusSet  TRAP-TYPE
        ENTERPRISE  pdh-al
        DESCRIPTION
           "This event is generated by  NE when  a RadioBranchTxActiveStatus  is 
            set The data passed with the event are:
            1) RadioBranchId
            2) radioBranchTxActiveStatus
            3) equipTrapAcknowledge code number"
        ::= 1041

    radioBranchTxActiveStatusClear  TRAP-TYPE
        ENTERPRISE  pdh-al
        DESCRIPTION
           "This event is generated by  NE when  a RadioBranchTxActiveStatus  is 
            cleared  The data passed with the event are:
            1) RadioBranchId
            2) radioBranchTxActiveStatus
            3) equipTrapAcknowledge code number"
        ::= 1042

    radioBranchPrxChange  TRAP-TYPE
        ENTERPRISE  pdh-al
        DESCRIPTION
           "This event is generated by NE when RadioBranchPrx is changed, in 
            modulus, more than radioBranchPrxHysteresisValue from last TRAP
            The data passed with the event are:
            1) RadioBranchId
            2) radioBranchPrx
            3) equipTrapAcknowledge code number"
        ::= 1043

    radioBranchPtxChange  TRAP-TYPE
        ENTERPRISE  pdh-al
        DESCRIPTION
           "This event is generated by NE when RadioBranchPtx is changed, in   
            modulus, more than   radioBranchPtxHysteresisValue from last TRAP
            The data passed with the event are:
            1) RadioBranchId
            2) radioBranchPtx
            3) equipTrapAcknowledge code number"
        ::= 1044

    radioBranchRtOduIduCommAlarmSet TRAP-TYPE
        ENTERPRISE pdh-al 
        DESCRIPTION "
            This event is generated by  NE when a 
            radioBranchRtOduIduCommAlarm is set
            The data passed with the event are:
            1) radioBranchId 
            2) OduIduCommunicationAlarm
            3) equipTrapAcknowledge code number"
        ::= 1045

    radioBranchRtOduIduCommAlarmCleared  TRAP-TYPE
        ENTERPRISE pdh-al 
        DESCRIPTION "
            This event is generated by  NE when a 
            radioBranchRtOduIduCommAlarm is cleared
            The data passed with the event are:
            1) radioBranchId 
            2) BaseBandOduIduCommAlarm
            3) equipTrapAcknowledge code number"
        ::= 1046



----------------------------------------------------------------------------------
--  4.12  PERFORMANCE MONITORING G.826 GROUP
----------------------------------------------------------------------------------
--  The following objects are used to manage the G.826 Performance Monitoring function.
----------------------------------------------------------------------------------
--  The following table contains the records with  the counters used to evaluate the Performance Monitoring  of the radio according to G.826 specification.
----------------------------------------------------------------------------------

    pmG826CounterTable  OBJECT-TYPE
        SYNTAX      SEQUENCE OF  PmG826CounterRecord
        ACCESS      not-accessible
        STATUS      mandatory
        DESCRIPTION 
            "Table with PmG826 records: one record for 1+0 configuration and two 
             record for 1+1 configuration."
        ::=  { pmG826  1 }

    pmG826CounterRecord  OBJECT-TYPE
        SYNTAX      PmG826CounterRecord
        ACCESS      not-accessible
        STATUS      mandatory
        DESCRIPTION 
            "PmG826  record"
        INDEX { pmG826BranchId, pmG826CounterBlockId }
        ::=  { pmG826CounterTable 1 }

    PmG826CounterRecord  ::=
        SEQUENCE {
            pmG826BranchId              INTEGER,
            pmG826CounterBlockId        INTEGER,
            pmG826CounterBlockType      INTEGER,
            pmG826CounterBlockStatus    INTEGER,
            pmG826CounterTimeStamp      TimeTicks,
            pmG826BBECounter            Counter,
            pmG826ESCounter             Counter,
            pmG826SESCounter            Counter,
            pmG826UASCounter            Counter,
            pmG826SEPCounter            Counter
        }

    pmG826BranchId  OBJECT-TYPE
        SYNTAX      INTEGER
        ACCESS      read-only
        STATUS      mandatory
        DESCRIPTION 
            "This object  identifies  the  Radio Branch"
       ::=  { pmG826CounterRecord  1 }

    pmG826CounterBlockId  OBJECT-TYPE
        SYNTAX      INTEGER
        ACCESS      read-only
        STATUS      mandatory
        DESCRIPTION 
            "This object  identifies  the counters block and the counter type 
             according to the following code:
             1  Current Daily counters
             2  Daily counters (Day before counters)
             3  Current 15 minutes counters
             4  15 minutes counters N. 1 (The most recent 15 minutes counters)
                 ..............................................
             n  15 minutes counters N. n
             20 15 minutes counters N.16(The oldest 15 min.counters 4 hours before)"
        ::=  { pmG826CounterRecord  2 }

    pmG826CounterBlockType  OBJECT-TYPE
        SYNTAX      INTEGER {
                            daily       (1),
                            fifteen-min (2)
                          }
        ACCESS      read-only
        STATUS      mandatory
        DESCRIPTION 
            "The type of the counter block"
        ::=  { pmG826CounterRecord  3}

    pmG826CounterBlockStatus OBJECT-TYPE
        SYNTAX      INTEGER {
                            meaningless   (1),
                            meaningfull   (2),
                            incomplete    (3),
                            dummy         (4),
                            lost          (5),
                            restarted     (6)
                          }
        ACCESS      read-only
        STATUS      mandatory
        DESCRIPTION 
            "status of the block counter"
        ::=  { pmG826CounterRecord  4 }

    pmG826CounterTimeStamp OBJECT-TYPE
        SYNTAX      TimeTicks
        ACCESS      read-only
        STATUS      mandatory
        DESCRIPTION
            "The object is the time when the performance record is closed reported
             as the second number since 1/1/70."
        ::=  { pmG826CounterRecord  5 }
    
    pmG826BBECounter  OBJECT-TYPE
        SYNTAX      Counter
        ACCESS      read-only
        STATUS      mandatory
        DESCRIPTION 
            "G826  BBE  counter"
        ::=  { pmG826CounterRecord  6 }

    pmG826ESCounter  OBJECT-TYPE
        SYNTAX      Counter
        ACCESS      read-only
        STATUS      mandatory
        DESCRIPTION 
            "G826  Es  counter"
        ::=  { pmG826CounterRecord  7 }

    pmG826SESCounter  OBJECT-TYPE
        SYNTAX      Counter
        ACCESS      read-only
        STATUS      mandatory
        DESCRIPTION 
            "G826  SES  counter"
        ::=  { pmG826CounterRecord  8 }

    pmG826UASCounter  OBJECT-TYPE
        SYNTAX      Counter
        ACCESS      read-only
        STATUS      mandatory
        DESCRIPTION 
            "G826  UAS  counter"
        ::=  { pmG826CounterRecord  9 }

    pmG826SEPCounter  OBJECT-TYPE
        SYNTAX      Counter
        ACCESS      read-only
        STATUS      mandatory
        DESCRIPTION 
            "G826  SEP  counter"
        ::=  { pmG826CounterRecord 10 }



----------------------------------------------------------------------------------
--  The following table contains the records used to manage the P.M. on both radio branch and  the threshold cross alarms
----------------------------------------------------------------------------------

    pmG826TpClassTable  OBJECT-TYPE
        SYNTAX      SEQUENCE OF  PmG826TpClassRecord
        ACCESS      not-accessible
        STATUS      mandatory
        DESCRIPTION 
            "Table with PmG826TpClass records: one record for 1+0 configuration and 
             two record for 1+1 configuration."
        ::=  { pmG826  2 }

    pmG826TpClassRecord  OBJECT-TYPE
        SYNTAX      PmG826TpClassRecord
        ACCESS      not-accessible
        STATUS      mandatory
        DESCRIPTION 
            "PmG826TpClass  record"
        INDEX { pmG826TpClassBranchId }
        ::=  { pmG826TpClassTable 1 }

    PmG826TpClassRecord  ::=
        SEQUENCE {
            pmG826TpClassBranchId         INTEGER,
            pmG826TpClassStartStop        INTEGER,
            pmG826TpClassCounterClear     INTEGER,
            pmG826TpClassAlarmClear       INTEGER,
            pmG826TpClassCounterBuffer    Opaque,
            pmG826TpClass15MEsAlarm       INTEGER,
            pmG826TpClass15MSesAlarm      INTEGER,
            pmG826TpClass24HEsAlarm       INTEGER,
            pmG826TpClass24HSesAlarm      INTEGER,
            pmG826TpClassUasAlarm         INTEGER,
            pmG826TpClassTimeStamp        TimeTicks,
            pmG826TpClass15MSepAlarm      INTEGER,
            pmG826TpClass24HSepAlarm      INTEGER,
            pmG826TpClassLabel            DisplayString
        }

    pmG826TpClassBranchId  OBJECT-TYPE
        SYNTAX      INTEGER
        ACCESS      read-only
        STATUS      mandatory
        DESCRIPTION 
            "This object  identifies  the  Radio Branch"
        ::=  { pmG826TpClassRecord  1 }

    pmG826TpClassStartStop  OBJECT-TYPE
        SYNTAX      INTEGER {
                              start   (1),
                              stop    (2)
                            }
        ACCESS      read-write
        STATUS      mandatory
        DESCRIPTION 
            "This object is used to start and to stop the Perfomance Monitoring 
             counter evaluation"
        ::=  { pmG826TpClassRecord  2 }

    pmG826TpClassCounterClear  OBJECT-TYPE
        SYNTAX      INTEGER {
                              clear   (1)
                            }
        ACCESS      write-only
        STATUS      mandatory
        DESCRIPTION 
            "This object is used to clear  the Perfomance Monitoring counters."
        ::=  { pmG826TpClassRecord  3 }

    pmG826TpClassAlarmClear  OBJECT-TYPE
        SYNTAX      INTEGER {
                              clear   (1)
                            }
        ACCESS      write-only
        STATUS      mandatory
        DESCRIPTION 
            "This object is used to clear the Perfomance Monitoring threshold cross alarms"
        ::=  { pmG826TpClassRecord  4 }

    pmG826TpClassCounterBuffer  OBJECT-TYPE
        SYNTAX      Opaque
        ACCESS      read-only
        STATUS      mandatory
        DESCRIPTION 
            "This object  is used to transfer  in only one request all G.826 
             Counters (16x15Minutes and 1x1Day).
             It is used by a dedicated  P.M. application on the Manager."
        ::=  { pmG826TpClassRecord  5 }

    pmG826TpClass15MEsAlarm  OBJECT-TYPE
        SYNTAX      INTEGER {
                              cleared                   (1),
                              activeReportable-Status   (2),
                              activeReportable-Warning  (3),
                              activeReportable-Minor    (4),
                              activeReportable-Major    (5),
                              activeReportable-Critical (6)
                            }
        ACCESS      read-only
        STATUS      mandatory
        DESCRIPTION 
            "15 minutes  ES threshold cross alarm  with associated Severity."
        ::=  { pmG826TpClassRecord  6 }

    pmG826TpClass15MSesAlarm  OBJECT-TYPE
        SYNTAX      INTEGER {
                              cleared                   (1),
                              activeReportable-Status   (2),
                              activeReportable-Warning  (3),
                              activeReportable-Minor    (4),
                              activeReportable-Major    (5),
                              activeReportable-Critical (6)
                            }
        ACCESS      read-only
        STATUS      mandatory
        DESCRIPTION 
            "15 minutes  SES threshold cross alarm  with associated Severity."
        ::=  { pmG826TpClassRecord  7 }

    pmG826TpClass24HEsAlarm  OBJECT-TYPE
        SYNTAX      INTEGER {
                              cleared                   (1),
                              activeReportable-Status   (2),
                              activeReportable-Warning  (3),
                              activeReportable-Minor    (4),
                              activeReportable-Major    (5),
                              activeReportable-Critical (6)
                            }
        ACCESS      read-only
        STATUS      mandatory
        DESCRIPTION 
            "Daily  ES threshold cross alarm  with associated Severity."
        ::=  { pmG826TpClassRecord  8 }

    pmG826TpClass24HSesAlarm  OBJECT-TYPE
        SYNTAX      INTEGER {
                              cleared                   (1),
                              activeReportable-Status   (2),
                              activeReportable-Warning  (3),
                              activeReportable-Minor    (4),
                              activeReportable-Major    (5),
                              activeReportable-Critical (6)
                            }
        ACCESS      read-only
        STATUS      mandatory
        DESCRIPTION 
            "Daily  SES threshold cross alarm  with associated Severity."
        ::=  { pmG826TpClassRecord  9 }

    pmG826TpClassUasAlarm  OBJECT-TYPE
        SYNTAX      INTEGER {
                              cleared                   (1),
                              activeReportable-Status   (2),
                              activeReportable-Warning  (3),
                              activeReportable-Minor    (4),
                              activeReportable-Major    (5),
                              activeReportable-Critical (6)
                            }
        ACCESS      read-only
        STATUS      mandatory
        DESCRIPTION 
            "UAS alarm with associated Severity."
        ::=  { pmG826TpClassRecord  10 }

    pmG826TpClassTimeStamp   OBJECT-TYPE
        SYNTAX      TimeTicks
        ACCESS      read-only
        STATUS      mandatory
        DESCRIPTION
            " "
        ::=  { pmG826TpClassRecord   11 }

    pmG826TpClass15MSepAlarm  OBJECT-TYPE
        SYNTAX      INTEGER {
                              cleared                   (1),
                              activeReportable-Status   (2),
                              activeReportable-Warning  (3),
                              activeReportable-Minor    (4),
                              activeReportable-Major    (5),
                              activeReportable-Critical (6)
                            }
        ACCESS      read-only
        STATUS      mandatory
        DESCRIPTION 
            "15 minutes  SEP threshold cross alarm  with associated Severity."
        ::=  { pmG826TpClassRecord  12 }

    pmG826TpClass24HSepAlarm  OBJECT-TYPE
        SYNTAX      INTEGER {
                              cleared                   (1),
                              activeReportable-Status   (2),
                              activeReportable-Warning  (3),
                              activeReportable-Minor    (4),
                              activeReportable-Major    (5),
                              activeReportable-Critical (6)
                            }
        ACCESS      read-only
        STATUS      mandatory
        DESCRIPTION 
            "Daily SEP threshold cross alarm  with associated Severity."
        ::=  { pmG826TpClassRecord  13 }

    pmG826TpClassLabel  OBJECT-TYPE
        SYNTAX      DisplayString   (SIZE(0..31))
        ACCESS      read-only
        STATUS      mandatory
        DESCRIPTION
            "ASCII string used to identify  the Tp class
             pmG826TpClassBranchId = 1 label = Radio 1 
             pmG826TpClassBranchId = 2 label = Radio 2
             pmG826TpClassBranchId = 3 label = Radio (switched)
             pmG826TpClassBranchId = 4 label = Tributary line side
             pmG826TpClassBranchId = 5 label = Tributary radio side"
        ::=  { pmG826TpClassRecord  14 }

----------------------------------------------------------------------------------
--  The following objects are common to both radio branch.
----------------------------------------------------------------------------------

    pmG826NSesSetUAS  OBJECT-TYPE
        SYNTAX      INTEGER
        ACCESS      read-write
        STATUS      mandatory
        DESCRIPTION 
            "Number of SES (according G.826) to set UAS"
        DEFVAL{ 10 }
        ::=  { pmG826  3 }


    pmG826NSesResetUAS  OBJECT-TYPE
        SYNTAX      INTEGER
        ACCESS      read-write
        STATUS      mandatory
        DESCRIPTION 
            "Number of seconds whitout errors (according G.826) to reset UAS"
        DEFVAL{ 10 }
        ::=  { pmG826  4 }

    pmG826NBBESetSES  OBJECT-TYPE
        SYNTAX      INTEGER
        ACCESS      read-write
        STATUS      mandatory
        DESCRIPTION 
            "Percentage of BBE in one second to declare SES"
        DEFVAL{ 30 }
        ::=  { pmG826  5 }

    pmG82615MEsThreshold  OBJECT-TYPE
        SYNTAX      INTEGER
        ACCESS      read-write
        STATUS      mandatory
        DESCRIPTION 
            "Number of ES within 15 minutes to set pmG826TpClass15MEsAlarm 
             (zero value disables the alarm)"
        DEFVAL{ 0 }
        ::=  { pmG826  6 }

    pmG82615MSesThreshold  OBJECT-TYPE
        SYNTAX      INTEGER
        ACCESS      read-write
        STATUS      mandatory
        DESCRIPTION 
            "Number of SES within 15 minutes to set pmG826TpClass15MSesAlarm 
             (zero value disables the alarm)"
        DEFVAL{ 0 }
        ::=  { pmG826 7 }

    pmG82624HEsThreshold  OBJECT-TYPE
        SYNTAX      INTEGER
        ACCESS      read-write
        STATUS      mandatory
        DESCRIPTION 
            "Number of ES within one day to set pmG826TpClass24HEsAlarm 
             (zero value disables the alarm)"
        DEFVAL{ 0 }
        ::=  { pmG826  8 }

    pmG82624HSesThreshold  OBJECT-TYPE
        SYNTAX      INTEGER
        ACCESS      read-write
        STATUS      mandatory
        DESCRIPTION 
            "Number of  SES within 15 minutes to set pmG826TpClass24HsesAlarm
             (zero value disables the alarm)"
        DEFVAL{ 0 }
        ::=  { pmG826  9 }



----------------------------------------------------------------------------------
--  The following objects define the profile of the threshold cross and UAS  alarms:
--
--  The general stucture of the object is the following:
--
--  pmG826<AlarmName>SeverityCode  OBJECT-TYPE
--     SYNTAX    INTEGER {
--                            disable                    (1),
--                            status-trapEnable          (2),
--                            status-trapEnableWithACK   (34),
--                            warning-trapEnable         (3),
--                            warning-trapEnableWithACK  (35),
--                            minor-trapEnable           (4),
--                            minor-trapEnableWithACK    (36),
--                            major-trapEnable           (5),
--                            major-trapEnableWithACK    (37),
--                            critical-trapEnable        (6),
--                            critical-trapEnableWithACK (38),
--                            status-trapDisable         (18),
--                            warning-trapDisable        (19),
--                            minor-trapDisable          (20),
--                            major-trapDisable          (21),
--                            critical-trapDisable       (22)
--                       }
--
--     ACCESS      read-write
--     STATUS      mandatory
--     DESCRIPTION "
--           Define the severity associated to the  <alarm name>  and  
--            enable/disable the trap generation on status  change   event.
--     "  DEFVAL{ x }
--    ::=  { pmG826  y }
----------------------------------------------------------------------------------

    pmG826TpClass15MEsAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the pmG826TpClass15MEsAlarm and  
             enable/disable the trap generation on status change   event."
        DEFVAL  { major-trapEnable }
        ::=  { pmG826  10 }

    pmG826TpClass15MSesAlarmSeverityCode  OBJECT-TYPE
        SYNTAX      INTEGER {
                              disable                    (1),
                              status-trapEnable          (2),
                              status-trapEnableWithACK   (34),
                              warning-trapEnable         (3),
                              warning-trapEnableWithACK  (35),
                              minor-trapEnable           (4),
                              minor-trapEnableWithACK    (36),
                              major-trapEnable           (5),
                              major-trapEnableWithACK    (37),
                              critical-trapEnable        (6),
                              critical-trapEnableWithACK (38),
                              status-trapDisable         (18),    
                              warning-trapDisable        (19),
                              minor-trapDisable          (20),
                              major-trapDisable          (21),
                              critical-trapDisable       (22)
                            }
        ACCESS      read-write
        STATUS      mandatory
        DESCRIPTION 
            "Define the severity associated to the pmG826TpClass15MSesAlarm and  
             enable/disable the trap generation on status change   event."
        DEFVAL  { major-trapEnable }
        ::=  { pmG826  11 }

    pmG826TpClass24HEsAlarmSeverityCode  OBJECT-TYPE
        SYNTAX      INTEGER {
                              disable                    (1),
                              status-trapEnable          (2),
                              status-trapEnableWithACK   (34),
                              warning-trapEnable         (3),
                              warning-trapEnableWithACK  (35),
                              minor-trapEnable           (4),
                              minor-trapEnableWithACK    (36),
                              major-trapEnable           (5),
                              major-trapEnableWithACK    (37),
                              critical-trapEnable        (6),
                              critical-trapEnableWithACK (38),
                              status-trapDisable         (18),    
                              warning-trapDisable        (19),
                              minor-trapDisable          (20),
                              major-trapDisable          (21),
                              critical-trapDisable       (22)
                            }
        ACCESS      read-write
        STATUS      mandatory
        DESCRIPTION 
            "Define the severity associated to the pmG826TpClass15MEsAlarm and  
             enable/disable the trap generation on status change  event."
        DEFVAL  { major-trapEnable }
        ::=  { pmG826  12 }

    pmG826TpClass24HSesAlarmSeverityCode  OBJECT-TYPE
        SYNTAX      INTEGER {
                              disable                    (1),
                              status-trapEnable          (2),
                              status-trapEnableWithACK   (34),
                              warning-trapEnable         (3),
                              warning-trapEnableWithACK  (35),
                              minor-trapEnable           (4),
                              minor-trapEnableWithACK    (36),
                              major-trapEnable           (5),
                              major-trapEnableWithACK    (37),
                              critical-trapEnable        (6),
                              critical-trapEnableWithACK (38),
                              status-trapDisable         (18),    
                              warning-trapDisable        (19),
                              minor-trapDisable          (20),
                              major-trapDisable          (21),
                              critical-trapDisable       (22)
                            }
        ACCESS      read-write
        STATUS      mandatory
        DESCRIPTION 
            "Define the severity associated to the pmG826TpClass15MSesAlarm and 
             enable/disable the trap generation on status  change   event."
        DEFVAL  { major-trapEnable }
        ::=  { pmG826  13 }

    pmG826TpClassUASAlarmSeverityCode  OBJECT-TYPE
        SYNTAX      INTEGER {
                              disable                    (1),
                              status-trapEnable          (2),
                              status-trapEnableWithACK   (34),
                              warning-trapEnable         (3),
                              warning-trapEnableWithACK  (35),
                              minor-trapEnable           (4),
                              minor-trapEnableWithACK    (36),
                              major-trapEnable           (5),
                              major-trapEnableWithACK    (37),
                              critical-trapEnable        (6),
                              critical-trapEnableWithACK (38),
                              status-trapDisable         (18),    
                              warning-trapDisable        (19),
                              minor-trapDisable          (20),
                              major-trapDisable          (21),
                              critical-trapDisable       (22)
                            }
        ACCESS      read-write
        STATUS      mandatory
        DESCRIPTION 
            "Define the severity associated to the pmG826TpClassUASAlarm and  
             enable/disable the trap generation on status  change   event."
        DEFVAL{ major-trapEnable }
        ::=  { pmG826  14 }

    pmG826BlockFrame1x2Mbit  OBJECT-TYPE
        SYNTAX      INTEGER    (1..64)
        ACCESS      read-write
        STATUS      mandatory
        DESCRIPTION 
            "Number of  frames per block when the capacity is 1x2Mbit/s"
        ::=  { pmG826  15 }

    pmG826BlockFrame2x2Mbit  OBJECT-TYPE
        SYNTAX      INTEGER    (1..64)
        ACCESS      read-write
        STATUS      mandatory
        DESCRIPTION 
            "Number of  frames per block when the capacity is 2x2Mbit/s"
        ::=  { pmG826  16 }

    pmG826BlockFrame4x2Mbit  OBJECT-TYPE
        SYNTAX      INTEGER    (1..64)
        ACCESS      read-write
        STATUS      mandatory
        DESCRIPTION 
            "Number of  frames per block when the capacity is 4x2Mbit/s"
        ::=  { pmG826  17 }

    pmG826BlockFrame8x2Mbit  OBJECT-TYPE
        SYNTAX      INTEGER    (1..64)
        ACCESS      read-write
        STATUS      mandatory
        DESCRIPTION 
            "Number of  frames per block when the capacity is 8x2Mbit/s"
        ::=  { pmG826  18 }

    pmG826BlockFrame16x2Mbit  OBJECT-TYPE
        SYNTAX      INTEGER    (1..64)
        ACCESS      read-write
        STATUS      mandatory
        DESCRIPTION 
            "Number of  frames per block when the capacity is 16x2Mbit/s or 1x34Mbit/s"
        ::=  { pmG826  19 }

    pmG82615MSepThreshold  OBJECT-TYPE
        SYNTAX      INTEGER
        ACCESS      read-write
        STATUS      mandatory
        DESCRIPTION 
            "Number of SEP within 15 minutes to set pmG826TpClass15MSepAlarm 
             (zero value disables the alarm)"
        DEFVAL{ 0 }
        ::=  { pmG826 20 }

    pmG82624HSepThreshold  OBJECT-TYPE
        SYNTAX      INTEGER
        ACCESS      read-write
        STATUS      mandatory
        DESCRIPTION 
            "Number of SEP within one day to set pmG826TpClass24HSepAlarm 
             (zero value disables the alarm)"
        DEFVAL{ 0 }
        ::=  { pmG826  21 }

    pmG826TpClass15MSepAlarmSeverityCode  OBJECT-TYPE
        SYNTAX      INTEGER {
                              disable                    (1),
                              status-trapEnable          (2),
                              status-trapEnableWithACK   (34),
                              warning-trapEnable         (3),
                              warning-trapEnableWithACK  (35),
                              minor-trapEnable           (4),
                              minor-trapEnableWithACK    (36),
                              major-trapEnable           (5),
                              major-trapEnableWithACK    (37),
                              critical-trapEnable        (6),
                              critical-trapEnableWithACK (38),
                              status-trapDisable         (18),    
                              warning-trapDisable        (19),
                              minor-trapDisable          (20),
                              major-trapDisable          (21),
                              critical-trapDisable       (22)
                            }
        ACCESS      read-write
        STATUS      mandatory
        DESCRIPTION 
            "Define the severity associated to the pmG826TpClass15MSepAlarm and  
             enable/disable the trap generation on status change   event."
        DEFVAL  { major-trapEnable }
        ::=  { pmG826  22 }

    pmG826TpClass24HSepAlarmSeverityCode  OBJECT-TYPE
        SYNTAX      INTEGER {
                              disable                    (1),
                              status-trapEnable          (2),
                              status-trapEnableWithACK   (34),
                              warning-trapEnable         (3),
                              warning-trapEnableWithACK  (35),
                              minor-trapEnable           (4),
                              minor-trapEnableWithACK    (36),
                              major-trapEnable           (5),
                              major-trapEnableWithACK    (37),
                              critical-trapEnable        (6),
                              critical-trapEnableWithACK (38),
                              status-trapDisable         (18),    
                              warning-trapDisable        (19),
                              minor-trapDisable          (20),
                              major-trapDisable          (21),
                              critical-trapDisable       (22)
                            }
        ACCESS      read-write
        STATUS      mandatory
        DESCRIPTION 
            "Define the severity associated to the pmG826TpClass24HSepAlarm and  
             enable/disable the trap generation on status change  event."
        DEFVAL  { major-trapEnable }
        ::=  { pmG826  23 }



----------------------------------------------------------------------------------
--The G.826 Performance group generates the following  trap
----------------------------------------------------------------------------------

    pmG826TpClass15MEsAlarmSet  TRAP-TYPE
        ENTERPRISE pdh-al 
        DESCRIPTION "
            This event is generated by  NE when  a pmG826TpClass15MEsAlarm is set
            The data passed with the event are:
              1) TpClassLabel
              2) TpClass15MEsAlarm
              3) equipTrapAcknowledge code number"
        ::= 1101

    pmG826TpClass15MEsAlarmCleared  TRAP-TYPE
        ENTERPRISE pdh-al 
        DESCRIPTION "
            This event is generated by  NE when a pmG826TpClass15MEsAlarm is cleared
            The data passed with the event are:
              1) TpClassLabel
              2) TpClass15MEsAlarm
              3) equipTrapAcknowledge code number"
        ::= 1102

    pmG826TpClass15MSesAlarmSet  TRAP-TYPE
        ENTERPRISE pdh-al 
        DESCRIPTION "
            This event is generated by  NE when  a pmG826TpClass15MSesAlarm is set
            The data passed with the event are:
              1) TpClassLabel
              2) TpClass15MSesAlarm
              3) equipTrapAcknowledge code number"
        ::= 1103

    pmG826TpClass15MSesAlarmCleared  TRAP-TYPE
        ENTERPRISE pdh-al 
        DESCRIPTION "
            This event is generated by  NE when a pmG826TpClass15MSesAlarm is 
            cleared  The data passed with the event are:
              1) TpClassLabel
              2) TpClass15MSesAlarm
              3) equipTrapAcknowledge code number"
        ::= 1104

    pmG826TpClass24HEsAlarmSet  TRAP-TYPE
        ENTERPRISE pdh-al 
        DESCRIPTION "
            This event is generated by  NE when  a pmG826TpClass24HEsAlarm is set
            The data passed with the event are:
              1) TpClassLabel
              2) TpClass24HEsAlarm
              3) equipTrapAcknowledge code number"
        ::= 1105

    pmG826TpClass24HEsAlarmCleared  TRAP-TYPE
        ENTERPRISE pdh-al 
        DESCRIPTION "
            This event is generated by  NE when a pmG826TpClass24HEsAlarm is cleared
            The data passed with the event are:
              1) TpClassLabel
              2) TpClass24HEsAlarm
              3) equipTrapAcknowledge code number"
        ::= 1106

    pmG826TpClass24HSesAlarmSet  TRAP-TYPE
        ENTERPRISE pdh-al 
        DESCRIPTION "
            This event is generated by  NE when  a pmG826TpClass24HSesAlarm is set
            The data passed with the event are:
              1) TpClassLabel
              2) TpClass24HSesAlarm
              3) equipTrapAcknowledge code number"
        ::= 1107

    pmG826TpClass24HSesAlarmCleared  TRAP-TYPE
        ENTERPRISE pdh-al 
        DESCRIPTION "
            This event is generated by  NE when a pmG826TpClass24HSesAlarm is 
            cleared The data passed with the event are:
              1) TpClassLabel
              2) TpClass24HSesAlarm
              3) equipTrapAcknowledge code number"
        ::= 1108

    pmG826TpClassUASAlarmSet  TRAP-TYPE
        ENTERPRISE pdh-al 
        DESCRIPTION "
            This event is generated by  NE when  a pmG826TpClass24HEsAlarm is set
            The data passed with the event are:
              1) TpClassLabel
              2) TpClassUASAlarm
              3) equipTrapAcknowledge code number"
        ::= 1109

    pmG826TpClassUASAlarmCleared  TRAP-TYPE
        ENTERPRISE pdh-al 
        DESCRIPTION "
            This event is generated by  NE when a pmG826TpClass24HEsAlarm is cleared
            The data passed with the event are:
              1) TpClassLabel
              2) TpClassUASAlarm
              3) equipTrapAcknowledge code number"
        ::= 1110

    pmG826TpClass15MSepAlarmSet  TRAP-TYPE
        ENTERPRISE pdh-al 
        DESCRIPTION "
            This event is generated by  NE when  a pmG826TpClass15MSepAlarm is set
            The data passed with the event are:
              1) TpClassLabel
              2) TpClass15MSepAlarm
              3) equipTrapAcknowledge code number"
        ::= 1111

    pmG826TpClass15MSepAlarmCleared  TRAP-TYPE
        ENTERPRISE pdh-al 
        DESCRIPTION "
            This event is generated by  NE when a pmG826TpClass15MSepAlarm is 
            cleared  The data passed with the event are:
              1) TpClassLabel
              2) TpClass15MSepAlarm
              3) equipTrapAcknowledge code number"
        ::= 1112

    pmG826TpClass24HSepAlarmSet  TRAP-TYPE
        ENTERPRISE pdh-al 
        DESCRIPTION "
            This event is generated by  NE when  a pmG826TpClass24HSepAlarm is set
            The data passed with the event are:
              1) TpClassLabel
              2) TpClass24HSepAlarm
              3) equipTrapAcknowledge code number"
        ::= 1113

    pmG826TpClass24HSepAlarmCleared  TRAP-TYPE
        ENTERPRISE pdh-al 
        DESCRIPTION "
            This event is generated by  NE when a pmG826TpClass24HSepAlarm is cleared
            The data passed with the event are:
              1) TpClassLabel
              2) TpClass24HSepAlarm
              3) equipTrapAcknowledge code number"
        ::= 1114



----------------------------------------------------------------------------------
--  4.13 PERFORMANCE MONITORING RECEIVED  POWER LEVEL  GROUP
----------------------------------------------------------------------------------
--  The following objects are used to manage the Received Power  Performance Monitoring function.
----------------------------------------------------------------------------------
--  The following table contains the records with  the counters used to monitor  the received  power  of the radio.
----------------------------------------------------------------------------------

    pmRxPwrCounterTable  OBJECT-TYPE
        SYNTAX      SEQUENCE OF  PmRxPwrCounterRecord
        ACCESS      not-accessible
        STATUS      mandatory
        DESCRIPTION 
            "Table with PmRxPwr records: one record for 1+0 configuration and two 
             record for 1+1 configuration."
        ::=  { pmRxPwr  1 }

    pmRxPwrCounterRecord  OBJECT-TYPE
        SYNTAX      PmRxPwrCounterRecord
        ACCESS      not-accessible
        STATUS      mandatory
        DESCRIPTION 
            "PmRxPwr  record"
        INDEX {  pmRxPwrBranchId, pmRxPwrCounterBlockId }
        ::=  { pmRxPwrCounterTable 1 }

    PmRxPwrCounterRecord  ::=
        SEQUENCE {
            pmRxPwrBranchId               INTEGER,
            pmRxPwrCounterBlockId         INTEGER,
            pmRxPwrCounterBlockType       INTEGER,
            pmRxPwrCounterBlockStatus     INTEGER,
            pmRxPwrCounterTimeStamp       TimeTicks,
            pmRxPwrRlts1Counter           Counter,
            pmRxPwrRlts2Counter           Counter,
            pmRxPwrRlts3Counter           Counter,
            pmRxPwrRlts4Counter           Counter,
            pmRxPwrTMMax                  INTEGER,
            pmRxPwrTMMin                  INTEGER
        }

    pmRxPwrBranchId  OBJECT-TYPE
        SYNTAX    INTEGER
        ACCESS      read-only
        STATUS      mandatory
        DESCRIPTION 
            "This object identifies the Radio Branch"
        ::=  { pmRxPwrCounterRecord  1 }

    pmRxPwrCounterBlockId  OBJECT-TYPE
        SYNTAX    INTEGER
        ACCESS      read-only
        STATUS      mandatory
        DESCRIPTION 
            "This object  identifies  the counters block and the counter type 
             according to the following code:
             1  Current Daily counters
             2  Daily counters (Day before counters)
             3  Current 15 minutes counters
             4  15 minutes counters N. 1 (The most recent 15 minutes counters)
                ..............................................
             n  15 minutes counters N. n
             20 15 minutes counters N.16(The oldest 15 min. counters 4 hours before)"
        ::=  { pmRxPwrCounterRecord  2 }

    pmRxPwrCounterBlockType  OBJECT-TYPE
        SYNTAX    INTEGER {
                            daily       (1),
                            fifteen-min (2)
                          }
        ACCESS      read-only
        STATUS      mandatory
        DESCRIPTION 
            "The type of the counter block"
        ::=  { pmRxPwrCounterRecord  3}

    pmRxPwrCounterBlockStatus OBJECT-TYPE
        SYNTAX    INTEGER {
                            meaningless   (1),
                            meaningfull   (2),
                            incomplete    (3),
                            dummy         (4),
                            lost          (5),
                            restarted     (6)
                          }
        ACCESS      read-only
        STATUS      mandatory
        DESCRIPTION 
            "status of the block counter"
        ::=  { pmRxPwrCounterRecord  4 }
  
    pmRxPwrCounterTimeStamp OBJECT-TYPE
        SYNTAX      TimeTicks
        ACCESS      read-only
        STATUS      mandatory
        DESCRIPTION
            "The object is the time when the performance record is closed reported
             as the second number since 1/1/70."
        ::=  { pmRxPwrCounterRecord  5 }

    pmRxPwrRlts1Counter  OBJECT-TYPE
        SYNTAX    Counter
        ACCESS      read-only
        STATUS      mandatory
        DESCRIPTION 
            "Number of seconds when the Received power is less than the threshold 1"
       ::=  { pmRxPwrCounterRecord  6 }

    pmRxPwrRlts2Counter  OBJECT-TYPE
        SYNTAX    Counter
        ACCESS      read-only
        STATUS      mandatory
        DESCRIPTION 
            "Number of seconds when the Received power is less than the threshold 2"
        ::=  { pmRxPwrCounterRecord  7 }

    pmRxPwrRlts3Counter  OBJECT-TYPE
        SYNTAX    Counter
        ACCESS      read-only
        STATUS      mandatory
        DESCRIPTION 
            "Number of seconds when the Received power is less than the threshold 3"
        ::=  { pmRxPwrCounterRecord  8 }

    pmRxPwrRlts4Counter  OBJECT-TYPE
        SYNTAX    Counter
        ACCESS      read-only
        STATUS      mandatory
        DESCRIPTION 
            "Number of seconds when the Received power is less than the threshold 4"
        ::=  { pmRxPwrCounterRecord  9 }

    pmRxPwrTMMax OBJECT-TYPE
        SYNTAX    INTEGER
        ACCESS      read-only
        STATUS      mandatory
        DESCRIPTION
            "Maximum Power Received Level  Tide Mark"
        ::=  { pmRxPwrCounterRecord  10 }

    pmRxPwrTMMin  OBJECT-TYPE
        SYNTAX    INTEGER
        ACCESS      read-only
        STATUS      mandatory
        DESCRIPTION
            "Minimum  Power Received Level  Tide Mark"
        ::=  { pmRxPwrCounterRecord  11 }



----------------------------------------------------------------------------------
--   The following table contains the records used to manage the P.M. on both radio branch and  the threshold cross alarms
----------------------------------------------------------------------------------

    pmRxPwrTpClassTable  OBJECT-TYPE
        SYNTAX      SEQUENCE OF  PmRxPwrTpClassRecord
        ACCESS      not-accessible
        STATUS      mandatory
        DESCRIPTION 
            "Table with PmRxPwrTpClass records: one record for 1+0 configuration 
             and two record for 1+1 configuration."
        ::=  { pmRxPwr  2 }

    pmRxPwrTpClassRecord  OBJECT-TYPE
        SYNTAX      PmRxPwrTpClassRecord
        ACCESS      not-accessible
        STATUS      mandatory
        DESCRIPTION 
            "PmRxPwrTpClass  record"
        INDEX {  pmRxPwrTpClassBranchId }
        ::=  { pmRxPwrTpClassTable 1 }

    PmRxPwrTpClassRecord  ::=
        SEQUENCE {
            pmRxPwrTpClassBranchId          INTEGER,
            pmRxPwrTpClassStartStop         INTEGER,
            pmRxPwrTpClassCounterClear      INTEGER,
            pmRxPwrTpClassAlarmClear        INTEGER,
            pmRxPwrTpClassCounterBuffer     Opaque,
            pmRxPwrTpClass15MRlts1Alarm     INTEGER,
            pmRxPwrTpClass15MRlts2Alarm     INTEGER,
            pmRxPwrTpClass15MRlts3Alarm     INTEGER,
            pmRxPwrTpClass15MRlts4Alarm     INTEGER,
            pmRxPwrTpClass24HRlts1Alarm     INTEGER,
            pmRxPwrTpClass24HRlts2Alarm     INTEGER,
            pmRxPwrTpClass24HRlts3Alarm     INTEGER,
            pmRxPwrTpClass24HRlts4Alarm     INTEGER,
            pmRxPwrTpClassTimeStamp         TimeTicks
        }

    pmRxPwrTpClassBranchId  OBJECT-TYPE
        SYNTAX    INTEGER
        ACCESS      read-only
        STATUS      mandatory
        DESCRIPTION 
            "This object  identifies  the  Radio Branch"
        ::=  { pmRxPwrTpClassRecord  1 }

    pmRxPwrTpClassStartStop  OBJECT-TYPE
        SYNTAX    INTEGER {
                            start   (1),
                            stop    (2)
                          }
        ACCESS      read-write
        STATUS      mandatory
        DESCRIPTION 
            "This object is used to start and to stop the Perfomance Monitoring 
             counter evaluation"
        ::=  { pmRxPwrTpClassRecord  2 }

    pmRxPwrTpClassCounterClear  OBJECT-TYPE
        SYNTAX    INTEGER {
                            clear   (1)
                          }
        ACCESS      write-only
        STATUS      mandatory
        DESCRIPTION 
            "This object is used to clear  the Perfomance Monitoring counters."
        ::=  { pmRxPwrTpClassRecord  3 }

    pmRxPwrTpClassAlarmClear  OBJECT-TYPE
        SYNTAX    INTEGER {
                            clear   (1)
                          }
        ACCESS      write-only
        STATUS      mandatory
        DESCRIPTION 
            "This object is used to clear  the Perfomance Monitoring threshold cross 
             alarms"
        ::=  { pmRxPwrTpClassRecord  4 }

    pmRxPwrTpClassCounterBuffer  OBJECT-TYPE
        SYNTAX      Opaque
        ACCESS      read-only
        STATUS      mandatory
        DESCRIPTION 
            "This object  is used to transfer  in only one request all Rx Power  
             Counters (16x15Minutes and 1x1Day).
             It is used by a dedicated  P.M. application on the Manager."
        ::=  { pmRxPwrTpClassRecord  5 }

    pmRxPwrTpClass15MRlts1Alarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "15 minutes  Rlts1  threshold cross alarm  with associated Severity."
        ::=  { pmRxPwrTpClassRecord  6 }

    pmRxPwrTpClass15MRlts2Alarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "15 minutes  Rlts2  threshold cross alarm  with associated Severity."
        ::=  { pmRxPwrTpClassRecord  7 }

    pmRxPwrTpClass15MRlts3Alarm  OBJECT-TYPE
        SYNTAX    INTEGER {
                            cleared                   (1),
                            activeReportable-Status   (2),
                            activeReportable-Warning  (3),
                            activeReportable-Minor    (4),
                            activeReportable-Major    (5),
                            activeReportable-Critical (6)
                        }
        ACCESS      read-only
        STATUS      mandatory
        DESCRIPTION 
            "15 minutes  Rlts3  threshold cross alarm  with associated Severity."
        ::=  { pmRxPwrTpClassRecord  8 }

    pmRxPwrTpClass15MRlts4Alarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "15 minutes  Rlts4  threshold cross alarm  with associated Severity."
        ::=  { pmRxPwrTpClassRecord  9 }

    pmRxPwrTpClass24HRlts1Alarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "Daily Rlts1 threshold cross alarm  with associated Severity."
        ::=  { pmRxPwrTpClassRecord  10 }

    pmRxPwrTpClass24HRlts2Alarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "Daily  Rlts2  threshold cross alarm  with associated Severity."
        ::=  { pmRxPwrTpClassRecord  11 }

    pmRxPwrTpClass24HRlts3Alarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "Daily   Rlts3  threshold cross alarm  with associated Severity."
        ::=  { pmRxPwrTpClassRecord  12 }

    pmRxPwrTpClass24HRlts4Alarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "Daily   Rlts4  threshold cross alarm  with associated Severity."
        ::=  { pmRxPwrTpClassRecord  13 }

    pmRxPwrTpClassTimeStamp OBJECT-TYPE
        SYNTAX      TimeTicks
        ACCESS      read-only
        STATUS      mandatory
        DESCRIPTION 
            "The object is the time when the performance record is closed reported
             as the second number since 1/1/70."
        ::=  { pmRxPwrTpClassRecord  14 }



----------------------------------------------------------------------------------
--  The following objects are common to both radio branches.
----------------------------------------------------------------------------------

    pmRxPwr24HRlts1Threshold  OBJECT-TYPE
        SYNTAX      INTEGER
        ACCESS      read-write
        STATUS      mandatory
        DESCRIPTION 
            "Number of  seconds  within a day  to set pmRxPwrTpClass24HRlts1Alarm 
             (zero value disables the alarm)"
        DEFVAL  { 0 }
        ::=  { pmRxPwr  3}

    pmRxPwr24HRlts2Threshold  OBJECT-TYPE
        SYNTAX      INTEGER
        ACCESS      read-write
        STATUS      mandatory
        DESCRIPTION 
            "Number of  seconds  within a day  to set pmRxPwrTpClass24HRlts2Alarm 
             (zero value disables the alarm)"
        DEFVAL  { 0 }
        ::=  { pmRxPwr  4}

    pmRxPwr24HRlts3Threshold  OBJECT-TYPE
        SYNTAX      INTEGER
        ACCESS      read-write
        STATUS      mandatory
        DESCRIPTION 
            "Number of  seconds  within a day  to set pmRxPwrTpClass24HRlts3Alarm 
             (zero value disables the alarm)"
        DEFVAL  { 0 }
        ::=  { pmRxPwr  5}

    pmRxPwr24HRlts4Threshold  OBJECT-TYPE
        SYNTAX      INTEGER
        ACCESS      read-write
        STATUS      mandatory
        DESCRIPTION 
            "Number of  seconds  within a day  to set pmRxPwrTpClass24HRlts4Alarm 
             (zero value disables the alarm)"
        DEFVAL  { 0 }
        ::=  { pmRxPwr  6}

    pmRxPwr15MRlts1Threshold  OBJECT-TYPE
        SYNTAX      INTEGER
        ACCESS      read-write
        STATUS      mandatory
        DESCRIPTION 
            "Number of  seconds  within 15 minutes  to set 
             pmRxPwrTpClass15MRlts1Alarm (zero value disables the alarm)"
        DEFVAL  { 0 }
        ::=  { pmRxPwr  7}

    pmRxPwr15MRlts2Threshold  OBJECT-TYPE
        SYNTAX      INTEGER
        ACCESS      read-write
        STATUS      mandatory
        DESCRIPTION 
            "Number of  seconds  within  15 minutes  to set 
             pmRxPwrTpClass15MRlts2Alarm (zero value disables the alarm)"
        DEFVAL  { 0 }
        ::=  { pmRxPwr  8}

    pmRxPwr15MRlts3Threshold  OBJECT-TYPE
        SYNTAX      INTEGER
        ACCESS      read-write
        STATUS      mandatory
        DESCRIPTION 
            "Number of  seconds  within  15 minutes to set 
             pmRxPwrTpClass15MRlts3Alarm (zero value disables the alarm)"
        DEFVAL  { 0 }
        ::=  { pmRxPwr  9}

    pmRxPwr15MRlts4Threshold  OBJECT-TYPE
        SYNTAX      INTEGER
        ACCESS      read-write
        STATUS      mandatory
        DESCRIPTION 
            "Number of  seconds  within  15 minutes to set 
             pmRxPwrTpClass15MRlts4Alarm (zero value disables the alarm)"
        DEFVAL  { 0 }
        ::=  { pmRxPwr  10}

    pmRxPwrRlt1Threshold  OBJECT-TYPE
        SYNTAX      INTEGER
        ACCESS      read-write
        STATUS      mandatory
        DESCRIPTION 
            "Reveived Power Level Threshold 1 (dBm value)"
        DEFVAL  { -30 }
        ::=  { pmRxPwr  11 }

    pmRxPwrRlt2Threshold  OBJECT-TYPE
        SYNTAX      INTEGER
        ACCESS      read-write
        STATUS      mandatory
        DESCRIPTION 
            "Reveived Power Level Threshold 2 (dBm value)"
        DEFVAL  { -40 }
        ::=  { pmRxPwr  12 }

    pmRxPwrRlt3Threshold  OBJECT-TYPE
        SYNTAX      INTEGER
        ACCESS      read-write
        STATUS      mandatory
        DESCRIPTION 
            "Reveived Power Level Threshold 3 (dBm value)"
        DEFVAL  { -50 }
        ::=  { pmRxPwr  13 }

    pmRxPwrRlt4Threshold  OBJECT-TYPE
        SYNTAX      INTEGER
        ACCESS      read-write
        STATUS      mandatory
        DESCRIPTION 
            "Reveived Power Level Threshold 4 (dBm value)"
        DEFVAL  { -60 }
        ::=  { pmRxPwr  14 }



----------------------------------------------------------------------------------
--  The following objects define the profile of the threshold cross and UAS  alarms:
--
--  The general stucture of the object is the following:
--
--
--   pmRxPwr<AlarmName>SeverityCode  OBJECT-TYPE
--     SYNTAX    INTEGER {
--                            disable                    (1),
--                            status-trapEnable          (2),
--                            status-trapEnableWithACK   (34),
--                            warning-trapEnable         (3),
--                            warning-trapEnableWithACK  (35),
--                            minor-trapEnable           (4),
--                            minor-trapEnableWithACK    (36),
--                            major-trapEnable           (5),
--                            major-trapEnableWithACK    (37),
--                            critical-trapEnable        (6),
--                            critical-trapEnableWithACK (38),
--                            status-trapDisable         (18),
--                            warning-trapDisable        (19),
--                            minor-trapDisable          (20),
--                            major-trapDisable          (21),
--                            critical-trapDisable       (22)
--                       }
--     ACCESS      read-write
--     STATUS      mandatory
--     DESCRIPTION "
--           Define the severity associated to the  <alarm name>  and  
--           enable/disable the trap generation on status
--           change   event.
--     "  DEFVAL{ x }
--    ::=  { pmRxPwr  y }
----------------------------------------------------------------------------------

    pmRxPwrTpClass15MRltsAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),   
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the pmRxPwrTpClass15MRltsAlarm and  
             enable/disable the trap generation on status change   event."
        DEFVAL  { major-trapEnable }
        ::=  { pmRxPwr  15 }

    pmRxPwrTpClass24HRltsAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the pmRxPwrTpClass24HRltsAlarm and  
             enable/disable the trap generation on status change event."
        DEFVAL  { major-trapEnable }
        ::=  { pmRxPwr  16 }



----------------------------------------------------------------------------------
--  The Received Power  Performance group generates the following  trap
----------------------------------------------------------------------------------

    pmRxPwrTpClass15MRlts1AlarmSet  TRAP-TYPE
        ENTERPRISE pdh-al 
        DESCRIPTION "
            This event is generated by  NE when  a pmRxPwrTpClass15MRlts1Alarm is 
            set  The data passed with the event are:
              1) radioBranchId 
              2) RxPwrTpClass15MRlts1Alarm
              3) equipTrapAcknowledge code number"
        ::= 1201

    pmRxPwrTpClass15MRlts1AlarmCleared  TRAP-TYPE
        ENTERPRISE pdh-al 
        DESCRIPTION "
            This event is generated by  NE when a pmRxPwrTpClass15MRlts1Alarm is 
            cleared The data passed with the event are:
              1) radioBranchId 
              2) RxPwrTpClass15MRlts1Alarm
              3) equipTrapAcknowledge code number"
        ::= 1202

    pmRxPwrTpClass15MRlts2AlarmSet  TRAP-TYPE
        ENTERPRISE pdh-al 
        DESCRIPTION "
            This event is generated by  NE when  a pmRxPwrTpClass15MRlts1Alarm is 
            set The data passed with the event are:
              1) radioBranchId 
              2) RxPwrTpClass15MRlts2Alarm
              3) equipTrapAcknowledge code number"
        ::= 1203

    pmRxPwrTpClass15MRlts2AlarmCleared  TRAP-TYPE
        ENTERPRISE pdh-al 
        DESCRIPTION "
            This event is generated by  NE when a pmRxPwrTpClass15MRlts1Alarm is 
            cleared  The data passed with the event are:
              1) radioBranchId 
              2) RxPwrTpClass15MRlts2Alarm
              3) equipTrapAcknowledge code number"
        ::= 1204

    pmRxPwrTpClass15MRlts3AlarmSet  TRAP-TYPE
        ENTERPRISE pdh-al 
        DESCRIPTION "
            This event is generated by  NE when  a pmRxPwrTpClass15MRlts1Alarm is 
            set  The data passed with the event are:
              1) radioBranchId 
              2) RxPwrTpClass15MRlts3Alarm
              3) equipTrapAcknowledge code number"
        ::= 1205

    pmRxPwrTpClass15MRlts3AlarmCleared  TRAP-TYPE
        ENTERPRISE pdh-al 
        DESCRIPTION "
            This event is generated by  NE when a pmRxPwrTpClass15MRlts1Alarm is 
            cleared  The data passed with the event are:
              1) radioBranchId 
              2) RxPwrTpClass15MRlts3Alarm
              3) equipTrapAcknowledge code number"
        ::= 1206

    pmRxPwrTpClass15MRlts4AlarmSet  TRAP-TYPE
        ENTERPRISE pdh-al 
        DESCRIPTION "
            This event is generated by  NE when  a pmRxPwrTpClass15MRlts4Alarm is 
            set  The data passed with the event are:
              1) radioBranchId 
              2) RxPwrTpClass15MRlts4Alarm
              3) equipTrapAcknowledge code number"
        ::= 1207

    pmRxPwrTpClass15MRlts4AlarmCleared  TRAP-TYPE
        ENTERPRISE pdh-al 
        DESCRIPTION "
            This event is generated by  NE when a pmRxPwrTpClass15MRlts4Alarm is 
            cleared The data passed with the event are:
              1) radioBranchId 
              2) RxPwrTpClass15MRlts4Alarm
              3) equipTrapAcknowledge code number"
        ::= 1208

    pmRxPwrTpClass24HRlts1AlarmSet  TRAP-TYPE
        ENTERPRISE pdh-al 
        DESCRIPTION "
            This event is generated by  NE when  a pmRxPwrTpClass24HRlts1Alarm is 
            set  The data passed with the event are:
              1) radioBranchId 
              2) RxPwrTpClass24HRlts1Alarm
              3) equipTrapAcknowledge code number"
        ::= 1209

    pmRxPwrTpClass24HRlts1AlarmCleared  TRAP-TYPE
        ENTERPRISE pdh-al 
        DESCRIPTION "
            This event is generated by  NE when a pmRxPwrTpClass24HRlts1Alarm is   
            cleared  The data passed with the event are:
              1) radioBranchId 
              2) RxPwrTpClass24HRlts1Alarm
              3) equipTrapAcknowledge code number"
        ::= 1210

    pmRxPwrTpClass24HRlts2AlarmSet  TRAP-TYPE
        ENTERPRISE pdh-al 
        DESCRIPTION "
            This event is generated by  NE when  a pmRxPwrTpClass24HRlts1Alarm is 
            set The data passed with the event are:
              1) radioBranchId 
              2) RxPwrTpClass24HRlts2Alarm
              3) equipTrapAcknowledge code number"
        ::= 1211

    pmRxPwrTpClass24HRlts2AlarmCleared  TRAP-TYPE
        ENTERPRISE pdh-al 
        DESCRIPTION "
            This event is generated by  NE when a pmRxPwrTpClass24HRlts1Alarm is 
            cleared    The data passed with the event are:
              1) radioBranchId 
              2) RxPwrTpClass24HRlts2Alarm
              3) equipTrapAcknowledge code number"
        ::= 1212

    pmRxPwrTpClass24HRlts3AlarmSet  TRAP-TYPE
        ENTERPRISE pdh-al 
        DESCRIPTION "
            This event is generated by  NE when  a pmRxPwrTpClass24HRlts1Alarm is 
            set The data passed with the event are:
              1) radioBranchId 
              2) RxPwrTpClass24HRlts3Alarm
              3) equipTrapAcknowledge code number"
        ::= 1213

    pmRxPwrTpClass24HRlts3AlarmCleared  TRAP-TYPE
        ENTERPRISE pdh-al 
        DESCRIPTION "
            This event is generated by  NE when a pmRxPwrTpClass24HRlts1Alarm is 
            cleared  The data passed with the event are:
              1) radioBranchId 
              2) RxPwrTpClass24HRlts3Alarm
              3) equipTrapAcknowledge code number"
        ::= 1214

    pmRxPwrTpClass24HRlts4AlarmSet  TRAP-TYPE
        ENTERPRISE pdh-al 
        DESCRIPTION "
            This event is generated by  NE when  a pmRxPwrTpClass24HRlts4Alarm is 
            set The data passed with the event are:
              1) radioBranchId 
              2) RxPwrTpClass24HRlts4Alarm
              3) equipTrapAcknowledge code number"
        ::= 1215

    pmRxPwrTpClass24HRlts4AlarmCleared  TRAP-TYPE
        ENTERPRISE pdh-al 
        DESCRIPTION "
            This event is generated by  NE when a pmRxPwrTpClass24HRlts4Alarm is 
            cleared The data passed with the event are:
              1) radioBranchId 
              2) RxPwrTpClass24HRlts4Alarm
              3) equipTrapAcknowledge code number"
        ::= 1216



----------------------------------------------------------------------------------
--  4.26 PERFORMANCE MONITORING TRANSMITTED POWER LEVEL GROUP
----------------------------------------------------------------------------------
--  The following objects are used to manage the Transmitted Power Performance 
--  Monitoring function.
----------------------------------------------------------------------------------

--  The following table contains the records with the counters used to monitor 
--  the Transmitted power of the radio.
----------------------------------------------------------------------------------

    pmTxPwrCounterTable  OBJECT-TYPE
        SYNTAX      SEQUENCE OF  PmTxPwrCounterRecord
        ACCESS      not-accessible
        STATUS      mandatory
        DESCRIPTION 
            "Table with PmTxPwr records: one record for 1+0 configuration and two 
             record for 1+1 configuration."
        ::=  { pmTxPwr  1 }

    pmTxPwrCounterRecord  OBJECT-TYPE
        SYNTAX      PmTxPwrCounterRecord
        ACCESS      not-accessible
        STATUS      mandatory
        DESCRIPTION 
            "PmTxPwr  record"
        INDEX {  pmTxPwrBranchId, pmTxPwrCounterBlockId }
        ::=  { pmTxPwrCounterTable 1 }

    PmTxPwrCounterRecord  ::=
        SEQUENCE {
            pmTxPwrBranchId               INTEGER,
            pmTxPwrCounterBlockId         INTEGER,
            pmTxPwrCounterBlockType       INTEGER,
            pmTxPwrCounterBlockStatus     INTEGER,
            pmTxPwrCounterTimeStamp       TimeTicks,
            pmTxPwrTlts1Counter           Counter,
            pmTxPwrTlts2Counter           Counter,
            pmTxPwrTlts3Counter           Counter,
            pmTxPwrTlts4Counter           Counter,
            pmTxPwrTMMax                  INTEGER,
            pmTxPwrTMMin                  INTEGER
        }

    pmTxPwrBranchId  OBJECT-TYPE
        SYNTAX    INTEGER
        ACCESS      read-only
        STATUS      mandatory
        DESCRIPTION 
            "This object  identifies  the  Radio Branch"
        ::=  { pmTxPwrCounterRecord  1 }

    pmTxPwrCounterBlockId  OBJECT-TYPE
        SYNTAX    INTEGER
        ACCESS      read-only
        STATUS      mandatory
        DESCRIPTION 
            "This object  identifies  the counters block and the counter type according to the following code:
             1   Current Daily counters
             2   Daily counters (Day before counters)
             3   Current 15 minutes counters
             4   15 minutes counters N. 1 (The most recent 15 minutes counters)
                 ..............................................
             n   15 minutes counters N. n
            19   15 minutes counters N. 16 (The oldest 15 minutes  counters - 4 hours before)"
        ::=  { pmTxPwrCounterRecord  2 }

    pmTxPwrCounterBlockType  OBJECT-TYPE
        SYNTAX    INTEGER {
                            daily       (1),
                            fifteen-min (2)
                          }
        ACCESS      read-only
        STATUS      mandatory
        DESCRIPTION 
            "The type of the counter block"
        ::=  { pmTxPwrCounterRecord  3}

    pmTxPwrCounterBlockStatus OBJECT-TYPE
        SYNTAX    INTEGER {
                            meaningless   (1),
                            meaningfull   (2),
                            incomplete    (3),
                            dummy         (4),
                            lost          (5),
                            restarted     (6)
                          }
        ACCESS      read-only
        STATUS      mandatory
        DESCRIPTION 
            "block counter status"
        ::=  { pmTxPwrCounterRecord  4 }

    pmTxPwrCounterTimeStamp OBJECT-TYPE
        SYNTAX      TimeTicks
        ACCESS      read-only
        STATUS      mandatory
        DESCRIPTION 
            "The object is the time when the performance record is closed reported
             as the second number since 1/1/70."
        ::=  { pmTxPwrCounterRecord  5 }

    pmTxPwrTlts1Counter  OBJECT-TYPE
        SYNTAX    Counter
        ACCESS      read-only
        STATUS      mandatory
        DESCRIPTION 
            "Number of seconds when the Transmitted  power is greater than the  threshold  1"
        ::=  { pmTxPwrCounterRecord  6 }

    pmTxPwrTlts2Counter  OBJECT-TYPE
        SYNTAX    Counter
        ACCESS      read-only
        STATUS      mandatory
        DESCRIPTION 
            "Number of seconds when the Transmitted  power is greater than the  threshold  2"
        ::=  { pmTxPwrCounterRecord  7 }

    pmTxPwrTlts3Counter  OBJECT-TYPE
        SYNTAX    Counter
        ACCESS      read-only
        STATUS      mandatory
        DESCRIPTION 
            "Number of seconds when the Transmitted  power is greater than the  threshold  3"
        ::=  { pmTxPwrCounterRecord  8 }

    pmTxPwrTlts4Counter  OBJECT-TYPE
        SYNTAX    Counter
        ACCESS      read-only
        STATUS      mandatory
        DESCRIPTION 
            "Number of seconds when the Transmitted  power is greater than the  threshold  4"
        ::=  { pmTxPwrCounterRecord  9 }

    pmTxPwrTMMax OBJECT-TYPE
        SYNTAX    INTEGER
        ACCESS      read-only
        STATUS      mandatory
        DESCRIPTION 
            "Maximum Transmitted Power Level  Tide Mark"
        ::=  { pmTxPwrCounterRecord  10 }

    pmTxPwrTMMin  OBJECT-TYPE
        SYNTAX    INTEGER
        ACCESS      read-only
        STATUS      mandatory
        DESCRIPTION 
            "Minimum  Transmitted Power Level  Tide Mark"
        ::=  { pmTxPwrCounterRecord  11 }



----------------------------------------------------------------------------------
--   The following table contains the records used to manage the P.M. on both radio branch and  the threshold cross alarms
----------------------------------------------------------------------------------

    pmTxPwrTpClassTable  OBJECT-TYPE
        SYNTAX      SEQUENCE OF  PmTxPwrTpClassRecord
        ACCESS      not-accessible
        STATUS      mandatory
        DESCRIPTION 
            "Table with PmTxPwrTpClass records: one record for 1+0 configuration and two record
             for 1+1 configuration."
        ::=  { pmTxPwr  2 }

    pmTxPwrTpClassRecord  OBJECT-TYPE
        SYNTAX      PmTxPwrTpClassRecord
        ACCESS      not-accessible
        STATUS      mandatory
        DESCRIPTION 
            "PmTxPwrTpClass  record"
        INDEX {  pmTxPwrTpClassBranchId }
        ::=  { pmTxPwrTpClassTable 1 }

    PmTxPwrTpClassRecord  ::=
        SEQUENCE {
            pmTxPwrTpClassBranchId          INTEGER,
            pmTxPwrTpClassStartStop         INTEGER,
            pmTxPwrTpClassCounterClear      INTEGER,
            pmTxPwrTpClassAlarmClear        INTEGER,
            pmTxPwrTpClassCounterBuffer     Opaque,
            pmTxPwrTpClass15MTlts1Alarm     INTEGER,
            pmTxPwrTpClass15MTlts2Alarm     INTEGER,
            pmTxPwrTpClass15MTlts3Alarm     INTEGER,
            pmTxPwrTpClass15MTlts4Alarm     INTEGER,
            pmTxPwrTpClass24HTlts1Alarm     INTEGER,
            pmTxPwrTpClass24HTlts2Alarm     INTEGER,
            pmTxPwrTpClass24HTlts3Alarm     INTEGER,
            pmTxPwrTpClass24HTlts4Alarm     INTEGER,
            pmTxPwrTpClassTimeStamp         TimeTicks
    }

    pmTxPwrTpClassBranchId  OBJECT-TYPE
        SYNTAX    INTEGER
        ACCESS      read-only
        STATUS      mandatory
        DESCRIPTION 
            "This object  identifies  the  Radio Branch"
        ::=  { pmTxPwrTpClassRecord  1 }

    pmTxPwrTpClassStartStop  OBJECT-TYPE
        SYNTAX    INTEGER {
                            start   (1),
                            stop    (2)
                          }
        ACCESS      read-write
        STATUS      mandatory
        DESCRIPTION 
            "This object is used to start and to stop the Perfomance Monitoring counter evaluation"
        ::=  { pmTxPwrTpClassRecord  2 }

    pmTxPwrTpClassCounterClear  OBJECT-TYPE
        SYNTAX    INTEGER {
                            clear   (1)
                          }
        ACCESS      write-only
        STATUS      mandatory
        DESCRIPTION 
            "This object is used to clear  the Perfomance Monitoring counters."
        ::=  { pmTxPwrTpClassRecord  3 }

    pmTxPwrTpClassAlarmClear  OBJECT-TYPE
        SYNTAX    INTEGER {
                            clear   (1)
                          }
        ACCESS      write-only
        STATUS      mandatory
        DESCRIPTION 
            "This object is used to clear  the Perfomance Monitoring threshold cross alarms"
        ::=  { pmTxPwrTpClassRecord  4 }

    pmTxPwrTpClassCounterBuffer  OBJECT-TYPE
        SYNTAX      Opaque
        ACCESS      read-only
        STATUS      mandatory
        DESCRIPTION 
            "This object  is used to transfer  in only one request all Tx Power Counters 
             (16x15Minutes and 1x1Day).
             It is used by a dedicated  P.M. application on the Manager."
        ::=  { pmTxPwrTpClassRecord  5 }

    pmTxPwrTpClass15MTlts1Alarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "15 minutes  Tlts1  threshold cross alarm  with associated Severity."
        ::=  { pmTxPwrTpClassRecord  6 }

    pmTxPwrTpClass15MTlts2Alarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "15 minutes  Tlts2  threshold cross alarm  with associated Severity."
        ::=  { pmTxPwrTpClassRecord  7 }

    pmTxPwrTpClass15MTlts3Alarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "15 minutes  Tlts3  threshold cross alarm  with associated Severity."
        ::=  { pmTxPwrTpClassRecord  8 }

    pmTxPwrTpClass15MTlts4Alarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "15 minutes  Tlts4  threshold cross alarm  with associated Severity."
        ::=  { pmTxPwrTpClassRecord  9 }

    pmTxPwrTpClass24HTlts1Alarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "Daily  Tlts1  threshold cross alarm  with associated Severity."
        ::=  { pmTxPwrTpClassRecord  10 }

    pmTxPwrTpClass24HTlts2Alarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "Daily  Tlts2  threshold cross alarm  with associated Severity."
        ::=  { pmTxPwrTpClassRecord  11 }

    pmTxPwrTpClass24HTlts3Alarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "Daily   Tlts3  threshold cross alarm  with associated Severity."
        ::=  { pmTxPwrTpClassRecord  12 }

    pmTxPwrTpClass24HTlts4Alarm  OBJECT-TYPE
        SYNTAX    INTEGER {
                            cleared                   (1),
                            activeReportable-Status   (2),
                            activeReportable-Warning  (3),
                            activeReportable-Minor    (4),
                            activeReportable-Major    (5),
                            activeReportable-Critical (6)
                          }
        ACCESS      read-only
        STATUS      mandatory
        DESCRIPTION 
            "Daily   Tlts4  threshold cross alarm  with associated Severity."
        ::=  { pmTxPwrTpClassRecord  13 }

    pmTxPwrTpClassTimeStamp OBJECT-TYPE
        SYNTAX      TimeTicks
        ACCESS      read-only
        STATUS      mandatory
        DESCRIPTION 
            "istante dell'inizio della misura, in secondi a partire dal 01/01/70"
        ::=  { pmTxPwrTpClassRecord  14 }



----------------------------------------------------------------------------------
--  The following objects are common to both radio branches.
----------------------------------------------------------------------------------

    pmTxPwr24HTlts1Threshold  OBJECT-TYPE
        SYNTAX    INTEGER
        ACCESS      read-write
        STATUS      mandatory
        DESCRIPTION 
            "Number of seconds within a day to set pmTxPwrTpClass24HTlts1Alarm 
             (0x0000 value disables the alarm)"
        DEFVAL  { '0000'h }
        ::=  { pmTxPwr  3}

    pmTxPwr24HTlts2Threshold  OBJECT-TYPE
        SYNTAX    INTEGER
        ACCESS      read-write
        STATUS      mandatory
        DESCRIPTION 
            "Number of seconds within a day to set pmTxPwrTpClass24HTlts2Alarm 
             (0x0000 value disables the alarm)"
        DEFVAL  { '0000'h }
        ::=  { pmTxPwr  4}

    pmTxPwr24HTlts3Threshold  OBJECT-TYPE
        SYNTAX    INTEGER
        ACCESS      read-write
        STATUS      mandatory
        DESCRIPTION 
            "Number of seconds within a day to set pmTxPwrTpClass24HTlts3Alarm
             (0x0000 value disables the alarm)"
        DEFVAL  { '0000'h }
        ::=  { pmTxPwr  5}

    pmTxPwr24HTlts4Threshold  OBJECT-TYPE
        SYNTAX    INTEGER
        ACCESS      read-write
        STATUS      mandatory
        DESCRIPTION 
            "Number of seconds within a day to set pmTxPwrTpClass24HTlts4Alarm
             (0x0000 value disables the alarm)"
        DEFVAL  { '0000'h }
        ::=  { pmTxPwr  6}

    pmTxPwr15MTlts1Threshold  OBJECT-TYPE
        SYNTAX    INTEGER
        ACCESS      read-write
        STATUS      mandatory
        DESCRIPTION 
            "Number of seconds within 15 minutes to set pmTxPwrTpClass15MTlts1Alarm
             (0x0000 value disables the alarm)"
        DEFVAL  { '0000'h }
        ::=  { pmTxPwr  7}

    pmTxPwr15MTlts2Threshold  OBJECT-TYPE
        SYNTAX    INTEGER
        ACCESS      read-write
        STATUS      mandatory
        DESCRIPTION 
            "Number of seconds within 15 minutes to set pmTxPwrTpClass15MTlts2Alarm
             (0x0000 value disables the alarm)"
        DEFVAL  { '0000'h }
        ::=  { pmTxPwr  8}

    pmTxPwr15MTlts3Threshold  OBJECT-TYPE
        SYNTAX    INTEGER
        ACCESS      read-write
        STATUS      mandatory
        DESCRIPTION 
            "Number of seconds within 15 minutes to set pmTxPwrTpClass15MTlts3Alarm
             (0x0000 value disables the alarm)"
        DEFVAL  { '0000'h }
        ::=  { pmTxPwr  9}

    pmTxPwr15MTlts4Threshold  OBJECT-TYPE
        SYNTAX    INTEGER
        ACCESS      read-write
        STATUS      mandatory
        DESCRIPTION 
            "Number of seconds within 15 minutes to set pmTxPwrTpClass15MTlts4Alarm
             (0x0000 value disables the alarm)"
        DEFVAL  { '0000'h }
        ::=  { pmTxPwr  10}

    pmTxPwrTlt1Threshold  OBJECT-TYPE
        SYNTAX    INTEGER
        ACCESS      read-write
        STATUS      mandatory
        DESCRIPTION 
            "Transmitted Power Level Threshold 1 (dBm value); range: 0 to +20"
        DEFVAL  { 13 }
        ::=  { pmTxPwr  11 }

    pmTxPwrTlt2Threshold  OBJECT-TYPE
        SYNTAX    INTEGER
        ACCESS      read-write
        STATUS      mandatory
        DESCRIPTION 
            "Transmitted Power Level Threshold 2 (dBm value); range: 0 to +20"
        DEFVAL  { 15 }
        ::=  { pmTxPwr  12 }

    pmTxPwrTlt3Threshold  OBJECT-TYPE
        SYNTAX    INTEGER
        ACCESS      read-write
        STATUS      mandatory
        DESCRIPTION 
            "Transmitted Power Level Threshold 3 (dBm value); range: 0 to +20"
        DEFVAL  { 17 }
        ::=  { pmTxPwr  13 }

    pmTxPwrTlt4Threshold  OBJECT-TYPE
        SYNTAX    INTEGER
        ACCESS      read-write
        STATUS      mandatory
        DESCRIPTION 
            "Transmitted Power Level Threshold 4 (dBm value); range: 0 to +20"
        DEFVAL  { 19 }
        ::=  { pmTxPwr  14 }



----------------------------------------------------------------------------------
--  The following objects define the profile of the threshold cross:
--
--  The general stucture of the object is the following:
--
--
--   pmTxPwr<AlarmName>SeverityCode  OBJECT-TYPE
--     SYNTAX    INTEGER {
--                            disable                    (1),
--                            status-trapEnable          (2),
--                            status-trapEnableWithACK   (34),
--                            warning-trapEnable         (3),
--                            warning-trapEnableWithACK  (35),
--                            minor-trapEnable           (4),
--                            minor-trapEnableWithACK    (36),
--                            major-trapEnable           (5),
--                            major-trapEnableWithACK    (37),
--                            critical-trapEnable        (6),
--                            critical-trapEnableWithACK (38),
--                            status-trapDisable         (18),
--                            warning-trapDisable        (19),
--                            minor-trapDisable          (20),
--                            major-trapDisable          (21),
--                            critical-trapDisable       (22)
--                       }
--     ACCESS      read-write
--     STATUS      mandatory
--     DESCRIPTION "
--           Define the severity associated to the  <alarm name>  and  enable/disable the trap generation on status
--           change   event.
--     "  DEFVAL{ x }
--    ::=  { pmTxPwr  y }
----------------------------------------------------------------------------------

    pmTxPwrTpClass15MTltsAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),   
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the pmTxPwrTpClass15MTltsAlarm 
             and  enable/disable the trap generation on status change event."
        DEFVAL  { major-trapEnable }
        ::=  { pmTxPwr  15 }

    pmTxPwrTpClass24HTltsAlarmSeverityCode  OBJECT-TYPE
        SYNTAX    INTEGER {
                            disable                    (1),
                            status-trapEnable          (2),
                            status-trapEnableWithACK   (34),
                            warning-trapEnable         (3),
                            warning-trapEnableWithACK  (35),
                            minor-trapEnable           (4),
                            minor-trapEnableWithACK    (36),
                            major-trapEnable           (5),
                            major-trapEnableWithACK    (37),
                            critical-trapEnable        (6),
                            critical-trapEnableWithACK (38),
                            status-trapDisable         (18),
                            warning-trapDisable        (19),
                            minor-trapDisable          (20),
                            major-trapDisable          (21),
                            critical-trapDisable       (22)
                          }
        ACCESS      read-write
        STATUS      mandatory
        DESCRIPTION 
            "Define the severity associated to the pmTxPwrTpClass24HTltsAlarm 
             and enable/disable the trap generation on status change event."
        DEFVAL  { major-trapEnable }
        ::=  { pmTxPwr  16 }



----------------------------------------------------------------------------------
--  The Transmitted Power Performance group generates the following trap
----------------------------------------------------------------------------------

    pmTxPwrTpClass15MTlts1AlarmSet  TRAP-TYPE
        ENTERPRISE pdh-al 
        DESCRIPTION "
            This event is generated by  NE when  a pmTxPwrTpClass15MTlts1Alarm is set
            The data passed with the event are:
              1) radioBranchId 
              2) TxPwrTpClass15MTlts1Alarm
              3) equipTrapAcknowledge code number"
        ::= 1301

    pmTxPwrTpClass15MTlts1AlarmCleared  TRAP-TYPE
        ENTERPRISE pdh-al 
        DESCRIPTION "
            This event is generated by  NE when a pmTxPwrTpClass15MTlts1Alarm is cleared
            The data passed with the event are:
              1) radioBranchId 
              2) TxPwrTpClass15MTlts1Alarm
              3) equipTrapAcknowledge code number"
        ::= 1302

    pmTxPwrTpClass15MTlts2AlarmSet  TRAP-TYPE
      ENTERPRISE pdh-al 
      DESCRIPTION "
          This event is generated by  NE when  a pmTxPwrTpClass15MTlts1Alarm is set
          The data passed with the event are:
            1) radioBranchId 
            2) TxPwrTpClass15MTlts2Alarm
            3) equipTrapAcknowledge code number"
      ::= 1303

    pmTxPwrTpClass15MTlts2AlarmCleared  TRAP-TYPE
      ENTERPRISE pdh-al 
      DESCRIPTION "
          This event is generated by  NE when a pmTxPwrTpClass15MTlts1Alarm is cleared
          The data passed with the event are:
            1) radioBranchId 
            2) TxPwrTpClass15MTlts2Alarm
            3) equipTrapAcknowledge code number"
      ::= 1304

    pmTxPwrTpClass15MTlts3AlarmSet  TRAP-TYPE
        ENTERPRISE pdh-al 
        DESCRIPTION "
            This event is generated by  NE when  a pmTxPwrTpClass15MTlts1Alarm is set
            The data passed with the event are:
              1) radioBranchId 
              2) TxPwrTpClass15MTlts3Alarm
              3) equipTrapAcknowledge code number"
        ::= 1305

    pmTxPwrTpClass15MTlts3AlarmCleared  TRAP-TYPE
        ENTERPRISE pdh-al 
        DESCRIPTION "
            This event is generated by  NE when a pmTxPwrTpClass15MTlts1Alarm is cleared
            The data passed with the event are:
              1) radioBranchId 
              2) TxPwrTpClass15MTlts3Alarm
              3) equipTrapAcknowledge code number"
        ::= 1306

    pmTxPwrTpClass15MTlts4AlarmSet  TRAP-TYPE
        ENTERPRISE pdh-al 
        DESCRIPTION "
            This event is generated by  NE when  a pmTxPwrTpClass15MTlts4Alarm is set
            The data passed with the event are:
              1) radioBranchId 
              2) TxPwrTpClass15MTlts4Alarm
              3) equipTrapAcknowledge code number"
        ::= 1307

    pmTxPwrTpClass15MTlts4AlarmCleared  TRAP-TYPE
        ENTERPRISE pdh-al 
        DESCRIPTION "
            This event is generated by  NE when a pmTxPwrTpClass15MTlts4Alarm is cleared
            The data passed with the event are:
              1) radioBranchId 
              2) TxPwrTpClass15MTlts4Alarm
              3) equipTrapAcknowledge code number"
        ::= 1308

    pmTxPwrTpClass24HTlts1AlarmSet  TRAP-TYPE
        ENTERPRISE pdh-al 
        DESCRIPTION "
            This event is generated by  NE when  a pmTxPwrTpClass24HTlts1Alarm is set
            The data passed with the event are:
              1) radioBranchId 
              2) TxPwrTpClass24HTlts1Alarm
              3) equipTrapAcknowledge code number"
        ::= 1309

    pmTxPwrTpClass24HTlts1AlarmCleared  TRAP-TYPE
        ENTERPRISE pdh-al 
        DESCRIPTION "
            This event is generated by  NE when a pmTxPwrTpClass24HTlts1Alarm is cleared
            The data passed with the event are:
              1) radioBranchId 
              2) TxPwrTpClass24HTlts1Alarm
              3) equipTrapAcknowledge code number"
        ::= 1310

    pmTxPwrTpClass24HTlts2AlarmSet  TRAP-TYPE
        ENTERPRISE pdh-al 
        DESCRIPTION "
            This event is generated by  NE when  a pmTxPwrTpClass24HTlts1Alarm is set
            The data passed with the event are:
              1) radioBranchId 
              2) TxPwrTpClass24HTlts2Alarm
              3) equipTrapAcknowledge code number"
        ::= 1311

    pmTxPwrTpClass24HTlts2AlarmCleared  TRAP-TYPE
        ENTERPRISE pdh-al 
        DESCRIPTION "
            This event is generated by  NE when a pmTxPwrTpClass24HTlts1Alarm is cleared
            The data passed with the event are:
              1) radioBranchId 
              2) TxPwrTpClass24HTlts2Alarm
              3) equipTrapAcknowledge code number"
        ::= 1312

    pmTxPwrTpClass24HTlts3AlarmSet  TRAP-TYPE
        ENTERPRISE pdh-al 
        DESCRIPTION "
            This event is generated by  NE when  a pmTxPwrTpClass24HTlts1Alarm is set
            The data passed with the event are:
              1) radioBranchId 
              2) TxPwrTpClass24HTlts3Alarm
              3) equipTrapAcknowledge code number"
        ::= 1313

    pmTxPwrTpClass24HTlts3AlarmCleared  TRAP-TYPE
        ENTERPRISE pdh-al 
        DESCRIPTION "
            This event is generated by  NE when a pmTxPwrTpClass24HTlts1Alarm is cleared
            The data passed with the event are:
              1) radioBranchId 
              2) TxPwrTpClass24HTlts3Alarm
              3) equipTrapAcknowledge code number"
        ::= 1314

    pmTxPwrTpClass24HTlts4AlarmSet  TRAP-TYPE
        ENTERPRISE pdh-al 
        DESCRIPTION "
            This event is generated by  NE when  a pmTxPwrTpClass24HTlts4Alarm is set
            The data passed with the event are:
              1) radioBranchId 
              2) TxPwrTpClass24HTlts4Alarm
              3) equipTrapAcknowledge code number"
        ::= 1315

    pmTxPwrTpClass24HTlts4AlarmCleared  TRAP-TYPE
        ENTERPRISE pdh-al 
        DESCRIPTION "
            This event is generated by  NE when a pmTxPwrTpClass24HTlts4Alarm is cleared
            The data passed with the event are:
              1) radioBranchId 
              2) TxPwrTpClass24HTlts4Alarm
              3) equipTrapAcknowledge code number"
        ::= 1316



--  4.17 portService  Group
--

--
-- This group  describes port used as service channel in PDH radio. 

    portServiceTable  OBJECT-TYPE
        SYNTAX      SEQUENCE OF  PortServiceRecord
        ACCESS      not-accessible
        STATUS      mandatory
        DESCRIPTION
            "Table with portService records describing 64Kbit/sec and 2Mbit ports within an unit."
        ::= { portService 1 }

    portServiceRecord  OBJECT-TYPE
        SYNTAX      PortServiceRecord
        ACCESS      not-accessible
        STATUS      mandatory
        DESCRIPTION
            "portService record"
        INDEX       { portServiceUnitId, portServiceId }
        ::= { portServiceTable 1 }

    PortServiceRecord  ::=
        SEQUENCE{
            portServiceUnitId               INTEGER,
            portServiceId                   INTEGER,
            portServiceType                 INTEGER,
            portServiceLabel                DisplayString,
            portServiceEnable               INTEGER,
            portServiceLevInPortA           INTEGER,
            portServiceLevOutPortA          INTEGER,
            portServiceLevInPortB           INTEGER,
            portServiceLevOutPortB          INTEGER,
            portServiceLosAlarm             INTEGER,
            portServiceInternalLosAlarm     INTEGER,
            portService64KbitAisTx          INTEGER,
            portServiceDialNumber           DisplayString,
            portServiceEmergencyCall        INTEGER,
            portServiceLineLoop             INTEGER,
            portServiceInternalLoop         INTEGER
        }

    portServiceUnitId  OBJECT-TYPE
        SYNTAX      INTEGER 
        ACCESS      read-only
        STATUS      mandatory
        DESCRIPTION
            "This object identifies unit where the Service port is present."
        ::= { portServiceRecord 1 }

    portServiceId  OBJECT-TYPE
        SYNTAX      INTEGER 
        ACCESS      read-only
        STATUS      mandatory
        DESCRIPTION
            "This object identifies the service port within the Unit."
        ::= { portServiceRecord 2 }

    portServiceType  OBJECT-TYPE
        SYNTAX      INTEGER {
                              service-voice             (1),
                              service-g703-Cod          (2),
                              service-g703-Contra       (3),
                              service-v11-Cod           (4),
                              service-v11-Contra        (5),
                              service-v28-async-1x9600  (6),
                              service-v28-async-2x4800  (7),
                              service-v24-sync-1x9600   (8),
                              service-v24-async-1x9600  (9),
                              service-eow               (10),
                              service-2Mb               (11),
                              undefined                 (12)
                            }
        ACCESS      read-write
        STATUS      mandatory
        DESCRIPTION
            "Define the type of the service  port."
        ::= { portServiceRecord 3 }

    portServiceLabel  OBJECT-TYPE
        SYNTAX      DisplayString   (SIZE(0..31))
        ACCESS      read-write
        STATUS      mandatory
        DESCRIPTION
            "ASCII string used by the operator to identify  the port service"
        ::= {portServiceRecord 4}

    portServiceEnable OBJECT-TYPE
        SYNTAX      INTEGER {
                              disable (1),
                              enable  (2)
                            }
        ACCESS      read-write
        STATUS      mandatory
        DESCRIPTION
            "Enable/disable the service port on the Unit (meaningfull when
             the port has alarms) "
        DEFVAL      { disable }
        ::= { portServiceRecord 5 }

    portServiceLevInPortA  OBJECT-TYPE
        SYNTAX      INTEGER
        ACCESS      read-write
        STATUS      mandatory
        DESCRIPTION
            "Attenuation value inserted at Port A input.
             Meaningfull only with service-voice and service-eow type"
    ::= { portServiceRecord 6 }

    portServiceLevOutPortA OBJECT-TYPE
        SYNTAX      INTEGER
        ACCESS      read-write
        STATUS      mandatory
        DESCRIPTION
            "Attenuation value inserted at Port A output 
             Meaningfull only with service-voice and service-eow type"
        ::= { portServiceRecord 7 }

    portServiceLevInPortB  OBJECT-TYPE
        SYNTAX      INTEGER
        ACCESS      read-write
        STATUS      mandatory
        DESCRIPTION
            "Attenuation value inserted at Port B input
             Meaningfull only with service-voice and service-eow type"
        ::= { portServiceRecord 8 }

    portServiceLevOutPortB  OBJECT-TYPE
        SYNTAX      INTEGER
        ACCESS      read-write
        STATUS      mandatory
        DESCRIPTION
            "Attenuation value inserted at Port B output
             Meaningfull only with service-voice and service-eow type"

        ::= { portServiceRecord 9 }

    portServiceLosAlarm  OBJECT-TYPE
        SYNTAX      INTEGER {
                              cleared (1),
                              activeReportable-Status (2),
                              activeReportable-Warning (3),
                              activeReportable-Minor (4),
                              activeReportable-Major (5),
                              activeReportable-Critical (6)
                            }
        ACCESS      read-only
        STATUS      mandatory
        DESCRIPTION
            "Service port lost of signal alarm   associated Severity. 
             Meaningfull only with service-g703-Cod and service-g703-Contra 
              type"
        ::= { portServiceRecord 10 }

    portServiceInternalLosAlarm  OBJECT-TYPE
        SYNTAX      INTEGER {
                              cleared (1),
                              activeReportable-Status (2),
                              activeReportable-Warning (3),
                              activeReportable-Minor (4),
                              activeReportable-Major (5),
                              activeReportable-Critical (6)
                            }
        ACCESS      read-only
        STATUS      mandatory
        DESCRIPTION
            "Service port lost of internal signal alarm status with
             associated Severity. Meaningfull only with service-g703-Cod and 
             service-g703-Contra type"
        ::= { portServiceRecord 11 }

    portService64KbitAisTx OBJECT-TYPE
        SYNTAX      INTEGER {
                              disable  (1),
                              enable   (2)
                            }
        ACCESS      read-write
        STATUS      mandatory
        DESCRIPTION
            "Enable/disable the AIS insetion at transmitted side for lack of the 
             received signal.
             Meaningfull only with service-g703-Cod and service-g703-Contra 
             type"
   ::= { portServiceRecord 12 }


    portServiceDialNumber OBJECT-TYPE
        SYNTAX      DisplayString   (SIZE(0..2))
        ACCESS      read-write
        STATUS      mandatory
        DESCRIPTION
            "Identification number of the radio terminal (1 to 99).
             Meaningfull only with service-voice type"
        ::= { portServiceRecord 13 }

    portServiceEmergencyCall OBJECT-TYPE
        SYNTAX      INTEGER {
                              enable (2)
                            }
        ACCESS      write-only
        STATUS      mandatory
        DESCRIPTION
            "This object allows to stop the selective call.
             Meaningfull only with service-voice type"
    ::= { portServiceRecord 14 }

    portServiceLineLoop OBJECT-TYPE
        SYNTAX      INTEGER {
                              loopOff (1),
                              loopOn  (2)
                            }
        ACCESS      read-write
        STATUS      mandatory
        DESCRIPTION
            "Enable/disable the line loop on port service"
        DEFVAL      { loopOff }
        ::= { portServiceRecord 15 }

    portServiceInternalLoop OBJECT-TYPE
        SYNTAX      INTEGER {
                              loopOff (1),
                              loopOn  (2)
                            }
        ACCESS      read-write
        STATUS      mandatory
        DESCRIPTION
            "Enable/disable the internal loop on port service"
        DEFVAL      { loopOff }
        ::= { portServiceRecord 16 }



--
-- The following objects define the profile of the portService  alarms:
--

    portServiceLosAlarmSeverityCode  OBJECT-TYPE
        SYNTAX    INTEGER {
                            disable (1),
                            status-trapEnable (2),
                            status-trapEnableWithACK (34),
                            warning-trapEnable (3),
                            warning-trapEnableWithACK (35),
                            minor-trapEnable (4),
                            minor-trapEnableWithACK (36),
                            major-trapEnable (5),
                            major-trapEnableWithACK (37),
                            critical-trapEnable (6),
                            critical-trapEnableWithACK (38),
                            status-trapDisable (18),
                            warning-trapDisable (19),
                            minor-trapDisable (20),
                            major-trapDisable (21),
                            critical-trapDisable (22)
                          }
        ACCESS      read-write
        STATUS      mandatory
        DESCRIPTION
            "Define the severity associated to the portServiceLosAlarm and enable/disable
             the trap generation on status change event."
        DEFVAL      { major-trapEnable }
        ::= { portService 2 }

    portServiceInternalLosAlarmSeverityCode  OBJECT-TYPE
        SYNTAX    INTEGER{
                            disable (1),
                            status-trapEnable (2),
                            status-trapEnableWithACK (34),
                            warning-trapEnable (3),
                            warning-trapEnableWithACK (35),
                            minor-trapEnable (4),
                            minor-trapEnableWithACK (36),
                            major-trapEnable (5),
                            major-trapEnableWithACK (37),
                            critical-trapEnable (6),
                            critical-trapEnableWithACK (38),
                            status-trapDisable (18),
                            warning-trapDisable (19),
                            minor-trapDisable (20),
                            major-trapDisable (21),
                            critical-trapDisable (22)
                         }
        ACCESS      read-write
        STATUS      mandatory
        DESCRIPTION
            "Define the severity associated to the portServiceInternalLosAlarm and enable/disable
             the trap generation on status change event."
        DEFVAL      { major-trapEnable }
        ::= { portService 3 }



--
-- The portService  Group generates the following TRAPs:
--

    portServiceLosAlarmSet  TRAP-TYPE
        ENTERPRISE pdh-al 
        DESCRIPTION
            "This event is generated by  NE when  a portServiceLosAlarm  is set
             The data passed with the event are:
                1) portServiceId
                2) UnitId
                3) portServiceLabel
                4) portServiceLosAlarm
                5) equipTrapAcknowledge code number"
        ::= 1401

    portServiceLosAlarmCleared  TRAP-TYPE
        ENTERPRISE pdh-al 
        DESCRIPTION
            "This event is generated by  NE when a portServiceLosAlarm is cleared
             The data passed with the event are:
                1) portServiceId
                2) UnitId
                3) portServiceLabel
                4) portServiceLosAlarm
                5) equipTrapAcknowledge code number"
        ::= 1402

    portServiceInternalLosAlarmSet  TRAP-TYPE
        ENTERPRISE pdh-al 
        DESCRIPTION
            "This event is generated by  NE when  a portServiceInternalLosAlarm  is set
             The data passed with the event are:
                1) portServiceId
                2) UnitId
                3) portServiceLabel
                4) portServiceInternalLosAlarm
                5) equipTrapAcknowledge code number"
        ::= 1403

    portServiceInternalLosAlarmCleared  TRAP-TYPE
        ENTERPRISE pdh-al 
        DESCRIPTION
            "This event is generated by  NE when a portServiceLosAlarm is cleared
             The data passed with the event are:
                1) portServiceId
                2) UnitId
                3) portServiceLabel
                4) portServiceInternalLosAlarm
                5) equipTrapAcknowledge code number"
        ::= 1404

----------------------------------------------------------------------------------
--  4.40 COMMAND LOG GROUP
--  This group is used to manage the command log.
----------------------------------------------------------------------------------

   commandLogTable        OBJECT-TYPE
        SYNTAX            SEQUENCE OF CommandRecord
        ACCESS            not-accessible
        STATUS            mandatory
        DESCRIPTION
            "Table with command  records"
        ::= {commandLog 1}
        
        
   commandLogRecord       OBJECT-TYPE
        SYNTAX            CommandRecord
        ACCESS            not-accessible
        STATUS            mandatory
        DESCRIPTION
            "Command record"
        INDEX { commandLogRecordId }
        ::= {commandLogTable 1}
        
        
   CommandRecord ::=
        SEQUENCE {
            commandLogRecordId
                 INTEGER,
            commandLogRecordRequestId
                 INTEGER,
            commandLogRecordObjectId
                 OBJECT IDENTIFIER,
            commandLogRecordObjectValue
                 DisplayString,
            commandLogRecordUserName
                 DisplayString,
            commandLogRecordSourceAddress
                 DisplayString,
            commandLogRecordTimeStamp
                 TimeTicks,
            commandLogRecordError
                 INTEGER
            }
            
            
   commandLogRecordId     OBJECT-TYPE
        SYNTAX            INTEGER
        ACCESS            read-only
        STATUS            mandatory
        DESCRIPTION 
            "index of command log record"
        ::= {commandLogRecord 1}
        
        
   commandLogRecordRequestId    OBJECT-TYPE
        SYNTAX            INTEGER
        ACCESS            read-only
        STATUS            mandatory
        DESCRIPTION 
            "request identifier of the packet"
        ::= {commandLogRecord 2}
        
        
   commandLogRecordObjectId     OBJECT-TYPE
        SYNTAX            OBJECT IDENTIFIER
        ACCESS            read-only
        STATUS            mandatory
        DESCRIPTION 
            "identifier of the managed object"
        ::= {commandLogRecord 3}
        
        
   commandLogRecordObjectValue     OBJECT-TYPE
        SYNTAX            DisplayString     (SIZE(0..63))
        ACCESS            read-only
        STATUS            mandatory
        DESCRIPTION 
            "value of the managed object displayed as a string"
        ::= {commandLogRecord 4}
        
        
   commandLogRecordUserName        OBJECT-TYPE
        SYNTAX            DisplayString     (SIZE(0..8))
        ACCESS            read-only
        STATUS            mandatory
        DESCRIPTION 
            "Name of the user that sent the request"
        ::= {commandLogRecord 5}
        
        
   commandLogRecordSourceAddress     OBJECT-TYPE
        SYNTAX            DisplayString     (SIZE(0..16))
        ACCESS            read-only
        STATUS            mandatory
        DESCRIPTION 
            "IP address of the remote machine that sent the request"
        ::= {commandLogRecord 6}
        
        
   commandLogRecordTimeStamp     OBJECT-TYPE
        SYNTAX            TimeTicks
        ACCESS            read-only
        STATUS            mandatory
        DESCRIPTION 
            "The time as seconds when command is registered since 01/01/1970"
        ::= {commandLogRecord 7}
        
        
   commandLogRecordError     OBJECT-TYPE
        SYNTAX            INTEGER
        ACCESS            read-only
        STATUS            mandatory
        DESCRIPTION 
            "Value returned by agent SNMP for the managed object"
        ::= {commandLogRecord 8}
        
        

----------------------------------------------------------------------------------
-- The following objects are used  to map the "action"
-- (delete record , transfer the log using NFS ...):
----------------------------------------------------------------------------------


   commandLogActionRequest     OBJECT-TYPE
        SYNTAX            INTEGER{
                                 delete (1),
                                 read (2)
                                 }
        ACCESS            write-only
        STATUS            mandatory
        DESCRIPTION
            "This leaf is used to delete record or to read it
            by FTP"
        ::= {commandLog 2}
        
        
   commandLogFtpFile     OBJECT-TYPE
        SYNTAX            DisplayString   (SIZE(0..255))
        ACCESS            read-write
        STATUS            mandatory
        DESCRIPTION
            "This leaf is reserved to file path where to
            transfer data"
        ::= {commandLog 3}
        
        
----------------------------------------------------------------------------------
-- The following objects are used  to enable/disable
-- writing of commands in the record
----------------------------------------------------------------------------------
        
        
   commandLogStartHourEnable     OBJECT-TYPE
        SYNTAX            INTEGER     (0..23)
        ACCESS            read-write
        STATUS            mandatory
        DESCRIPTION
            "Start hour of filter to enable/disable
            writing in the logger"
        DEFVAL            {0}
        ::= {commandLog 4}
        
        
   commandLogEndHourEnable     OBJECT-TYPE
        SYNTAX            INTEGER     (0..23)
        ACCESS            read-write
        STATUS            mandatory
        DESCRIPTION
            "End hour of filter to enable/disable
            writing in the logger"
        DEFVAL            {23}
        ::= {commandLog 5}
        
        
----------------------------------------------------------------------------------
-- The following objects are used  to filter
-- commands when an action (read or delete) is requested
----------------------------------------------------------------------------------
        
        
   commandLogStartTimeFilter     OBJECT-TYPE
        SYNTAX            TimeTicks
        ACCESS            read-write
        STATUS            mandatory
        DESCRIPTION
            "The events with EventTime greater than this object are read/delete from the log.
             Null value means no filter"
        DEFVAL            {0}
        ::= {commandLog 6}
        
        
   commandLogEndTimeFilter     OBJECT-TYPE
        SYNTAX            TimeTicks
        ACCESS            read-write
        STATUS            mandatory
        DESCRIPTION
            "The events with EventTime less than this object are read/delete from the log. 
             Null value means no filter"
        DEFVAL            {0}
        ::= {commandLog 7}
        
        
   commandLogObjectFilter     OBJECT-TYPE
        SYNTAX            OBJECT IDENTIFIER
        ACCESS            read-write
        STATUS            mandatory
        DESCRIPTION
            "Object identifier of filter to manage
            commands in the record. Pdh-Al value means no filter"
        DEFVAL            {pdh-al}
        ::= {commandLog 8}
        
        
   commandLogUserNameFilter     OBJECT-TYPE
        SYNTAX            DisplayString     (SIZE(0..8))
        ACCESS            read-write
        STATUS            mandatory
        DESCRIPTION
            "Name of the user that sent the request for the filter to manage
            commands in the record. ** value means no filter" 
        DEFVAL            {""}
        ::= {commandLog 9}
        
   
   commandLogSourceAddressFilter     OBJECT-TYPE
        SYNTAX            DisplayString     (SIZE(0..16))
        ACCESS            read-write
        STATUS            mandatory
        DESCRIPTION
            "IP address of source machine of filter to manage
            commands in the record. 0 value means no filter"
        DEFVAL            {"0"}
        ::= {commandLog 10}
        
   
   commandLogErrorFilter     OBJECT-TYPE
        SYNTAX            INTEGER
        ACCESS            read-write
        STATUS            mandatory
        DESCRIPTION
            "Error field for filter to manage commands in the record"
        DEFVAL            {-1}
        ::= {commandLog 11}
        
        
        
----------------------------------------------------------------------------------
-- The following objects are used  to manage
-- action in the FTP transfer
----------------------------------------------------------------------------------
      
     
   commandLogFtpStatus     OBJECT-TYPE
        SYNTAX            INTEGER{
                                 transferring (1),
                                 completed (2),
                                 interrupted (3),
                                 empty (4)
                                 }
        ACCESS            read-only
        STATUS            mandatory
        DESCRIPTION
            "This leaf is used for the status of transfer"
        DEFVAL            {completed}
        ::= {commandLog 12}
        
        
   commandLogFtpStatusTrapNotification     OBJECT-TYPE
        SYNTAX            INTEGER{
                                 trapDisable (1),
                                 trapEnable (2),
                                 trapEnableWithACK (3)
                                 }
        ACCESS            read-write
        STATUS            mandatory
        DESCRIPTION
            "Enable/disable the trap generation on FTP tranfer operation"
        DEFVAL            {trapEnable}
        ::= {commandLog 13}   
        
        
----------------------------------------------------------------------------------
-- The command logger group generates this trap
----------------------------------------------------------------------------------

    commandLogFtpStatusTrap  TRAP-TYPE
        ENTERPRISE pdh-al
        DESCRIPTION
            "This event is generated by SDH-NE when the status of FTP transfer is changed
             The data passed with the event are
             1) commandLogFtpStatus
             2) accessControlLoginIpAddress
             3) equipTrapAcknowledge code number"
        ::= 3001



END
