-- Copyright (C) , 2010.  All Rights Reserved.
-- This MIB was automatically generated from the TEJAS MIB Database
-- with makemib.
-- DO NOT EDIT THIS FILE DIRECTLY!

          TEJAS-MIB DEFINITIONS ::= BEGIN

           IMPORTS
              MODULE-IDENTITY,
              NOTIFICATION-TYPE,
              OBJECT-TYPE,
              Counter32,
              IpAddress,
              Integer32,
              Gauge32,
              TimeTicks
                    FROM SNMPv2-SMI
              
              
              enterprises
                    FROM SNMPv2-SMI
              DisplayString,
              TruthValue,
              RowStatus,
              TEXTUAL-CONVENTION
                    FROM SNMPv2-TC
	      
              ifIndex
                    FROM RFC1213-MIB
              MODULE-COMPLIANCE, OBJECT-GROUP, NOTIFICATION-GROUP
                    FROM SNMPv2-CONF;


          tejasMib MODULE-IDENTITY
              LAST-UPDATED "1007071013Z"
              ORGANIZATION ""
              CONTACT-INFO "

		NMS Support,

		Postal: Tejas Networks, Pvt. Ltd.
				1st Floor, Zone 2, Khanija Bhavan,
				49, Race Course Road, Bangalore 560 001,
				India

		Tel: 	+91 80 226 7495
		Fax: 	+91 80 226 7494
		E-mail: tejnms@india.tejasnetworks.com
"

              DESCRIPTION  "The MIB module to describe manageable objects for the TJ100 Product Family."
              ::= { enterprises 8255 }


         Fixed2 ::= TEXTUAL-CONVENTION
         STATUS       current
         DESCRIPTION
                     "Represents a fixed decimal as an integer that is one
                      hundred times the float value."
         SYNTAX       Integer32


         String16 ::= TEXTUAL-CONVENTION
         STATUS       current
         DESCRIPTION
                     "Represents an Octet String consisting of 16 octets."
         SYNTAX       OCTET STRING (SIZE (16))

          opticalBox  OBJECT IDENTIFIER ::= { tejasMib 1 }

       generic    OBJECT IDENTIFIER ::= { opticalBox    1 }
       products   OBJECT IDENTIFIER ::= { opticalBox    2 }


       genOptBoxTraps    OBJECT IDENTIFIER ::= { generic   0 }
       genOptBoxConf     OBJECT IDENTIFIER ::= { generic   1 }
       genOptBoxObjs     OBJECT IDENTIFIER ::= { generic   2 }
       genOptBoxFuncs    OBJECT IDENTIFIER ::= { generic   3 }

       optBoxGroups      OBJECT IDENTIFIER ::= { genOptBoxConf 1 }
       optBoxCompliances OBJECT IDENTIFIER ::= { genOptBoxConf 2 }

       nodeType    OBJECT IDENTIFIER ::= { products 1 }
       tjcardType    OBJECT IDENTIFIER ::= { products 2 }

       tj100   OBJECT IDENTIFIER ::= { nodeType 1 }

       stc   OBJECT IDENTIFIER ::= { nodeType 2 }

       tic     OBJECT IDENTIFIER ::= { tjcardType 1 }

      errorTable OBJECT-TYPE
      SYNTAX SEQUENCE OF ErrorTableEntry
      MAX-ACCESS not-accessible
      STATUS     current
      DESCRIPTION "Used for Errors."
         ::= { generic 4 }
      
      errorTableEntry OBJECT-TYPE
      SYNTAX ErrorTableEntry
      MAX-ACCESS not-accessible
      STATUS current
      DESCRIPTION
        "An entry in the Error Table."
      INDEX      { requestId }
         ::= { errorTable 1 }
      
      ErrorTableEntry ::=
         SEQUENCE {
           requestId INTEGER,
           error     OCTET STRING }

      requestId OBJECT-TYPE
      SYNTAX INTEGER
      MAX-ACCESS read-only
      STATUS current
      DESCRIPTION "Rrquest ID"
      ::= {errorTableEntry 1}

      error OBJECT-TYPE
      SYNTAX OCTET STRING
      MAX-ACCESS read-only
      STATUS current
      DESCRIPTION "Error"
      ::= {errorTableEntry 2}

      trapArgs     OBJECT IDENTIFIER ::= { generic   5 }

      slotNumberTrapArg OBJECT-TYPE
      SYNTAX INTEGER
      MAX-ACCESS read-only
      STATUS current
      DESCRIPTION "Card Slot Number"
         ::= { trapArgs  1}

      portNumberTrapArg OBJECT-TYPE
      SYNTAX INTEGER
      MAX-ACCESS read-only
      STATUS current
      DESCRIPTION "Port Number"
         ::= { trapArgs  2}

      imageNumberTrapArg OBJECT-TYPE
      SYNTAX INTEGER
      MAX-ACCESS read-only
      STATUS current
      DESCRIPTION "Image Number"
         ::= { trapArgs  3}

      alarmStateTrapArg OBJECT-TYPE
      SYNTAX INTEGER
      MAX-ACCESS read-only
      STATUS current
      DESCRIPTION "Alarm State"
         ::= { trapArgs 4 }

      serialnoTrapArg OBJECT-TYPE
      SYNTAX INTEGER
      MAX-ACCESS read-only
      STATUS current
      DESCRIPTION "Serial No"
         ::= { trapArgs 5 }

      operationTrapArg OBJECT-TYPE
      SYNTAX INTEGER { opCreate(0), opModify(1), opDelete(2) }
      MAX-ACCESS read-only
      STATUS current
      DESCRIPTION "DB Operation"
         ::= { trapArgs 6 }

      userTrapArg OBJECT-TYPE
      SYNTAX OCTET STRING
      MAX-ACCESS read-only
      STATUS current
      DESCRIPTION "User"
         ::= { trapArgs 7 }

      objectNameTrapArg OBJECT-TYPE
      SYNTAX OCTET STRING
      MAX-ACCESS read-only
      STATUS current
      DESCRIPTION "Object Name"
         ::= { trapArgs 8 }

      changesTrapArg OBJECT-TYPE
      SYNTAX OCTET STRING
      MAX-ACCESS read-only
      STATUS current
      DESCRIPTION "Changes"
         ::= { trapArgs 9 }

      md5TrapArg OBJECT-TYPE
      SYNTAX OCTET STRING
      MAX-ACCESS read-only
      STATUS current
      DESCRIPTION "md5 string"
         ::= { trapArgs 10 }

      routerIDTrapArg OBJECT-TYPE
      SYNTAX INTEGER
      MAX-ACCESS read-only
      STATUS current
      DESCRIPTION "Router ID"
         ::= { trapArgs 11 }

      dirTrapArg OBJECT-TYPE
      SYNTAX INTEGER
      MAX-ACCESS read-only
      STATUS current
      DESCRIPTION "direction"
         ::= { trapArgs 12 }

      tuNumberTrapArg OBJECT-TYPE
      SYNTAX INTEGER
      MAX-ACCESS read-only
      STATUS current
      DESCRIPTION "vtNo"
         ::= { trapArgs 13 }

      trapCountTrapArg OBJECT-TYPE
      SYNTAX INTEGER
      MAX-ACCESS read-only
      STATUS current
      DESCRIPTION "TrapCount"
         ::= { trapArgs 14 }

      cardTypeTrapArg OBJECT-TYPE
      SYNTAX INTEGER
      MAX-ACCESS read-only
      STATUS current
      DESCRIPTION "Card Type"
         ::= { trapArgs 15 }

      usernameTrapArg OBJECT-TYPE
      SYNTAX OCTET STRING
      MAX-ACCESS read-only
      STATUS current
      DESCRIPTION "User Name"
         ::= { trapArgs 16 }

      serviceIdTrapArg OBJECT-TYPE
      SYNTAX OCTET STRING
      MAX-ACCESS read-only
      STATUS current
      DESCRIPTION "Service Name"
         ::= { trapArgs 17 }

      lctNameTrapArg OBJECT-TYPE
      SYNTAX OCTET STRING
      MAX-ACCESS read-only
      STATUS current
      DESCRIPTION "Lct Name"
         ::= { trapArgs 19 }

      tcaMonTypeTrapArg OBJECT-TYPE
      SYNTAX OCTET STRING
      MAX-ACCESS read-only
      STATUS current
      DESCRIPTION "PM Attribute Name"
         ::= { trapArgs 20 }

      tcaMonValTrapArg OBJECT-TYPE
      SYNTAX INTEGER
      MAX-ACCESS read-only
      STATUS current
      DESCRIPTION "Monitored Value"
         ::= { trapArgs 21 }

      tcaThValTrapArg OBJECT-TYPE
      SYNTAX INTEGER
      MAX-ACCESS read-only
      STATUS current
      DESCRIPTION "Threshhold Value"
         ::= { trapArgs 22 }

      tcaDurationTrapArg OBJECT-TYPE
      SYNTAX OCTET STRING
      MAX-ACCESS read-only
      STATUS current
      DESCRIPTION "15 min or 24 hr"
         ::= { trapArgs 23 }

      additionalTrapArg OBJECT-TYPE
      SYNTAX OCTET STRING
      MAX-ACCESS read-only
      STATUS current
      DESCRIPTION "Additional Argument in Trap"
         ::= { trapArgs 24 }

      ifNameTrapArg OBJECT-TYPE
      SYNTAX OCTET STRING
      MAX-ACCESS read-only
      STATUS current
      DESCRIPTION "Additional Argument in Trap"
         ::= { trapArgs 25 }

      fanNumberTrapArg OBJECT-TYPE
      SYNTAX OCTET STRING
      MAX-ACCESS read-only
      STATUS current
      DESCRIPTION "Additional Argument in Trap"
         ::= { trapArgs 26 }

      informs    OBJECT IDENTIFIER ::= { generic   6 }
      genOptBoxInforms    OBJECT IDENTIFIER ::= { informs 0 }

      optBoxInformGroup NOTIFICATION-GROUP
      NOTIFICATIONS {
                aliveInform,
                dbChangeInform }
      STATUS current
      DESCRIPTION ""
       ::= { optBoxGroups 2 }

    aliveInform NOTIFICATION-TYPE
        OBJECTS {
                    serialnoTrapArg
                  }
        STATUS  current
        DESCRIPTION "Alive Message"
    ::= { genOptBoxInforms 1 }

    dbChangeInform NOTIFICATION-TYPE
        OBJECTS {
                    serialnoTrapArg,
                    operationTrapArg,
                    userTrapArg,
                    objectNameTrapArg,
                    changesTrapArg,
                    md5TrapArg
                  }
        STATUS  current
        DESCRIPTION "DB Change Message"
    ::= { genOptBoxInforms 2 }


      genIndexes	 OBJECT IDENTIFIER ::= { generic   7 }

      colval OBJECT-TYPE
      SYNTAX INTEGER
      MAX-ACCESS not-accessible
      STATUS current
      DESCRIPTION "An index in table under genOptBoxFuncs node in MIB Tree"
      ::= {genIndexes 1}

       statInterval OBJECT-TYPE
       SYNTAX INTEGER
       MAX-ACCESS not-accessible
       STATUS current
       DESCRIPTION  "An index in intervals table"
       		::= {genIndexes 2} 

    traps    OBJECT IDENTIFIER ::= { genOptBoxTraps   4 }

    alarmsAndEvents    OBJECT IDENTIFIER ::= { traps   1 }

    tcas    OBJECT IDENTIFIER ::= { traps   2 }

      trapAutoCardSwitchToWork NOTIFICATION-TYPE
      OBJECTS {
                    objectNameTrapArg,
                    lctNameTrapArg,
                    trapCountTrapArg
                }
      STATUS  current
      DESCRIPTION "Severity    : zilch 
                   Format      :  $1 Switch to the work card  $2 . 
                   Childtraps  : 
                   Description : Switch to work card"
             ::= { alarmsAndEvents 0 386 }

      trapAutoCardSwitchToProtect NOTIFICATION-TYPE
      OBJECTS {
                    objectNameTrapArg,
                    lctNameTrapArg,
                    trapCountTrapArg
                }
      STATUS  current
      DESCRIPTION "Severity    : minor 
                   Format      :  $1 Switch to the protecting card  
                   $2 . 
                   Childtraps  : 
                   Description : Switch to protecting card"
             ::= { alarmsAndEvents 0 387 }

      trapAutoCardSwitchToProtectClear NOTIFICATION-TYPE
      OBJECTS {
                    objectNameTrapArg,
                    lctNameTrapArg,
                    trapCountTrapArg
                }
      STATUS  current
      DESCRIPTION "Severity    : minor 
                   Format      :  $1 Switch to the protecting card  
                   $2 . 
                   Childtraps  : 
                   Description : Switch to protecting card"
             ::= { alarmsAndEvents 0 10387 }

      trapCardLockOutOfProtection NOTIFICATION-TYPE
      OBJECTS {
                    objectNameTrapArg,
                    lctNameTrapArg,
                    trapCountTrapArg
                }
      STATUS  current
      DESCRIPTION "Severity    : minor 
                   Format      :  $1 Lockout of protection, switch 
                   to the work card 
                   Childtraps  : 
                   Description : Lockout of protection"
             ::= { alarmsAndEvents 0 648 }

      trapCardLockOutOfProtectionClear NOTIFICATION-TYPE
      OBJECTS {
                    objectNameTrapArg,
                    lctNameTrapArg,
                    trapCountTrapArg
                }
      STATUS  current
      DESCRIPTION "Severity    : minor 
                   Format      :  $1 Lockout of protection, switch 
                   to the work card 
                   Childtraps  : 
                   Description : Lockout of protection"
             ::= { alarmsAndEvents 0 10648 }

      trapCardForcedSwitchToWork NOTIFICATION-TYPE
      OBJECTS {
                    objectNameTrapArg,
                    lctNameTrapArg,
                    trapCountTrapArg
                }
      STATUS  current
      DESCRIPTION "Severity    : minor 
                   Format      :  $1 Forced switch to the work card  
                   $2 . 
                   Childtraps  : 
                   Description : Forced Switch to work card"
             ::= { alarmsAndEvents 0 649 }

      trapCardForcedSwitchToWorkClear NOTIFICATION-TYPE
      OBJECTS {
                    objectNameTrapArg,
                    lctNameTrapArg,
                    trapCountTrapArg
                }
      STATUS  current
      DESCRIPTION "Severity    : minor 
                   Format      :  $1 Forced switch to the work card  
                   $2 . 
                   Childtraps  : 
                   Description : Forced Switch to work card"
             ::= { alarmsAndEvents 0 10649 }

      trapCardManualSwitchToWork NOTIFICATION-TYPE
      OBJECTS {
                    objectNameTrapArg,
                    lctNameTrapArg,
                    trapCountTrapArg
                }
      STATUS  current
      DESCRIPTION "Severity    : minor 
                   Format      :  $1 Manual switch to the work card  
                   $2 . 
                   Childtraps  : 
                   Description : Manual Switch to work card"
             ::= { alarmsAndEvents 0 650 }

      trapCardManualSwitchToWorkClear NOTIFICATION-TYPE
      OBJECTS {
                    objectNameTrapArg,
                    lctNameTrapArg,
                    trapCountTrapArg
                }
      STATUS  current
      DESCRIPTION "Severity    : minor 
                   Format      :  $1 Manual switch to the work card  
                   $2 . 
                   Childtraps  : 
                   Description : Manual Switch to work card"
             ::= { alarmsAndEvents 0 10650 }

      trapTSF NOTIFICATION-TYPE
      OBJECTS {
                    objectNameTrapArg,
                    lctNameTrapArg,
                    trapCountTrapArg,
                    portNumberTrapArg
                }
      STATUS  current
      DESCRIPTION "Severity    : major 
                   Format      :  $1 Timing reference failed on  $2 
                   . 
                   Childtraps  : 
                   Description : Timing reference failed"
             ::= { alarmsAndEvents 0 241 }

      trapTSFClear NOTIFICATION-TYPE
      OBJECTS {
                    objectNameTrapArg,
                    lctNameTrapArg,
                    trapCountTrapArg,
                    portNumberTrapArg
                }
      STATUS  current
      DESCRIPTION "Severity    : major 
                   Format      :  $1 Timing reference failed on  $2 
                   . 
                   Childtraps  : 
                   Description : Timing reference failed"
             ::= { alarmsAndEvents 0 10241 }

      trapCCFAILED NOTIFICATION-TYPE
      OBJECTS {
                    objectNameTrapArg,
                    lctNameTrapArg,
                    trapCountTrapArg,
                    slotNumberTrapArg
                }
      STATUS  current
      DESCRIPTION "Severity    : critical 
                   Childtraps  : 
                   Description : Connectivity Check Failed"
             ::= { alarmsAndEvents 0 658 }

      trapCCFAILEDClear NOTIFICATION-TYPE
      OBJECTS {
                    objectNameTrapArg,
                    lctNameTrapArg,
                    trapCountTrapArg,
                    slotNumberTrapArg
                }
      STATUS  current
      DESCRIPTION "Severity    : critical 
                   Childtraps  : 
                   Description : Connectivity Check Failed"
             ::= { alarmsAndEvents 0 10658 }

      trapUnexMAID NOTIFICATION-TYPE
      OBJECTS {
                    objectNameTrapArg,
                    lctNameTrapArg,
                    trapCountTrapArg,
                    slotNumberTrapArg
                }
      STATUS  current
      DESCRIPTION "Severity    : critical 
                   Format      :  $1  $2 : Unexpected MAID 
                   Childtraps  : 
                   Description : Unexpected MAID"
             ::= { alarmsAndEvents 0 661 }

      trapUnexMAIDClear NOTIFICATION-TYPE
      OBJECTS {
                    objectNameTrapArg,
                    lctNameTrapArg,
                    trapCountTrapArg,
                    slotNumberTrapArg
                }
      STATUS  current
      DESCRIPTION "Severity    : critical 
                   Format      :  $1  $2 : Unexpected MAID 
                   Childtraps  : 
                   Description : Unexpected MAID"
             ::= { alarmsAndEvents 0 10661 }

      trapRDI NOTIFICATION-TYPE
      OBJECTS {
                    objectNameTrapArg,
                    lctNameTrapArg,
                    trapCountTrapArg,
                    slotNumberTrapArg
                }
      STATUS  current
      DESCRIPTION "Severity    : critical 
                   Format      :  $1  $2 : Remote Defect Indication 
                   Childtraps  : 
                   Description : Remote Defect Indication"
             ::= { alarmsAndEvents 0 662 }

      trapRDIClear NOTIFICATION-TYPE
      OBJECTS {
                    objectNameTrapArg,
                    lctNameTrapArg,
                    trapCountTrapArg,
                    slotNumberTrapArg
                }
      STATUS  current
      DESCRIPTION "Severity    : critical 
                   Format      :  $1  $2 : Remote Defect Indication 
                   Childtraps  : 
                   Description : Remote Defect Indication"
             ::= { alarmsAndEvents 0 10662 }

      trapIntervalMismatch NOTIFICATION-TYPE
      OBJECTS {
                    objectNameTrapArg,
                    lctNameTrapArg,
                    trapCountTrapArg,
                    slotNumberTrapArg
                }
      STATUS  current
      DESCRIPTION "Severity    : critical 
                   Format      :  $1  $2 : CCM Interval Mismatch 
                   Childtraps  : 
                   Description : CCM Interval Mismatch"
             ::= { alarmsAndEvents 0 663 }

      trapIntervalMismatchClear NOTIFICATION-TYPE
      OBJECTS {
                    objectNameTrapArg,
                    lctNameTrapArg,
                    trapCountTrapArg,
                    slotNumberTrapArg
                }
      STATUS  current
      DESCRIPTION "Severity    : critical 
                   Format      :  $1  $2 : CCM Interval Mismatch 
                   Childtraps  : 
                   Description : CCM Interval Mismatch"
             ::= { alarmsAndEvents 0 10663 }

      trapLoopDetected NOTIFICATION-TYPE
      OBJECTS {
                    objectNameTrapArg,
                    lctNameTrapArg,
                    trapCountTrapArg,
                    slotNumberTrapArg
                }
      STATUS  current
      DESCRIPTION "Severity    : critical 
                   Format      :  $1  $2 : Loop Detected 
                   Childtraps  : 
                   Description : Loop Detected"
             ::= { alarmsAndEvents 0 664 }

      trapLoopDetectedClear NOTIFICATION-TYPE
      OBJECTS {
                    objectNameTrapArg,
                    lctNameTrapArg,
                    trapCountTrapArg,
                    slotNumberTrapArg
                }
      STATUS  current
      DESCRIPTION "Severity    : critical 
                   Format      :  $1  $2 : Loop Detected 
                   Childtraps  : 
                   Description : Loop Detected"
             ::= { alarmsAndEvents 0 10664 }

      trapUnexMEPID NOTIFICATION-TYPE
      OBJECTS {
                    objectNameTrapArg,
                    lctNameTrapArg,
                    trapCountTrapArg,
                    slotNumberTrapArg
                }
      STATUS  current
      DESCRIPTION "Severity    : critical 
                   Format      :  $1  $2 : Unexpected MEPID 
                   Childtraps  : 
                   Description : Unexpected MEPID"
             ::= { alarmsAndEvents 0 665 }

      trapUnexMEPIDClear NOTIFICATION-TYPE
      OBJECTS {
                    objectNameTrapArg,
                    lctNameTrapArg,
                    trapCountTrapArg,
                    slotNumberTrapArg
                }
      STATUS  current
      DESCRIPTION "Severity    : critical 
                   Format      :  $1  $2 : Unexpected MEPID 
                   Childtraps  : 
                   Description : Unexpected MEPID"
             ::= { alarmsAndEvents 0 10665 }

      trapUnexMDLevel NOTIFICATION-TYPE
      OBJECTS {
                    objectNameTrapArg,
                    lctNameTrapArg,
                    trapCountTrapArg,
                    slotNumberTrapArg
                }
      STATUS  current
      DESCRIPTION "Severity    : critical 
                   Format      :  $1  $2 : Unexpected MDLevel 
                   Childtraps  : 
                   Description : Unexpected MDLevel"
             ::= { alarmsAndEvents 0 666 }

      trapUnexMDLevelClear NOTIFICATION-TYPE
      OBJECTS {
                    objectNameTrapArg,
                    lctNameTrapArg,
                    trapCountTrapArg,
                    slotNumberTrapArg
                }
      STATUS  current
      DESCRIPTION "Severity    : critical 
                   Format      :  $1  $2 : Unexpected MDLevel 
                   Childtraps  : 
                   Description : Unexpected MDLevel"
             ::= { alarmsAndEvents 0 10666 }

      trapTrafficFieldMismatch NOTIFICATION-TYPE
      OBJECTS {
                    objectNameTrapArg,
                    lctNameTrapArg,
                    trapCountTrapArg,
                    slotNumberTrapArg
                }
      STATUS  current
      DESCRIPTION "Severity    : critical 
                   Format      :  $1  $2 : TrafficFieldMismatch 
                   Childtraps  : 
                   Description : Traffic Field Mismatch"
             ::= { alarmsAndEvents 0 689 }

      trapTrafficFieldMismatchClear NOTIFICATION-TYPE
      OBJECTS {
                    objectNameTrapArg,
                    lctNameTrapArg,
                    trapCountTrapArg,
                    slotNumberTrapArg
                }
      STATUS  current
      DESCRIPTION "Severity    : critical 
                   Format      :  $1  $2 : TrafficFieldMismatch 
                   Childtraps  : 
                   Description : Traffic Field Mismatch"
             ::= { alarmsAndEvents 0 10689 }

      trapMEPStatusChange NOTIFICATION-TYPE
      OBJECTS {
                    objectNameTrapArg,
                    lctNameTrapArg,
                    trapCountTrapArg,
                    slotNumberTrapArg
                }
      STATUS  current
      DESCRIPTION "Severity    : inform 
                   Format      :  $1 MEP Status 
                   Childtraps  : 
                   Description : MEP Status"
             ::= { alarmsAndEvents 0 691 }

      trapPdhLOS NOTIFICATION-TYPE
      OBJECTS {
                    objectNameTrapArg,
                    lctNameTrapArg,
                    trapCountTrapArg,
                    portNumberTrapArg
                }
      STATUS  current
      DESCRIPTION "Severity    : major 
                   Format      :  $1 Loss of Signal on Port 
                   Childtraps  : 
                   Description : Loss of Signal"
             ::= { alarmsAndEvents 0 202 }

      trapPdhLOSClear NOTIFICATION-TYPE
      OBJECTS {
                    objectNameTrapArg,
                    lctNameTrapArg,
                    trapCountTrapArg,
                    portNumberTrapArg
                }
      STATUS  current
      DESCRIPTION "Severity    : major 
                   Format      :  $1 Loss of Signal on Port 
                   Childtraps  : 
                   Description : Loss of Signal"
             ::= { alarmsAndEvents 0 10202 }

      trapPdhAis NOTIFICATION-TYPE
      OBJECTS {
                    objectNameTrapArg,
                    lctNameTrapArg,
                    trapCountTrapArg,
                    portNumberTrapArg
                }
      STATUS  current
      DESCRIPTION "Severity    : major 
                   Childtraps  : 
                   Description : Alarm Indication Signal on Port"
             ::= { alarmsAndEvents 0 203 }

      trapPdhAisClear NOTIFICATION-TYPE
      OBJECTS {
                    objectNameTrapArg,
                    lctNameTrapArg,
                    trapCountTrapArg,
                    portNumberTrapArg
                }
      STATUS  current
      DESCRIPTION "Severity    : major 
                   Childtraps  : 
                   Description : Alarm Indication Signal on Port"
             ::= { alarmsAndEvents 0 10203 }

      trapPdhTcaES NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      :  $1 TCA:ES on Port  $2  for  $3  
                   interval 
                   Childtraps  : 
                   Description : TCA: Errored Seconds - PDH"
             ::= { tcas 0 204 }

      trapPdhTcaSES NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      :  $1 TCA:SES on Port  $2  for  $3  
                   interval 
                   Childtraps  : 
                   Description : TCA: Severely Errored Seconds - PDH"
             ::= { tcas 0 205 }

      trapPdhTcaCV NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      :  $1 TCA:CV on Port  $2  for  $3  
                   interval 
                   Childtraps  : 
                   Description : TCA:Coding Violations - PDH"
             ::= { tcas 0 206 }

      trapCCEXAutomaticSwitchToChannel NOTIFICATION-TYPE
      OBJECTS {
                    objectNameTrapArg,
                    lctNameTrapArg,
                    trapCountTrapArg
                }
      STATUS  current
      DESCRIPTION "Severity    : zilch 
                   Format      :  $1 Non Revertive switch from 
                   channel  $2 . 
                   Childtraps  : 
                   Description : Protection Switch Complete"
             ::= { alarmsAndEvents 0 445 }

      trapCCEXLockOut NOTIFICATION-TYPE
      OBJECTS {
                    objectNameTrapArg,
                    lctNameTrapArg,
                    trapCountTrapArg
                }
      STATUS  current
      DESCRIPTION "Severity    : minor 
                   Format      :  $1 Lockout of protection, Switch 
                   from the protect channel  $2  . 
                   Childtraps  : 
                   Description : Lockout Active"
             ::= { alarmsAndEvents 0 446 }

      trapCCEXLockOutClear NOTIFICATION-TYPE
      OBJECTS {
                    objectNameTrapArg,
                    lctNameTrapArg,
                    trapCountTrapArg
                }
      STATUS  current
      DESCRIPTION "Severity    : minor 
                   Format      :  $1 Lockout of protection, Switch 
                   from the protect channel  $2  . 
                   Childtraps  : 
                   Description : Lockout Active"
             ::= { alarmsAndEvents 0 10446 }

      trapCCEXForcedSwitchToChannel NOTIFICATION-TYPE
      OBJECTS {
                    objectNameTrapArg,
                    lctNameTrapArg,
                    trapCountTrapArg
                }
      STATUS  current
      DESCRIPTION "Severity    : minor 
                   Format      :  $1 Forced switch from the channel  
                   $2 . 
                   Childtraps  : 
                   Description : Forced Switch Active"
             ::= { alarmsAndEvents 0 447 }

      trapCCEXForcedSwitchToChannelClear NOTIFICATION-TYPE
      OBJECTS {
                    objectNameTrapArg,
                    lctNameTrapArg,
                    trapCountTrapArg
                }
      STATUS  current
      DESCRIPTION "Severity    : minor 
                   Format      :  $1 Forced switch from the channel  
                   $2 . 
                   Childtraps  : 
                   Description : Forced Switch Active"
             ::= { alarmsAndEvents 0 10447 }

      trapCCEXManualSwitchToChannel NOTIFICATION-TYPE
      OBJECTS {
                    objectNameTrapArg,
                    lctNameTrapArg,
                    trapCountTrapArg
                }
      STATUS  current
      DESCRIPTION "Severity    : minor 
                   Format      :  $1 Manual switch from the channel  
                   $2 . 
                   Childtraps  : 
                   Description : Manual Switch Active"
             ::= { alarmsAndEvents 0 448 }

      trapCCEXManualSwitchToChannelClear NOTIFICATION-TYPE
      OBJECTS {
                    objectNameTrapArg,
                    lctNameTrapArg,
                    trapCountTrapArg
                }
      STATUS  current
      DESCRIPTION "Severity    : minor 
                   Format      :  $1 Manual switch from the channel  
                   $2 . 
                   Childtraps  : 
                   Description : Manual Switch Active"
             ::= { alarmsAndEvents 0 10448 }

      trapCCEXRevertToWork NOTIFICATION-TYPE
      OBJECTS {
                    objectNameTrapArg,
                    lctNameTrapArg,
                    trapCountTrapArg
                }
      STATUS  current
      DESCRIPTION "Severity    : warning 
                   Format      :  $1 Revertive switch from channel 
                   Childtraps  : 
                   Description : Protection Switch Active"
             ::= { alarmsAndEvents 0 449 }

      trapCCEXRevertToWorkClear NOTIFICATION-TYPE
      OBJECTS {
                    objectNameTrapArg,
                    lctNameTrapArg,
                    trapCountTrapArg
                }
      STATUS  current
      DESCRIPTION "Severity    : warning 
                   Format      :  $1 Revertive switch from channel 
                   Childtraps  : 
                   Description : Protection Switch Active"
             ::= { alarmsAndEvents 0 10449 }

      trapCCEXManualSwitchFailed NOTIFICATION-TYPE
      OBJECTS {
                    objectNameTrapArg,
                    lctNameTrapArg,
                    trapCountTrapArg
                }
      STATUS  current
      DESCRIPTION "Severity    : zilch 
                   Format      :  $1 Manual switch for channel  $2  
                   failed. 
                   Childtraps  : 
                   Description : Manual Switch Fail"
             ::= { alarmsAndEvents 0 450 }

      trapPdhLof NOTIFICATION-TYPE
      OBJECTS {
                    objectNameTrapArg,
                    lctNameTrapArg,
                    trapCountTrapArg,
                    portNumberTrapArg
                }
      STATUS  current
      DESCRIPTION "Severity    : major 
                   Format      :  $1 Loss Of Frame on Port 
                   Childtraps  : 
                   Description : Loss Of Frame on Port"
             ::= { alarmsAndEvents 0 523 }

      trapPdhLofClear NOTIFICATION-TYPE
      OBJECTS {
                    objectNameTrapArg,
                    lctNameTrapArg,
                    trapCountTrapArg,
                    portNumberTrapArg
                }
      STATUS  current
      DESCRIPTION "Severity    : major 
                   Format      :  $1 Loss Of Frame on Port 
                   Childtraps  : 
                   Description : Loss Of Frame on Port"
             ::= { alarmsAndEvents 0 10523 }

      trapIfClientPRBSActive NOTIFICATION-TYPE
      OBJECTS {
                    objectNameTrapArg,
                    lctNameTrapArg,
                    trapCountTrapArg
                }
      STATUS  current
      DESCRIPTION "Severity    : warning 
                   Format      :  $1 PRBS Active on Client Side 
                   Childtraps  : 
                   Description : PRBS Active on Client Side"
             ::= { alarmsAndEvents 0 527 }

      trapIfClientPRBSActiveClear NOTIFICATION-TYPE
      OBJECTS {
                    objectNameTrapArg,
                    lctNameTrapArg,
                    trapCountTrapArg
                }
      STATUS  current
      DESCRIPTION "Severity    : warning 
                   Format      :  $1 PRBS Active on Client Side 
                   Childtraps  : 
                   Description : PRBS Active on Client Side"
             ::= { alarmsAndEvents 0 10527 }

      trapIfNetworkPRBSActive NOTIFICATION-TYPE
      OBJECTS {
                    objectNameTrapArg,
                    lctNameTrapArg,
                    trapCountTrapArg
                }
      STATUS  current
      DESCRIPTION "Severity    : warning 
                   Format      :  $1 PRBS Active on Network Side 
                   Childtraps  : 
                   Description : PRBS Active on Network Side"
             ::= { alarmsAndEvents 0 528 }

      trapIfNetworkPRBSActiveClear NOTIFICATION-TYPE
      OBJECTS {
                    objectNameTrapArg,
                    lctNameTrapArg,
                    trapCountTrapArg
                }
      STATUS  current
      DESCRIPTION "Severity    : warning 
                   Format      :  $1 PRBS Active on Network Side 
                   Childtraps  : 
                   Description : PRBS Active on Network Side"
             ::= { alarmsAndEvents 0 10528 }

      trapIfLossPRBSSync NOTIFICATION-TYPE
      OBJECTS {
                    objectNameTrapArg,
                    lctNameTrapArg,
                    trapCountTrapArg
                }
      STATUS  current
      DESCRIPTION "Severity    : warning 
                   Format      :  $1 Loss of PRBS Synchronization 
                   Childtraps  : 
                   Description : Loss of PRBS Synchronization"
             ::= { alarmsAndEvents 0 529 }

      trapIfLossPRBSSyncClear NOTIFICATION-TYPE
      OBJECTS {
                    objectNameTrapArg,
                    lctNameTrapArg,
                    trapCountTrapArg
                }
      STATUS  current
      DESCRIPTION "Severity    : warning 
                   Format      :  $1 Loss of PRBS Synchronization 
                   Childtraps  : 
                   Description : Loss of PRBS Synchronization"
             ::= { alarmsAndEvents 0 10529 }

      trapPdhTcaUAS NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      :  $1 TCA:UAS on Port  $2  for  $3  
                   interval 
                   Childtraps  : 
                   Description : TCA: Unavailable Seconds - PDH"
             ::= { tcas 0 534 }

      trapPdhLom NOTIFICATION-TYPE
      OBJECTS {
                    objectNameTrapArg,
                    lctNameTrapArg,
                    trapCountTrapArg,
                    portNumberTrapArg
                }
      STATUS  current
      DESCRIPTION "Severity    : major 
                   Format      :  $1 Loss Of MultiFrame on Port 
                   Childtraps  : 
                   Description : Loss Of MultiFrame"
             ::= { alarmsAndEvents 0 536 }

      trapPdhLomClear NOTIFICATION-TYPE
      OBJECTS {
                    objectNameTrapArg,
                    lctNameTrapArg,
                    trapCountTrapArg,
                    portNumberTrapArg
                }
      STATUS  current
      DESCRIPTION "Severity    : major 
                   Format      :  $1 Loss Of MultiFrame on Port 
                   Childtraps  : 
                   Description : Loss Of MultiFrame"
             ::= { alarmsAndEvents 0 10536 }

      trapPdhRai NOTIFICATION-TYPE
      OBJECTS {
                    objectNameTrapArg,
                    lctNameTrapArg,
                    trapCountTrapArg,
                    portNumberTrapArg
                }
      STATUS  current
      DESCRIPTION "Severity    : major 
                   Childtraps  : 
                   Description : Remote Alarm Indication"
             ::= { alarmsAndEvents 0 538 }

      trapPdhRaiClear NOTIFICATION-TYPE
      OBJECTS {
                    objectNameTrapArg,
                    lctNameTrapArg,
                    trapCountTrapArg,
                    portNumberTrapArg
                }
      STATUS  current
      DESCRIPTION "Severity    : major 
                   Childtraps  : 
                   Description : Remote Alarm Indication"
             ::= { alarmsAndEvents 0 10538 }

      trapPdhTcaPathES NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      :  $1 TCA:ES on Path  $2  for  $3  
                   interval 
                   Childtraps  : 
                   Description : TCA: Errored Seconds - PDH Path"
             ::= { tcas 0 549 }

      trapPdhTcaPathSES NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      :  $1 TCA:SES on Path  $2  for  $3  
                   interval 
                   Childtraps  : 
                   Description : TCA: Severely Errored Seconds - PDH 
                   Path"
             ::= { tcas 0 550 }

      trapPdhTcaPathUAS NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      :  $1 TCA:UAS on Path  $2  for  $3  
                   interval 
                   Childtraps  : 
                   Description : TCA: Unavailable Seconds - PDH Path"
             ::= { tcas 0 551 }

      trapPdhTcaPathCV NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      :  $1 TCA:CV on Path  $2  for  $3  
                   interval 
                   Childtraps  : 
                   Description : TCA:CV Code Violation- PDH Path"
             ::= { tcas 0 552 }

      trapLinkChange NOTIFICATION-TYPE
      OBJECTS {
                    objectNameTrapArg,
                    lctNameTrapArg,
                    trapCountTrapArg,
                    portNumberTrapArg
                }
      STATUS  current
      DESCRIPTION "Severity    : major 
                   Format      :  $1  $2 : Link Down~ $3 : Link Up 
                   Childtraps  : 
                   Description : Link Down"
             ::= { alarmsAndEvents 0 305 }

      trapLinkChangeClear NOTIFICATION-TYPE
      OBJECTS {
                    objectNameTrapArg,
                    lctNameTrapArg,
                    trapCountTrapArg,
                    portNumberTrapArg
                }
      STATUS  current
      DESCRIPTION "Severity    : major 
                   Format      :  $1  $2 : Link Down~ $3 : Link Up 
                   Childtraps  : 
                   Description : Link Down"
             ::= { alarmsAndEvents 0 10305 }

      trapPortMirroringActive NOTIFICATION-TYPE
      OBJECTS {
                    objectNameTrapArg,
                    lctNameTrapArg,
                    trapCountTrapArg
                }
      STATUS  current
      DESCRIPTION "Severity    : minor 
                   Format      :  $1 Port Mirroring Active: 
                   Childtraps  : 
                   Description : Port Mirroring Active"
             ::= { alarmsAndEvents 0 688 }

      trapPortMirroringActiveClear NOTIFICATION-TYPE
      OBJECTS {
                    objectNameTrapArg,
                    lctNameTrapArg,
                    trapCountTrapArg
                }
      STATUS  current
      DESCRIPTION "Severity    : minor 
                   Format      :  $1 Port Mirroring Active: 
                   Childtraps  : 
                   Description : Port Mirroring Active"
             ::= { alarmsAndEvents 0 10688 }

      trapLAGLinkChange NOTIFICATION-TYPE
      OBJECTS {
                    objectNameTrapArg,
                    lctNameTrapArg,
                    trapCountTrapArg,
                    portNumberTrapArg
                }
      STATUS  current
      DESCRIPTION "Severity    : major 
                   Format      :  $1  $2 : LAG Link Down~ $3 : LAG 
                   Link Up 
                   Childtraps  : 
                   Description : LAG Link Down"
             ::= { alarmsAndEvents 0 625 }

      trapLAGLinkChangeClear NOTIFICATION-TYPE
      OBJECTS {
                    objectNameTrapArg,
                    lctNameTrapArg,
                    trapCountTrapArg,
                    portNumberTrapArg
                }
      STATUS  current
      DESCRIPTION "Severity    : major 
                   Format      :  $1  $2 : LAG Link Down~ $3 : LAG 
                   Link Up 
                   Childtraps  : 
                   Description : LAG Link Down"
             ::= { alarmsAndEvents 0 10625 }

      trapRedundancySwitch NOTIFICATION-TYPE
      OBJECTS {
                    objectNameTrapArg,
                    lctNameTrapArg,
                    trapCountTrapArg,
                    slotNumberTrapArg
                }
      STATUS  current
      DESCRIPTION "Severity    : zilch 
                   Format      :  $1 Card in slot  $2  has become 
                   primary. 
                   Childtraps  : 
                   Description : Switch to secondary"
             ::= { alarmsAndEvents 0 1 }

      trapSoftwareVersionUpgraded NOTIFICATION-TYPE
      OBJECTS {
                    objectNameTrapArg,
                    lctNameTrapArg,
                    trapCountTrapArg
                }
      STATUS  current
      DESCRIPTION "Severity    : zilch 
                   Format      :  $1 Software upgraded from version  
                   $2  to 
                   Childtraps  : 
                   Description : Software Version Upgraded"
             ::= { alarmsAndEvents 0 154 }

      trapAuthenticationFailed NOTIFICATION-TYPE
      OBJECTS {
                    objectNameTrapArg,
                    lctNameTrapArg,
                    trapCountTrapArg,
                    usernameTrapArg
                }
      STATUS  current
      DESCRIPTION "Severity    : minor 
                   Format      :  $1 Invalid authentication attempt 
                   for user with login 
                   Childtraps  : 
                   Description : User Authentication Failed
                   HPOVFormat  : Authentication Failure For User 
                   $additionalArg"
             ::= { alarmsAndEvents 0 320 }

      trapAuthenticationFailedClear NOTIFICATION-TYPE
      OBJECTS {
                    objectNameTrapArg,
                    lctNameTrapArg,
                    trapCountTrapArg,
                    usernameTrapArg
                }
      STATUS  current
      DESCRIPTION "Severity    : minor 
                   Format      :  $1 Invalid authentication attempt 
                   for user with login 
                   Childtraps  : 
                   Description : User Authentication Failed
                   HPOVFormat  : Authentication Failure For User 
                   $additionalArg"
             ::= { alarmsAndEvents 0 10320 }

      trapAuthenticationSucceeded NOTIFICATION-TYPE
      OBJECTS {
                    objectNameTrapArg,
                    lctNameTrapArg,
                    trapCountTrapArg,
                    usernameTrapArg
                }
      STATUS  current
      DESCRIPTION "Severity    : zilch 
                   Format      :  $1 User  $2  logged in 
                   Childtraps  : 
                   Description : User Authentication Succeeded
                   HPOVFormat  : Authentication Succeeded For User 
                   $additionalArg"
             ::= { alarmsAndEvents 0 321 }

      trapAuthUserLoggedOut NOTIFICATION-TYPE
      OBJECTS {
                    objectNameTrapArg,
                    lctNameTrapArg,
                    trapCountTrapArg,
                    usernameTrapArg
                }
      STATUS  current
      DESCRIPTION "Severity    : zilch 
                   Format      :  $1 User   $2  logged out. 
                   Childtraps  : 
                   Description : User Logged Out
                   HPOVFormat  : User $additionalArg Logged Out"
             ::= { alarmsAndEvents 0 322 }

      trapConfigurationDefaulted NOTIFICATION-TYPE
      OBJECTS {
                    objectNameTrapArg,
                    lctNameTrapArg,
                    trapCountTrapArg
                }
      STATUS  current
      DESCRIPTION "Severity    : minor 
                   Format      :  $1 Factory Defaults Restored 
                   Childtraps  : 
                   Description : Factory Defaults Restored"
             ::= { alarmsAndEvents 0 682 }

      trapConfigurationDefaultedClear NOTIFICATION-TYPE
      OBJECTS {
                    objectNameTrapArg,
                    lctNameTrapArg,
                    trapCountTrapArg
                }
      STATUS  current
      DESCRIPTION "Severity    : minor 
                   Format      :  $1 Factory Defaults Restored 
                   Childtraps  : 
                   Description : Factory Defaults Restored"
             ::= { alarmsAndEvents 0 10682 }

      trapRoutingTableTooLarge NOTIFICATION-TYPE
      OBJECTS {
                    objectNameTrapArg,
                    lctNameTrapArg,
                    trapCountTrapArg
                }
      STATUS  current
      DESCRIPTION "Severity    : minor 
                   Format      :  $1 Routing table near capacity 
                   Childtraps  : 
                   Description : Routing table near capacity"
             ::= { alarmsAndEvents 0 684 }

      trapRoutingTableTooLargeClear NOTIFICATION-TYPE
      OBJECTS {
                    objectNameTrapArg,
                    lctNameTrapArg,
                    trapCountTrapArg
                }
      STATUS  current
      DESCRIPTION "Severity    : minor 
                   Format      :  $1 Routing table near capacity 
                   Childtraps  : 
                   Description : Routing table near capacity"
             ::= { alarmsAndEvents 0 10684 }

      trapRoutingTableTooLargeMajor NOTIFICATION-TYPE
      OBJECTS {
                    objectNameTrapArg,
                    lctNameTrapArg,
                    trapCountTrapArg
                }
      STATUS  current
      DESCRIPTION "Severity    : major 
                   Format      :  $1 Routing table near capacity 
                   Childtraps  : 
                   Description : Routing table near capacity"
             ::= { alarmsAndEvents 0 685 }

      trapRoutingTableTooLargeMajorClear NOTIFICATION-TYPE
      OBJECTS {
                    objectNameTrapArg,
                    lctNameTrapArg,
                    trapCountTrapArg
                }
      STATUS  current
      DESCRIPTION "Severity    : major 
                   Format      :  $1 Routing table near capacity 
                   Childtraps  : 
                   Description : Routing table near capacity"
             ::= { alarmsAndEvents 0 10685 }

      trapProbableConfigMismatch NOTIFICATION-TYPE
      OBJECTS {
                    objectNameTrapArg,
                    lctNameTrapArg,
                    trapCountTrapArg,
                    slotNumberTrapArg
                }
      STATUS  current
      DESCRIPTION "Severity    : major 
                   Format      :  $1 Probable Config Mismatch on 
                   node. 
                   Childtraps  : 
                   Description : Probable Config Mismatch on node."
             ::= { alarmsAndEvents 0 696 }

      trapNTPSynchronisationLost NOTIFICATION-TYPE
      OBJECTS {
                    objectNameTrapArg,
                    lctNameTrapArg,
                    trapCountTrapArg
                }
      STATUS  current
      DESCRIPTION "Severity    : minor 
                   Format      :  $1 NTP Server Unreachable 
                   Childtraps  : 
                   Description : NTP Server Unreachable"
             ::= { alarmsAndEvents 0 535 }

      trapNTPSynchronisationLostClear NOTIFICATION-TYPE
      OBJECTS {
                    objectNameTrapArg,
                    lctNameTrapArg,
                    trapCountTrapArg
                }
      STATUS  current
      DESCRIPTION "Severity    : minor 
                   Format      :  $1 NTP Server Unreachable 
                   Childtraps  : 
                   Description : NTP Server Unreachable"
             ::= { alarmsAndEvents 0 10535 }

      trapEnvironmentalAlarm NOTIFICATION-TYPE
      OBJECTS {
                    objectNameTrapArg,
                    lctNameTrapArg,
                    trapCountTrapArg
                }
      STATUS  current
      DESCRIPTION "Severity    : critical 
                   Format      :  $1 External alarm 
                   Childtraps  : 
                   Description : External Alarm occurred
                   HPOVFormat  : $LCTName ($additionalArg)"
             ::= { alarmsAndEvents 0 224 }

      trapEnvironmentalAlarmClear NOTIFICATION-TYPE
      OBJECTS {
                    objectNameTrapArg,
                    lctNameTrapArg,
                    trapCountTrapArg
                }
      STATUS  current
      DESCRIPTION "Severity    : critical 
                   Format      :  $1 External alarm 
                   Childtraps  : 
                   Description : External Alarm occurred
                   HPOVFormat  : $LCTName ($additionalArg)"
             ::= { alarmsAndEvents 0 10224 }

      trapLanPortDown NOTIFICATION-TYPE
      OBJECTS {
                    objectNameTrapArg,
                    lctNameTrapArg,
                    trapCountTrapArg,
                    ifNameTrapArg
                }
      STATUS  current
      DESCRIPTION "Severity    : major 
                   Format      :  $1 LAN Port Down 
                   Childtraps  : 
                   Description : LAN Port Down"
             ::= { alarmsAndEvents 0 384 }

      trapLanPortDownClear NOTIFICATION-TYPE
      OBJECTS {
                    objectNameTrapArg,
                    lctNameTrapArg,
                    trapCountTrapArg,
                    ifNameTrapArg
                }
      STATUS  current
      DESCRIPTION "Severity    : major 
                   Format      :  $1 LAN Port Down 
                   Childtraps  : 
                   Description : LAN Port Down"
             ::= { alarmsAndEvents 0 10384 }

      trapDCNFailure NOTIFICATION-TYPE
      OBJECTS {
                    objectNameTrapArg,
                    lctNameTrapArg,
                    trapCountTrapArg,
                    ifNameTrapArg
                }
      STATUS  current
      DESCRIPTION "Severity    : major 
                   Format      :  $1 DCN Failure on 
                   Childtraps  : 
                   Description : DCN Failure"
             ::= { alarmsAndEvents 0 473 }

      trapDCNFailureClear NOTIFICATION-TYPE
      OBJECTS {
                    objectNameTrapArg,
                    lctNameTrapArg,
                    trapCountTrapArg,
                    ifNameTrapArg
                }
      STATUS  current
      DESCRIPTION "Severity    : major 
                   Format      :  $1 DCN Failure on 
                   Childtraps  : 
                   Description : DCN Failure"
             ::= { alarmsAndEvents 0 10473 }

      trapRSDcnFailure NOTIFICATION-TYPE
      OBJECTS {
                    objectNameTrapArg,
                    lctNameTrapArg,
                    trapCountTrapArg,
                    ifNameTrapArg
                }
      STATUS  current
      DESCRIPTION "Severity    : major 
                   Format      :  $1 DCN Failure on 
                   Childtraps  : 
                   Description : Section / RS DCC Link Failure"
             ::= { alarmsAndEvents 0 596 }

      trapRSDcnFailureClear NOTIFICATION-TYPE
      OBJECTS {
                    objectNameTrapArg,
                    lctNameTrapArg,
                    trapCountTrapArg,
                    ifNameTrapArg
                }
      STATUS  current
      DESCRIPTION "Severity    : major 
                   Format      :  $1 DCN Failure on 
                   Childtraps  : 
                   Description : Section / RS DCC Link Failure"
             ::= { alarmsAndEvents 0 10596 }

      trapMSDcnFailure NOTIFICATION-TYPE
      OBJECTS {
                    objectNameTrapArg,
                    lctNameTrapArg,
                    trapCountTrapArg,
                    ifNameTrapArg
                }
      STATUS  current
      DESCRIPTION "Severity    : major 
                   Format      :  $1 DCN Failure on 
                   Childtraps  : 
                   Description : Line / MS DCC Link Failure"
             ::= { alarmsAndEvents 0 597 }

      trapMSDcnFailureClear NOTIFICATION-TYPE
      OBJECTS {
                    objectNameTrapArg,
                    lctNameTrapArg,
                    trapCountTrapArg,
                    ifNameTrapArg
                }
      STATUS  current
      DESCRIPTION "Severity    : major 
                   Format      :  $1 DCN Failure on 
                   Childtraps  : 
                   Description : Line / MS DCC Link Failure"
             ::= { alarmsAndEvents 0 10597 }

      trapCommDcnFailure NOTIFICATION-TYPE
      OBJECTS {
                    objectNameTrapArg,
                    lctNameTrapArg,
                    trapCountTrapArg,
                    ifNameTrapArg
                }
      STATUS  current
      DESCRIPTION "Severity    : major 
                   Format      :  $1 DCN Failure on 
                   Childtraps  : 
                   Description : Communication Link Failure"
             ::= { alarmsAndEvents 0 598 }

      trapCommDcnFailureClear NOTIFICATION-TYPE
      OBJECTS {
                    objectNameTrapArg,
                    lctNameTrapArg,
                    trapCountTrapArg,
                    ifNameTrapArg
                }
      STATUS  current
      DESCRIPTION "Severity    : major 
                   Format      :  $1 DCN Failure on 
                   Childtraps  : 
                   Description : Communication Link Failure"
             ::= { alarmsAndEvents 0 10598 }

      trapInputPowerFeedOverload NOTIFICATION-TYPE
      OBJECTS {
                    objectNameTrapArg,
                    lctNameTrapArg,
                    trapCountTrapArg,
                    slotNumberTrapArg
                }
      STATUS  current
      DESCRIPTION "Severity    : major 
                   Format      :  $1 Input Voltage High on  $2 . 
                   Childtraps  : 
                   Description : Input Voltage High on PSU Card"
             ::= { alarmsAndEvents 0 524 }

      trapInputPowerFeedOverloadClear NOTIFICATION-TYPE
      OBJECTS {
                    objectNameTrapArg,
                    lctNameTrapArg,
                    trapCountTrapArg,
                    slotNumberTrapArg
                }
      STATUS  current
      DESCRIPTION "Severity    : major 
                   Format      :  $1 Input Voltage High on  $2 . 
                   Childtraps  : 
                   Description : Input Voltage High on PSU Card"
             ::= { alarmsAndEvents 0 10524 }

      trapInputPowerFeedUnderload NOTIFICATION-TYPE
      OBJECTS {
                    objectNameTrapArg,
                    lctNameTrapArg,
                    trapCountTrapArg,
                    slotNumberTrapArg
                }
      STATUS  current
      DESCRIPTION "Severity    : major 
                   Format      :  $1 Input Voltage Low on  $2 . 
                   Childtraps  : 
                   Description : Input Voltage Low on PSU Card"
             ::= { alarmsAndEvents 0 525 }

      trapInputPowerFeedUnderloadClear NOTIFICATION-TYPE
      OBJECTS {
                    objectNameTrapArg,
                    lctNameTrapArg,
                    trapCountTrapArg,
                    slotNumberTrapArg
                }
      STATUS  current
      DESCRIPTION "Severity    : major 
                   Format      :  $1 Input Voltage Low on  $2 . 
                   Childtraps  : 
                   Description : Input Voltage Low on PSU Card"
             ::= { alarmsAndEvents 0 10525 }

      trapCircuitProvisioning NOTIFICATION-TYPE
      OBJECTS {
                    objectNameTrapArg,
                    lctNameTrapArg,
                    trapCountTrapArg,
                    serviceIdTrapArg
                }
      STATUS  current
      DESCRIPTION "Severity    : minor 
                   Format      :  $1 Provisioning of circuit  $2  in 
                   progress.~Provisioning of circuit  $3  completed 
                   Childtraps  : 
                   Description : Provisioning in progress"
             ::= { alarmsAndEvents 0 308 }

      trapCircuitProvisioningClear NOTIFICATION-TYPE
      OBJECTS {
                    objectNameTrapArg,
                    lctNameTrapArg,
                    trapCountTrapArg,
                    serviceIdTrapArg
                }
      STATUS  current
      DESCRIPTION "Severity    : minor 
                   Format      :  $1 Provisioning of circuit  $2  in 
                   progress.~Provisioning of circuit  $3  completed 
                   Childtraps  : 
                   Description : Provisioning in progress"
             ::= { alarmsAndEvents 0 10308 }

      trapCircuitProvisioningSucceeded NOTIFICATION-TYPE
      OBJECTS {
                    objectNameTrapArg,
                    lctNameTrapArg,
                    trapCountTrapArg,
                    serviceIdTrapArg
                }
      STATUS  current
      DESCRIPTION "Severity    : zilch 
                   Format      :  $1 Successfully provisioned 
                   circuit  $2 . 
                   Childtraps  : 
                   Description : Successfully provisioned circuit"
             ::= { alarmsAndEvents 0 309 }

      trapCircuitProvisioningFailed NOTIFICATION-TYPE
      OBJECTS {
                    objectNameTrapArg,
                    lctNameTrapArg,
                    trapCountTrapArg,
                    serviceIdTrapArg
                }
      STATUS  current
      DESCRIPTION "Severity    : zilch 
                   Format      :  $1 Failed to provision circuit 
                   Childtraps  : 
                   Description : Failed to provision circuit"
             ::= { alarmsAndEvents 0 310 }

      trapCircuitUnProvisioning NOTIFICATION-TYPE
      OBJECTS {
                    objectNameTrapArg,
                    lctNameTrapArg,
                    trapCountTrapArg,
                    serviceIdTrapArg
                }
      STATUS  current
      DESCRIPTION "Severity    : minor 
                   Format      :  $1 Unprovisioning of circuit  $2  
                   in progress.~Unprovisioning of Circuit  $3  
                   completed 
                   Childtraps  : 
                   Description : Unprovisioning in progress"
             ::= { alarmsAndEvents 0 374 }

      trapCircuitUnProvisioningClear NOTIFICATION-TYPE
      OBJECTS {
                    objectNameTrapArg,
                    lctNameTrapArg,
                    trapCountTrapArg,
                    serviceIdTrapArg
                }
      STATUS  current
      DESCRIPTION "Severity    : minor 
                   Format      :  $1 Unprovisioning of circuit  $2  
                   in progress.~Unprovisioning of Circuit  $3  
                   completed 
                   Childtraps  : 
                   Description : Unprovisioning in progress"
             ::= { alarmsAndEvents 0 10374 }

      trapCircuitUnProvisioningSucceeded NOTIFICATION-TYPE
      OBJECTS {
                    objectNameTrapArg,
                    lctNameTrapArg,
                    trapCountTrapArg,
                    serviceIdTrapArg
                }
      STATUS  current
      DESCRIPTION "Severity    : zilch 
                   Format      :  $1 Successfully unprovisioned 
                   circuit  $2 . 
                   Childtraps  : 
                   Description : Successfully unprovisioned circuit"
             ::= { alarmsAndEvents 0 375 }

      trapCircuitUnprovisioningFailed NOTIFICATION-TYPE
      OBJECTS {
                    objectNameTrapArg,
                    lctNameTrapArg,
                    trapCountTrapArg,
                    serviceIdTrapArg
                }
      STATUS  current
      DESCRIPTION "Severity    : zilch 
                   Format      :  $1 Failed to unprovision circuit 
                   Childtraps  : 
                   Description : Failed to unprovision circuit"
             ::= { alarmsAndEvents 0 376 }

      trapTrafficDown NOTIFICATION-TYPE
      OBJECTS {
                    objectNameTrapArg,
                    lctNameTrapArg,
                    trapCountTrapArg,
                    serviceIdTrapArg
                }
      STATUS  current
      DESCRIPTION "Severity    : major 
                   Format      :  $1 Traffic on circuit  $2  is 
                   down.~Traffic down on circuit  $3  cleared 
                   Childtraps  : 
                   Description : Traffic on circuit is down"
             ::= { alarmsAndEvents 0 379 }

      trapTrafficDownClear NOTIFICATION-TYPE
      OBJECTS {
                    objectNameTrapArg,
                    lctNameTrapArg,
                    trapCountTrapArg,
                    serviceIdTrapArg
                }
      STATUS  current
      DESCRIPTION "Severity    : major 
                   Format      :  $1 Traffic on circuit  $2  is 
                   down.~Traffic down on circuit  $3  cleared 
                   Childtraps  : 
                   Description : Traffic on circuit is down"
             ::= { alarmsAndEvents 0 10379 }

      trapTrafficDegraded NOTIFICATION-TYPE
      OBJECTS {
                    objectNameTrapArg,
                    lctNameTrapArg,
                    trapCountTrapArg,
                    serviceIdTrapArg
                }
      STATUS  current
      DESCRIPTION "Severity    : minor 
                   Format      :  $1 Traffic on circuit  $2  is 
                   degraded.~Traffic degradation cleared on circuit 
                   Childtraps  : 
                   Description : Traffic on circuit is degraded"
             ::= { alarmsAndEvents 0 380 }

      trapTrafficDegradedClear NOTIFICATION-TYPE
      OBJECTS {
                    objectNameTrapArg,
                    lctNameTrapArg,
                    trapCountTrapArg,
                    serviceIdTrapArg
                }
      STATUS  current
      DESCRIPTION "Severity    : minor 
                   Format      :  $1 Traffic on circuit  $2  is 
                   degraded.~Traffic degradation cleared on circuit 
                   Childtraps  : 
                   Description : Traffic on circuit is degraded"
             ::= { alarmsAndEvents 0 10380 }

      trapNoConfigurationFileFound NOTIFICATION-TYPE
      OBJECTS {
                    objectNameTrapArg,
                    lctNameTrapArg,
                    trapCountTrapArg,
                    slotNumberTrapArg
                }
      STATUS  current
      DESCRIPTION "Severity    : minor 
                   Childtraps  : 
                   Description : Configuration File Not Found"
             ::= { alarmsAndEvents 0 6 }

      trapNoConfigurationFileFoundClear NOTIFICATION-TYPE
      OBJECTS {
                    objectNameTrapArg,
                    lctNameTrapArg,
                    trapCountTrapArg,
                    slotNumberTrapArg
                }
      STATUS  current
      DESCRIPTION "Severity    : minor 
                   Childtraps  : 
                   Description : Configuration File Not Found"
             ::= { alarmsAndEvents 0 10006 }

      trapBadChecksum NOTIFICATION-TYPE
      OBJECTS {
                    objectNameTrapArg,
                    lctNameTrapArg,
                    trapCountTrapArg,
                    slotNumberTrapArg
                }
      STATUS  current
      DESCRIPTION "Severity    : major 
                   Format      :  $1 Bad checksum on 
                   image/configuration file on 
                   Childtraps  : 
                   Description : Bad checksum on configuration file"
             ::= { alarmsAndEvents 0 7 }

      trapBadChecksumClear NOTIFICATION-TYPE
      OBJECTS {
                    objectNameTrapArg,
                    lctNameTrapArg,
                    trapCountTrapArg,
                    slotNumberTrapArg
                }
      STATUS  current
      DESCRIPTION "Severity    : major 
                   Format      :  $1 Bad checksum on 
                   image/configuration file on 
                   Childtraps  : 
                   Description : Bad checksum on configuration file"
             ::= { alarmsAndEvents 0 10007 }

      trapBadFile NOTIFICATION-TYPE
      OBJECTS {
                    objectNameTrapArg,
                    lctNameTrapArg,
                    trapCountTrapArg,
                    slotNumberTrapArg
                }
      STATUS  current
      DESCRIPTION "Severity    : zilch 
                   Format      :  $1 Bad configuration file on 
                   Childtraps  : 
                   Description : Bad configuration file"
             ::= { alarmsAndEvents 0 8 }

      trapBadLogFile NOTIFICATION-TYPE
      OBJECTS {
                    objectNameTrapArg,
                    lctNameTrapArg,
                    trapCountTrapArg,
                    slotNumberTrapArg
                }
      STATUS  current
      DESCRIPTION "Severity    : major 
                   Format      :  $1 Bad log file on 
                   Childtraps  : 
                   Description : Bad log file"
             ::= { alarmsAndEvents 0 9 }

      trapOverTemp NOTIFICATION-TYPE
      OBJECTS {
                    objectNameTrapArg,
                    lctNameTrapArg,
                    trapCountTrapArg,
                    slotNumberTrapArg
                }
      STATUS  current
      DESCRIPTION "Severity    : critical 
                   Format      :  $1 Temperature too high on  $2 . 
                   Childtraps  : 
                   Description : Temperature too high."
             ::= { alarmsAndEvents 0 10 }

      trapOverTempClear NOTIFICATION-TYPE
      OBJECTS {
                    objectNameTrapArg,
                    lctNameTrapArg,
                    trapCountTrapArg,
                    slotNumberTrapArg
                }
      STATUS  current
      DESCRIPTION "Severity    : critical 
                   Format      :  $1 Temperature too high on  $2 . 
                   Childtraps  : 
                   Description : Temperature too high."
             ::= { alarmsAndEvents 0 10010 }

      trapCardRemoved NOTIFICATION-TYPE
      OBJECTS {
                    objectNameTrapArg,
                    lctNameTrapArg,
                    trapCountTrapArg,
                    slotNumberTrapArg
                }
      STATUS  current
      DESCRIPTION "Severity    : major 
                   Format      :  $1  $2  missing or removed. 
                   Childtraps  : 
                   Description : Card missing or removed"
             ::= { alarmsAndEvents 0 11 }

      trapCardRemovedClear NOTIFICATION-TYPE
      OBJECTS {
                    objectNameTrapArg,
                    lctNameTrapArg,
                    trapCountTrapArg,
                    slotNumberTrapArg
                }
      STATUS  current
      DESCRIPTION "Severity    : major 
                   Format      :  $1  $2  missing or removed. 
                   Childtraps  : 
                   Description : Card missing or removed"
             ::= { alarmsAndEvents 0 10011 }

      trapFilespaceLow NOTIFICATION-TYPE
      OBJECTS {
                    objectNameTrapArg,
                    lctNameTrapArg,
                    trapCountTrapArg,
                    slotNumberTrapArg
                }
      STATUS  current
      DESCRIPTION "Severity    : minor 
                   Format      :  $1 File system almost full on  $2 
                   . 
                   Childtraps  : 
                   Description : File system almost full"
             ::= { alarmsAndEvents 0 12 }

      trapFilespaceLowClear NOTIFICATION-TYPE
      OBJECTS {
                    objectNameTrapArg,
                    lctNameTrapArg,
                    trapCountTrapArg,
                    slotNumberTrapArg
                }
      STATUS  current
      DESCRIPTION "Severity    : minor 
                   Format      :  $1 File system almost full on  $2 
                   . 
                   Childtraps  : 
                   Description : File system almost full"
             ::= { alarmsAndEvents 0 10012 }

      trapHardwareFailure NOTIFICATION-TYPE
      OBJECTS {
                    objectNameTrapArg,
                    lctNameTrapArg,
                    trapCountTrapArg,
                    slotNumberTrapArg
                }
      STATUS  current
      DESCRIPTION "Severity    : major 
                   Format      :  $1 Hardware Failure on  $2 . 
                   Childtraps  : 
                   Description : Hardware Failure"
             ::= { alarmsAndEvents 0 13 }

      trapHardwareFailureClear NOTIFICATION-TYPE
      OBJECTS {
                    objectNameTrapArg,
                    lctNameTrapArg,
                    trapCountTrapArg,
                    slotNumberTrapArg
                }
      STATUS  current
      DESCRIPTION "Severity    : major 
                   Format      :  $1 Hardware Failure on  $2 . 
                   Childtraps  : 
                   Description : Hardware Failure"
             ::= { alarmsAndEvents 0 10013 }

      trapSoftwareDownloading NOTIFICATION-TYPE
      OBJECTS {
                    objectNameTrapArg,
                    lctNameTrapArg,
                    trapCountTrapArg,
                    slotNumberTrapArg
                }
      STATUS  current
      DESCRIPTION "Severity    : minor 
                   Format      :  $1 Downloading Software on  $2 
                   .~Software Downloading process complete on 
                   Childtraps  : 
                   Description : Software Downloading."
             ::= { alarmsAndEvents 0 14 }

      trapSoftwareDownloadingClear NOTIFICATION-TYPE
      OBJECTS {
                    objectNameTrapArg,
                    lctNameTrapArg,
                    trapCountTrapArg,
                    slotNumberTrapArg
                }
      STATUS  current
      DESCRIPTION "Severity    : minor 
                   Format      :  $1 Downloading Software on  $2 
                   .~Software Downloading process complete on 
                   Childtraps  : 
                   Description : Software Downloading."
             ::= { alarmsAndEvents 0 10014 }

      trapSoftwareFailure NOTIFICATION-TYPE
      OBJECTS {
                    objectNameTrapArg,
                    lctNameTrapArg,
                    trapCountTrapArg,
                    slotNumberTrapArg
                }
      STATUS  current
      DESCRIPTION "Severity    : major 
                   Format      :  $1 Program Fault, Software Failure 
                   on  $2 . 
                   Childtraps  : 
                   Description : Program Fault, Software Failure"
             ::= { alarmsAndEvents 0 15 }

      trapSoftwareFailureClear NOTIFICATION-TYPE
      OBJECTS {
                    objectNameTrapArg,
                    lctNameTrapArg,
                    trapCountTrapArg,
                    slotNumberTrapArg
                }
      STATUS  current
      DESCRIPTION "Severity    : major 
                   Format      :  $1 Program Fault, Software Failure 
                   on  $2 . 
                   Childtraps  : 
                   Description : Program Fault, Software Failure"
             ::= { alarmsAndEvents 0 10015 }

      trapSysBoot NOTIFICATION-TYPE
      OBJECTS {
                    objectNameTrapArg,
                    lctNameTrapArg,
                    trapCountTrapArg,
                    slotNumberTrapArg
                }
      STATUS  current
      DESCRIPTION "Severity    : critical 
                   Format      :  $1  $2  was booted. 
                   Childtraps  : 
                   Description : System Reboot"
             ::= { alarmsAndEvents 0 16 }

      trapSerialEpromFailure NOTIFICATION-TYPE
      OBJECTS {
                    objectNameTrapArg,
                    lctNameTrapArg,
                    trapCountTrapArg,
                    slotNumberTrapArg
                }
      STATUS  current
      DESCRIPTION "Severity    : major 
                   Format      :  $1 Serial EPROM read failed on  $2 
                   . 
                   Childtraps  : 
                   Description : EEPROM Failure"
             ::= { alarmsAndEvents 0 17 }

      trapSerialEpromFailureClear NOTIFICATION-TYPE
      OBJECTS {
                    objectNameTrapArg,
                    lctNameTrapArg,
                    trapCountTrapArg,
                    slotNumberTrapArg
                }
      STATUS  current
      DESCRIPTION "Severity    : major 
                   Format      :  $1 Serial EPROM read failed on  $2 
                   . 
                   Childtraps  : 
                   Description : EEPROM Failure"
             ::= { alarmsAndEvents 0 10017 }

      trapCardFpgaFailure NOTIFICATION-TYPE
      OBJECTS {
                    objectNameTrapArg,
                    lctNameTrapArg,
                    trapCountTrapArg,
                    slotNumberTrapArg
                }
      STATUS  current
      DESCRIPTION "Severity    : major 
                   Format      :  $1 FPGA Load Failure on  $2 . 
                   Childtraps  : 
                   Description : FPGA Load Failure"
             ::= { alarmsAndEvents 0 18 }

      trapCardFpgaFailureClear NOTIFICATION-TYPE
      OBJECTS {
                    objectNameTrapArg,
                    lctNameTrapArg,
                    trapCountTrapArg,
                    slotNumberTrapArg
                }
      STATUS  current
      DESCRIPTION "Severity    : major 
                   Format      :  $1 FPGA Load Failure on  $2 . 
                   Childtraps  : 
                   Description : FPGA Load Failure"
             ::= { alarmsAndEvents 0 10018 }

      trapVersionMismatch NOTIFICATION-TYPE
      OBJECTS {
                    objectNameTrapArg,
                    lctNameTrapArg,
                    trapCountTrapArg,
                    slotNumberTrapArg
                }
      STATUS  current
      DESCRIPTION "Severity    : minor 
                   Format      :  $1 Software version mismatch in 
                   Card on slot  $2 . 
                   Childtraps  : 
                   Description : SW version mismatch"
             ::= { alarmsAndEvents 0 19 }

      trapVersionMismatchClear NOTIFICATION-TYPE
      OBJECTS {
                    objectNameTrapArg,
                    lctNameTrapArg,
                    trapCountTrapArg,
                    slotNumberTrapArg
                }
      STATUS  current
      DESCRIPTION "Severity    : minor 
                   Format      :  $1 Software version mismatch in 
                   Card on slot  $2 . 
                   Childtraps  : 
                   Description : SW version mismatch"
             ::= { alarmsAndEvents 0 10019 }

      trapCfgOutOfSync NOTIFICATION-TYPE
      OBJECTS {
                    objectNameTrapArg,
                    lctNameTrapArg,
                    trapCountTrapArg,
                    slotNumberTrapArg
                }
      STATUS  current
      DESCRIPTION "Severity    : minor 
                   Format      :  $1 Config out of sync in Card on 
                   slot  $2 . 
                   Childtraps  : 
                   Description : Config out of sync."
             ::= { alarmsAndEvents 0 20 }

      trapCfgOutOfSyncClear NOTIFICATION-TYPE
      OBJECTS {
                    objectNameTrapArg,
                    lctNameTrapArg,
                    trapCountTrapArg,
                    slotNumberTrapArg
                }
      STATUS  current
      DESCRIPTION "Severity    : minor 
                   Format      :  $1 Config out of sync in Card on 
                   slot  $2 . 
                   Childtraps  : 
                   Description : Config out of sync."
             ::= { alarmsAndEvents 0 10020 }

      trapRedundantCardFailure NOTIFICATION-TYPE
      OBJECTS {
                    objectNameTrapArg,
                    lctNameTrapArg,
                    trapCountTrapArg,
                    slotNumberTrapArg
                }
      STATUS  current
      DESCRIPTION "Severity    : minor 
                   Format      :  $1 Redundant Card communication 
                   failure on slot  $2 . 
                   Childtraps  : 
                   Description : Redundant pair communication 
                   failure"
             ::= { alarmsAndEvents 0 21 }

      trapRedundantCardFailureClear NOTIFICATION-TYPE
      OBJECTS {
                    objectNameTrapArg,
                    lctNameTrapArg,
                    trapCountTrapArg,
                    slotNumberTrapArg
                }
      STATUS  current
      DESCRIPTION "Severity    : minor 
                   Format      :  $1 Redundant Card communication 
                   failure on slot  $2 . 
                   Childtraps  : 
                   Description : Redundant pair communication 
                   failure"
             ::= { alarmsAndEvents 0 10021 }

      trapI2CBusFailure NOTIFICATION-TYPE
      OBJECTS {
                    objectNameTrapArg,
                    lctNameTrapArg,
                    trapCountTrapArg,
                    slotNumberTrapArg
                }
      STATUS  current
      DESCRIPTION "Severity    : minor 
                   Format      :  $1 I2C Failure in Card on slot 
                   Childtraps  : 
                   Description : Bus Error"
             ::= { alarmsAndEvents 0 22 }

      trapI2CBusFailureClear NOTIFICATION-TYPE
      OBJECTS {
                    objectNameTrapArg,
                    lctNameTrapArg,
                    trapCountTrapArg,
                    slotNumberTrapArg
                }
      STATUS  current
      DESCRIPTION "Severity    : minor 
                   Format      :  $1 I2C Failure in Card on slot 
                   Childtraps  : 
                   Description : Bus Error"
             ::= { alarmsAndEvents 0 10022 }

      trapConfigDownload NOTIFICATION-TYPE
      OBJECTS {
                    objectNameTrapArg,
                    lctNameTrapArg,
                    trapCountTrapArg,
                    slotNumberTrapArg
                }
      STATUS  current
      DESCRIPTION "Severity    : minor 
                   Format      :  $1 Downloading config file on  $2 
                   .~Config Downloading process complete on 
                   Childtraps  : 
                   Description : Config Downloading."
             ::= { alarmsAndEvents 0 23 }

      trapConfigDownloadClear NOTIFICATION-TYPE
      OBJECTS {
                    objectNameTrapArg,
                    lctNameTrapArg,
                    trapCountTrapArg,
                    slotNumberTrapArg
                }
      STATUS  current
      DESCRIPTION "Severity    : minor 
                   Format      :  $1 Downloading config file on  $2 
                   .~Config Downloading process complete on 
                   Childtraps  : 
                   Description : Config Downloading."
             ::= { alarmsAndEvents 0 10023 }

      trapSoftwareCommitting NOTIFICATION-TYPE
      OBJECTS {
                    objectNameTrapArg,
                    lctNameTrapArg,
                    trapCountTrapArg,
                    slotNumberTrapArg
                }
      STATUS  current
      DESCRIPTION "Severity    : minor 
                   Format      :  $1 Committing Software on  $2 
                   .~Software commit process complete on 
                   Childtraps  : 
                   Description : Software Committing."
             ::= { alarmsAndEvents 0 32 }

      trapSoftwareCommittingClear NOTIFICATION-TYPE
      OBJECTS {
                    objectNameTrapArg,
                    lctNameTrapArg,
                    trapCountTrapArg,
                    slotNumberTrapArg
                }
      STATUS  current
      DESCRIPTION "Severity    : minor 
                   Format      :  $1 Committing Software on  $2 
                   .~Software commit process complete on 
                   Childtraps  : 
                   Description : Software Committing."
             ::= { alarmsAndEvents 0 10032 }

      trapMemoryspaceLow NOTIFICATION-TYPE
      OBJECTS {
                    objectNameTrapArg,
                    lctNameTrapArg,
                    trapCountTrapArg,
                    slotNumberTrapArg
                }
      STATUS  current
      DESCRIPTION "Severity    : minor 
                   Format      :  $1 Memory Usage exceeded the 
                   threshold on  $2 . 
                   Childtraps  : 
                   Description : Memory Usage exceeded threshold"
             ::= { alarmsAndEvents 0 116 }

      trapMemoryspaceLowClear NOTIFICATION-TYPE
      OBJECTS {
                    objectNameTrapArg,
                    lctNameTrapArg,
                    trapCountTrapArg,
                    slotNumberTrapArg
                }
      STATUS  current
      DESCRIPTION "Severity    : minor 
                   Format      :  $1 Memory Usage exceeded the 
                   threshold on  $2 . 
                   Childtraps  : 
                   Description : Memory Usage exceeded threshold"
             ::= { alarmsAndEvents 0 10116 }

      trapConfigUpload NOTIFICATION-TYPE
      OBJECTS {
                    objectNameTrapArg,
                    lctNameTrapArg,
                    trapCountTrapArg,
                    slotNumberTrapArg
                }
      STATUS  current
      DESCRIPTION "Severity    : warning 
                   Format      :  $1 Uploading config file on  $2 
                   .~Config Upload process complete on 
                   Childtraps  : 
                   Description : Uploading Config."
             ::= { alarmsAndEvents 0 117 }

      trapConfigUploadClear NOTIFICATION-TYPE
      OBJECTS {
                    objectNameTrapArg,
                    lctNameTrapArg,
                    trapCountTrapArg,
                    slotNumberTrapArg
                }
      STATUS  current
      DESCRIPTION "Severity    : warning 
                   Format      :  $1 Uploading config file on  $2 
                   .~Config Upload process complete on 
                   Childtraps  : 
                   Description : Uploading Config."
             ::= { alarmsAndEvents 0 10117 }

      trapCardMisMatch NOTIFICATION-TYPE
      OBJECTS {
                    objectNameTrapArg,
                    lctNameTrapArg,
                    trapCountTrapArg,
                    cardTypeTrapArg
                }
      STATUS  current
      DESCRIPTION "Severity    : major 
                   Format      :  $1 Card of type  $2  expected but 
                   not found.~Mismatch Resolved for  $3 . 
                   Childtraps  : 
                   Description : Card mismatch"
             ::= { alarmsAndEvents 0 153 }

      trapCardMisMatchClear NOTIFICATION-TYPE
      OBJECTS {
                    objectNameTrapArg,
                    lctNameTrapArg,
                    trapCountTrapArg,
                    cardTypeTrapArg
                }
      STATUS  current
      DESCRIPTION "Severity    : major 
                   Format      :  $1 Card of type  $2  expected but 
                   not found.~Mismatch Resolved for  $3 . 
                   Childtraps  : 
                   Description : Card mismatch"
             ::= { alarmsAndEvents 0 10153 }

      trapSoftwareDownloadFailed NOTIFICATION-TYPE
      OBJECTS {
                    objectNameTrapArg,
                    lctNameTrapArg,
                    trapCountTrapArg,
                    slotNumberTrapArg
                }
      STATUS  current
      DESCRIPTION "Severity    : minor 
                   Format      :  $1 Software Download on  $2  
                   failed. 
                   Childtraps  : 
                   Description : Software Download failed."
             ::= { alarmsAndEvents 0 311 }

      trapSoftwareDownloadFailedClear NOTIFICATION-TYPE
      OBJECTS {
                    objectNameTrapArg,
                    lctNameTrapArg,
                    trapCountTrapArg,
                    slotNumberTrapArg
                }
      STATUS  current
      DESCRIPTION "Severity    : minor 
                   Format      :  $1 Software Download on  $2  
                   failed. 
                   Childtraps  : 
                   Description : Software Download failed."
             ::= { alarmsAndEvents 0 10311 }

      trapConfigDownloadFailed NOTIFICATION-TYPE
      OBJECTS {
                    objectNameTrapArg,
                    lctNameTrapArg,
                    trapCountTrapArg,
                    slotNumberTrapArg
                }
      STATUS  current
      DESCRIPTION "Severity    : zilch 
                   Format      :  $1 Downloading config file on  $2  
                   failed. 
                   Childtraps  : 
                   Description : Downloading Config failed."
             ::= { alarmsAndEvents 0 312 }

      trapConfigUploadFailed NOTIFICATION-TYPE
      OBJECTS {
                    objectNameTrapArg,
                    lctNameTrapArg,
                    trapCountTrapArg,
                    slotNumberTrapArg
                }
      STATUS  current
      DESCRIPTION "Severity    : zilch 
                   Format      :  $1 Uploading config file on  $2  
                   failed. 
                   Childtraps  : 
                   Description : Uploading Config failed."
             ::= { alarmsAndEvents 0 313 }

      trapSoftwareCommitFailed NOTIFICATION-TYPE
      OBJECTS {
                    objectNameTrapArg,
                    lctNameTrapArg,
                    trapCountTrapArg,
                    slotNumberTrapArg
                }
      STATUS  current
      DESCRIPTION "Severity    : zilch 
                   Childtraps  : 
                   Description : Software Commit failed."
             ::= { alarmsAndEvents 0 318 }

      trapSoftwareCommitSucceeded NOTIFICATION-TYPE
      OBJECTS {
                    objectNameTrapArg,
                    lctNameTrapArg,
                    trapCountTrapArg,
                    slotNumberTrapArg
                }
      STATUS  current
      DESCRIPTION "Severity    : zilch 
                   Format      :  $1 Software Commit on  $2  
                   succeeded. 
                   Childtraps  : 
                   Description : Software Commit succeeded."
             ::= { alarmsAndEvents 0 319 }

      trapSoftwareDownloadSucceeded NOTIFICATION-TYPE
      OBJECTS {
                    objectNameTrapArg,
                    lctNameTrapArg,
                    trapCountTrapArg,
                    slotNumberTrapArg
                }
      STATUS  current
      DESCRIPTION "Severity    : zilch 
                   Format      :  $1 Software Download on  $2  
                   succeeded. 
                   Childtraps  : 
                   Description : Software Download succeeded."
             ::= { alarmsAndEvents 0 323 }

      trapInterCardLinkFailure NOTIFICATION-TYPE
      OBJECTS {
                    objectNameTrapArg,
                    lctNameTrapArg,
                    trapCountTrapArg,
                    slotNumberTrapArg
                }
      STATUS  current
      DESCRIPTION "Severity    : minor 
                   Format      :  $1 Communication failure between 
                   Primary PSS card and  $2 . 
                   Childtraps  : 
                   Description : Inter Card Communication failure"
             ::= { alarmsAndEvents 0 378 }

      trapInterCardLinkFailureClear NOTIFICATION-TYPE
      OBJECTS {
                    objectNameTrapArg,
                    lctNameTrapArg,
                    trapCountTrapArg,
                    slotNumberTrapArg
                }
      STATUS  current
      DESCRIPTION "Severity    : minor 
                   Format      :  $1 Communication failure between 
                   Primary PSS card and  $2 . 
                   Childtraps  : 
                   Description : Inter Card Communication failure"
             ::= { alarmsAndEvents 0 10378 }

      trapEventDbVersionMismatch NOTIFICATION-TYPE
      OBJECTS {
                    objectNameTrapArg,
                    lctNameTrapArg,
                    trapCountTrapArg,
                    slotNumberTrapArg
                }
      STATUS  current
      DESCRIPTION "Severity    : zilch 
                   Format      :  $1 Event Database version mismatch 
                   on  $2 . 
                   Childtraps  : 
                   Description : Event Database version mismatch."
             ::= { alarmsAndEvents 0 385 }

      trapFanFailure NOTIFICATION-TYPE
      OBJECTS {
                    objectNameTrapArg,
                    lctNameTrapArg,
                    trapCountTrapArg,
                    fanNumberTrapArg
                }
      STATUS  current
      DESCRIPTION "Severity    : critical 
                   Format      :  $1 Fan failed in slot  $2 . 
                   Childtraps  : 
                   Description : Fan Failed"
             ::= { alarmsAndEvents 0 434 }

      trapFanFailureClear NOTIFICATION-TYPE
      OBJECTS {
                    objectNameTrapArg,
                    lctNameTrapArg,
                    trapCountTrapArg,
                    fanNumberTrapArg
                }
      STATUS  current
      DESCRIPTION "Severity    : critical 
                   Format      :  $1 Fan failed in slot  $2 . 
                   Childtraps  : 
                   Description : Fan Failed"
             ::= { alarmsAndEvents 0 10434 }

      trapOnbdVLow NOTIFICATION-TYPE
      OBJECTS {
                    objectNameTrapArg,
                    lctNameTrapArg,
                    trapCountTrapArg,
                    portNumberTrapArg
                }
      STATUS  current
      DESCRIPTION "Severity    : major 
                   Format      :  $1 Onboard Voltage Low on  $2 . 
                   Childtraps  : 
                   Description : Onboard voltage generation lower 
                   threshold crossed."
             ::= { alarmsAndEvents 0 470 }

      trapOnbdVLowClear NOTIFICATION-TYPE
      OBJECTS {
                    objectNameTrapArg,
                    lctNameTrapArg,
                    trapCountTrapArg,
                    portNumberTrapArg
                }
      STATUS  current
      DESCRIPTION "Severity    : major 
                   Format      :  $1 Onboard Voltage Low on  $2 . 
                   Childtraps  : 
                   Description : Onboard voltage generation lower 
                   threshold crossed."
             ::= { alarmsAndEvents 0 10470 }

      trapOnbdVHigh NOTIFICATION-TYPE
      OBJECTS {
                    objectNameTrapArg,
                    lctNameTrapArg,
                    trapCountTrapArg,
                    portNumberTrapArg
                }
      STATUS  current
      DESCRIPTION "Severity    : major 
                   Format      :  $1 Onboard Voltage High on  $2 . 
                   Childtraps  : 
                   Description : Onboard voltage generation upper 
                   threshold crossed."
             ::= { alarmsAndEvents 0 471 }

      trapOnbdVHighClear NOTIFICATION-TYPE
      OBJECTS {
                    objectNameTrapArg,
                    lctNameTrapArg,
                    trapCountTrapArg,
                    portNumberTrapArg
                }
      STATUS  current
      DESCRIPTION "Severity    : major 
                   Format      :  $1 Onboard Voltage High on  $2 . 
                   Childtraps  : 
                   Description : Onboard voltage generation upper 
                   threshold crossed."
             ::= { alarmsAndEvents 0 10471 }

      trapSystemBoot NOTIFICATION-TYPE
      OBJECTS {
                    objectNameTrapArg,
                    lctNameTrapArg,
                    trapCountTrapArg,
                    slotNumberTrapArg
                }
      STATUS  current
      DESCRIPTION "Severity    : critical 
                   Format      :  $1  $2  was booted. 
                   Childtraps  : 
                   Description : System Reboot"
             ::= { alarmsAndEvents 0 533 }

      trapSystemBootClear NOTIFICATION-TYPE
      OBJECTS {
                    objectNameTrapArg,
                    lctNameTrapArg,
                    trapCountTrapArg,
                    slotNumberTrapArg
                }
      STATUS  current
      DESCRIPTION "Severity    : critical 
                   Format      :  $1  $2  was booted. 
                   Childtraps  : 
                   Description : System Reboot"
             ::= { alarmsAndEvents 0 10533 }

      trapProvisioningDisabled NOTIFICATION-TYPE
      OBJECTS {
                    objectNameTrapArg,
                    lctNameTrapArg,
                    trapCountTrapArg,
                    slotNumberTrapArg
                }
      STATUS  current
      DESCRIPTION "Severity    : critical 
                   Format      :  $1 Provisiong Disabled Since 
                   Filesystem Full on  $2 . 
                   Childtraps  : 
                   Description : Provisioning Disabled -FileSystem 
                   Full"
             ::= { alarmsAndEvents 0 542 }

      trapProvisioningDisabledClear NOTIFICATION-TYPE
      OBJECTS {
                    objectNameTrapArg,
                    lctNameTrapArg,
                    trapCountTrapArg,
                    slotNumberTrapArg
                }
      STATUS  current
      DESCRIPTION "Severity    : critical 
                   Format      :  $1 Provisiong Disabled Since 
                   Filesystem Full on  $2 . 
                   Childtraps  : 
                   Description : Provisioning Disabled -FileSystem 
                   Full"
             ::= { alarmsAndEvents 0 10542 }

      trapConfigRestoreSucceeded NOTIFICATION-TYPE
      OBJECTS {
                    objectNameTrapArg,
                    lctNameTrapArg,
                    trapCountTrapArg,
                    slotNumberTrapArg
                }
      STATUS  current
      DESCRIPTION "Severity    : zilch 
                   Format      :  $1 Downloading config file on  $2  
                   is complete. 
                   Childtraps  : 
                   Description : Database Restore Completed"
             ::= { alarmsAndEvents 0 544 }

      trapConfigRestoreFailedEvent NOTIFICATION-TYPE
      OBJECTS {
                    objectNameTrapArg,
                    lctNameTrapArg,
                    trapCountTrapArg,
                    slotNumberTrapArg
                }
      STATUS  current
      DESCRIPTION "Severity    : zilch 
                   Childtraps  : 
                   Description : Database Restore Failed"
             ::= { alarmsAndEvents 0 545 }

      trapConfigBackupSucceeded NOTIFICATION-TYPE
      OBJECTS {
                    objectNameTrapArg,
                    lctNameTrapArg,
                    trapCountTrapArg,
                    slotNumberTrapArg
                }
      STATUS  current
      DESCRIPTION "Severity    : zilch 
                   Format      :  $1 Uploading config file on  $2 . 
                   Childtraps  : 
                   Description : Database Save Completed"
             ::= { alarmsAndEvents 0 546 }

      trapConfigBackupFailed NOTIFICATION-TYPE
      OBJECTS {
                    objectNameTrapArg,
                    lctNameTrapArg,
                    trapCountTrapArg,
                    slotNumberTrapArg
                }
      STATUS  current
      DESCRIPTION "Severity    : major 
                   Format      :  $1 Uploading config file on  $2  
                   failed. 
                   Childtraps  : 
                   Description : Database Save Failed"
             ::= { alarmsAndEvents 0 547 }

      trapConfigBackupFailedClear NOTIFICATION-TYPE
      OBJECTS {
                    objectNameTrapArg,
                    lctNameTrapArg,
                    trapCountTrapArg,
                    slotNumberTrapArg
                }
      STATUS  current
      DESCRIPTION "Severity    : major 
                   Format      :  $1 Uploading config file on  $2  
                   failed. 
                   Childtraps  : 
                   Description : Database Save Failed"
             ::= { alarmsAndEvents 0 10547 }

      trapUpgradeCheckReleaseStart NOTIFICATION-TYPE
      OBJECTS {
                    objectNameTrapArg,
                    lctNameTrapArg,
                    trapCountTrapArg,
                    slotNumberTrapArg
                }
      STATUS  current
      DESCRIPTION "Severity    : zilch 
                   Format      :  $1 Upgrade Check Release Started. 
                   Childtraps  : 
                   Description : Upgrade Check Release Started"
             ::= { alarmsAndEvents 0 553 }

      trapUpgradeCheckReleasePassed NOTIFICATION-TYPE
      OBJECTS {
                    objectNameTrapArg,
                    lctNameTrapArg,
                    trapCountTrapArg,
                    slotNumberTrapArg
                }
      STATUS  current
      DESCRIPTION "Severity    : zilch 
                   Format      :  $1 Upgrade Check Release Passed. 
                   Childtraps  : 
                   Description : Upgrade Check Release Passed"
             ::= { alarmsAndEvents 0 554 }

      trapUpgradeCheckReleaseFailed NOTIFICATION-TYPE
      OBJECTS {
                    objectNameTrapArg,
                    lctNameTrapArg,
                    trapCountTrapArg,
                    slotNumberTrapArg
                }
      STATUS  current
      DESCRIPTION "Severity    : zilch 
                   Format      :  $1 Upgrade Check Release Failed. 
                   Childtraps  : 
                   Description : Upgrade Check Release Failed"
             ::= { alarmsAndEvents 0 555 }

      trapUpgradeDeliverReleaseStart NOTIFICATION-TYPE
      OBJECTS {
                    objectNameTrapArg,
                    lctNameTrapArg,
                    trapCountTrapArg,
                    slotNumberTrapArg
                }
      STATUS  current
      DESCRIPTION "Severity    : zilch 
                   Format      :  $1 Upgrade Deliver Release 
                   Started. 
                   Childtraps  : 
                   Description : Upgrade Deliver Release Started"
             ::= { alarmsAndEvents 0 556 }

      trapUpgradeDeliverReleasePassed NOTIFICATION-TYPE
      OBJECTS {
                    objectNameTrapArg,
                    lctNameTrapArg,
                    trapCountTrapArg,
                    slotNumberTrapArg
                }
      STATUS  current
      DESCRIPTION "Severity    : zilch 
                   Childtraps  : 
                   Description : Upgrade Deliver Release Passed"
             ::= { alarmsAndEvents 0 557 }

      trapUpgradeDeliverReleaseFailed NOTIFICATION-TYPE
      OBJECTS {
                    objectNameTrapArg,
                    lctNameTrapArg,
                    trapCountTrapArg,
                    slotNumberTrapArg
                }
      STATUS  current
      DESCRIPTION "Severity    : zilch 
                   Childtraps  : 
                   Description : Upgrade Deliver Release Failed"
             ::= { alarmsAndEvents 0 558 }

      trapUpgradeDeleteReleaseStart NOTIFICATION-TYPE
      OBJECTS {
                    objectNameTrapArg,
                    lctNameTrapArg,
                    trapCountTrapArg,
                    slotNumberTrapArg
                }
      STATUS  current
      DESCRIPTION "Severity    : zilch 
                   Childtraps  : 
                   Description : Upgrade Delete Release Started"
             ::= { alarmsAndEvents 0 559 }

      trapUpgradeDeleteReleasePassed NOTIFICATION-TYPE
      OBJECTS {
                    objectNameTrapArg,
                    lctNameTrapArg,
                    trapCountTrapArg,
                    slotNumberTrapArg
                }
      STATUS  current
      DESCRIPTION "Severity    : zilch 
                   Format      :  $1 Upgrade Delete Release Passed. 
                   Childtraps  : 
                   Description : Upgrade Delete Release Passed"
             ::= { alarmsAndEvents 0 560 }

      trapUpgradeDeleteReleaseFailed NOTIFICATION-TYPE
      OBJECTS {
                    objectNameTrapArg,
                    lctNameTrapArg,
                    trapCountTrapArg,
                    slotNumberTrapArg
                }
      STATUS  current
      DESCRIPTION "Severity    : zilch 
                   Format      :  $1 Upgrade Delete Release Failed. 
                   Childtraps  : 
                   Description : Upgrade Delete Release Failed"
             ::= { alarmsAndEvents 0 561 }

      trapUpgradeCheckStart NOTIFICATION-TYPE
      OBJECTS {
                    objectNameTrapArg,
                    lctNameTrapArg,
                    trapCountTrapArg,
                    slotNumberTrapArg
                }
      STATUS  current
      DESCRIPTION "Severity    : zilch 
                   Format      :  $1 Upgrade Check Started. 
                   Childtraps  : 
                   Description : Upgrade Check Started"
             ::= { alarmsAndEvents 0 562 }

      trapUpgradeCheckPassed NOTIFICATION-TYPE
      OBJECTS {
                    objectNameTrapArg,
                    lctNameTrapArg,
                    trapCountTrapArg,
                    slotNumberTrapArg
                }
      STATUS  current
      DESCRIPTION "Severity    : zilch 
                   Format      :  $1 Upgrade Check Passed. 
                   Childtraps  : 
                   Description : Upgrade Check Passed"
             ::= { alarmsAndEvents 0 563 }

      trapUpgradeCheckFailed NOTIFICATION-TYPE
      OBJECTS {
                    objectNameTrapArg,
                    lctNameTrapArg,
                    trapCountTrapArg,
                    slotNumberTrapArg
                }
      STATUS  current
      DESCRIPTION "Severity    : zilch 
                   Format      :  $1 Upgrade Check Failed. 
                   Childtraps  : 
                   Description : Upgrade Check Failed"
             ::= { alarmsAndEvents 0 564 }

      trapUpgradeLoadStart NOTIFICATION-TYPE
      OBJECTS {
                    objectNameTrapArg,
                    lctNameTrapArg,
                    trapCountTrapArg,
                    slotNumberTrapArg
                }
      STATUS  current
      DESCRIPTION "Severity    : zilch 
                   Format      :  $1 Upgrade Load Started. 
                   Childtraps  : 
                   Description : Upgrade Load Started"
             ::= { alarmsAndEvents 0 565 }

      trapUpgradeLoadPassed NOTIFICATION-TYPE
      OBJECTS {
                    objectNameTrapArg,
                    lctNameTrapArg,
                    trapCountTrapArg,
                    slotNumberTrapArg
                }
      STATUS  current
      DESCRIPTION "Severity    : zilch 
                   Format      :  $1 Upgrade Load Passed. 
                   Childtraps  : 
                   Description : Upgrade Load Passed"
             ::= { alarmsAndEvents 0 566 }

      trapUpgradeLoadFailed NOTIFICATION-TYPE
      OBJECTS {
                    objectNameTrapArg,
                    lctNameTrapArg,
                    trapCountTrapArg,
                    slotNumberTrapArg
                }
      STATUS  current
      DESCRIPTION "Severity    : zilch 
                   Format      :  $1 Upgrade Load Failed. 
                   Childtraps  : 
                   Description : Upgrade Load Failed"
             ::= { alarmsAndEvents 0 567 }

      trapUpgradeInvokeStart NOTIFICATION-TYPE
      OBJECTS {
                    objectNameTrapArg,
                    lctNameTrapArg,
                    trapCountTrapArg,
                    slotNumberTrapArg
                }
      STATUS  current
      DESCRIPTION "Severity    : zilch 
                   Format      :  $1 Upgrade Invoke Started. 
                   Childtraps  : 
                   Description : Upgrade Invoke Started"
             ::= { alarmsAndEvents 0 568 }

      trapUpgradeInvokePassed NOTIFICATION-TYPE
      OBJECTS {
                    objectNameTrapArg,
                    lctNameTrapArg,
                    trapCountTrapArg,
                    slotNumberTrapArg
                }
      STATUS  current
      DESCRIPTION "Severity    : zilch 
                   Format      :  $1 Upgrade Invoke Passed. 
                   Childtraps  : 
                   Description : Upgrade Invoke Passed"
             ::= { alarmsAndEvents 0 569 }

      trapUpgradeInvokeFailed NOTIFICATION-TYPE
      OBJECTS {
                    objectNameTrapArg,
                    lctNameTrapArg,
                    trapCountTrapArg,
                    slotNumberTrapArg
                }
      STATUS  current
      DESCRIPTION "Severity    : zilch 
                   Format      :  $1 Upgrade Invoke Failed. 
                   Childtraps  : 
                   Description : Upgrade Invoke Failed"
             ::= { alarmsAndEvents 0 570 }

      trapUpgradeCommitStart NOTIFICATION-TYPE
      OBJECTS {
                    objectNameTrapArg,
                    lctNameTrapArg,
                    trapCountTrapArg,
                    slotNumberTrapArg
                }
      STATUS  current
      DESCRIPTION "Severity    : zilch 
                   Format      :  $1 Upgrade Commit Started. 
                   Childtraps  : 
                   Description : Upgrade Commit Started"
             ::= { alarmsAndEvents 0 571 }

      trapUpgradeCommitPassed NOTIFICATION-TYPE
      OBJECTS {
                    objectNameTrapArg,
                    lctNameTrapArg,
                    trapCountTrapArg,
                    slotNumberTrapArg
                }
      STATUS  current
      DESCRIPTION "Severity    : zilch 
                   Format      :  $1 Upgrade Commit Passed. 
                   Childtraps  : 
                   Description : Upgrade Commit Passed"
             ::= { alarmsAndEvents 0 572 }

      trapUpgradeCommitFailed NOTIFICATION-TYPE
      OBJECTS {
                    objectNameTrapArg,
                    lctNameTrapArg,
                    trapCountTrapArg,
                    slotNumberTrapArg
                }
      STATUS  current
      DESCRIPTION "Severity    : zilch 
                   Format      :  $1 Upgrade Commit Failed. 
                   Childtraps  : 
                   Description : Upgrade Commit Failed"
             ::= { alarmsAndEvents 0 573 }

      trapUpgradeCancelStart NOTIFICATION-TYPE
      OBJECTS {
                    objectNameTrapArg,
                    lctNameTrapArg,
                    trapCountTrapArg,
                    slotNumberTrapArg
                }
      STATUS  current
      DESCRIPTION "Severity    : zilch 
                   Format      :  $1 Upgrade Cancel Started. 
                   Childtraps  : 
                   Description : Upgrade Cancel Started"
             ::= { alarmsAndEvents 0 574 }

      trapUpgradeCancelPassed NOTIFICATION-TYPE
      OBJECTS {
                    objectNameTrapArg,
                    lctNameTrapArg,
                    trapCountTrapArg,
                    slotNumberTrapArg
                }
      STATUS  current
      DESCRIPTION "Severity    : zilch 
                   Format      :  $1 Upgrade Cancel Passed. 
                   Childtraps  : 
                   Description : Upgrade Cancel Passed"
             ::= { alarmsAndEvents 0 575 }

      trapUpgradeCancelFailed NOTIFICATION-TYPE
      OBJECTS {
                    objectNameTrapArg,
                    lctNameTrapArg,
                    trapCountTrapArg,
                    slotNumberTrapArg
                }
      STATUS  current
      DESCRIPTION "Severity    : zilch 
                   Format      :  $1 Upgrade Cancel Failed. 
                   Childtraps  : 
                   Description : Upgrade Cancel Failed"
             ::= { alarmsAndEvents 0 576 }

      trapUpgradeCancelReleaseStart NOTIFICATION-TYPE
      OBJECTS {
                    objectNameTrapArg,
                    lctNameTrapArg,
                    trapCountTrapArg,
                    slotNumberTrapArg
                }
      STATUS  current
      DESCRIPTION "Severity    : zilch 
                   Childtraps  : 
                   Description : Upgrade Cancel Release Started"
             ::= { alarmsAndEvents 0 577 }

      trapUpgradeCancelReleasePassed NOTIFICATION-TYPE
      OBJECTS {
                    objectNameTrapArg,
                    lctNameTrapArg,
                    trapCountTrapArg,
                    slotNumberTrapArg
                }
      STATUS  current
      DESCRIPTION "Severity    : zilch 
                   Format      :  $1 Upgrade Cancel Release Passed. 
                   Childtraps  : 
                   Description : Upgrade Cancel Release Passed"
             ::= { alarmsAndEvents 0 578 }

      trapConfigRestoreFailed NOTIFICATION-TYPE
      OBJECTS {
                    objectNameTrapArg,
                    lctNameTrapArg,
                    trapCountTrapArg,
                    slotNumberTrapArg
                }
      STATUS  current
      DESCRIPTION "Severity    : major 
                   Format      :  $1 Downloading config file on  $2  
                   failed.~Cleared download config file on 
                   Childtraps  : 
                   Description : Database Restore Failed"
             ::= { alarmsAndEvents 0 579 }

      trapConfigRestoreFailedClear NOTIFICATION-TYPE
      OBJECTS {
                    objectNameTrapArg,
                    lctNameTrapArg,
                    trapCountTrapArg,
                    slotNumberTrapArg
                }
      STATUS  current
      DESCRIPTION "Severity    : major 
                   Format      :  $1 Downloading config file on  $2  
                   failed.~Cleared download config file on 
                   Childtraps  : 
                   Description : Database Restore Failed"
             ::= { alarmsAndEvents 0 10579 }

      trapConfigCommitSucceeded NOTIFICATION-TYPE
      OBJECTS {
                    objectNameTrapArg,
                    lctNameTrapArg,
                    trapCountTrapArg,
                    slotNumberTrapArg
                }
      STATUS  current
      DESCRIPTION "Severity    : zilch 
                   Format      :  $1 Database Commit Complete. 
                   Childtraps  : 
                   Description : Database Commit Complete"
             ::= { alarmsAndEvents 0 580 }

      trapConfigCommitFailed NOTIFICATION-TYPE
      OBJECTS {
                    objectNameTrapArg,
                    lctNameTrapArg,
                    trapCountTrapArg,
                    slotNumberTrapArg
                }
      STATUS  current
      DESCRIPTION "Severity    : zilch 
                   Format      :  $1 Database Commit Failure. 
                   Childtraps  : 
                   Description : Database Commit Failure"
             ::= { alarmsAndEvents 0 581 }

      trapUpgradeDeliverReleaseServerUnreachable NOTIFICATION-TYPE
      OBJECTS {
                    objectNameTrapArg,
                    lctNameTrapArg,
                    trapCountTrapArg,
                    slotNumberTrapArg
                }
      STATUS  current
      DESCRIPTION "Severity    : zilch 
                   Format      :  $1 Upgrade Deliver Release Failed 
                   - Cannot Reach Release Server. 
                   Childtraps  : 
                   Description : Upgrade Deliver Release Failed - 
                   Cannot Reach Release Server"
             ::= { alarmsAndEvents 0 582 }

      trapUpgradeDeliverReleaseChecksumFailed NOTIFICATION-TYPE
      OBJECTS {
                    objectNameTrapArg,
                    lctNameTrapArg,
                    trapCountTrapArg,
                    slotNumberTrapArg
                }
      STATUS  current
      DESCRIPTION "Severity    : zilch 
                   Format      :  $1 Upgrade Deliver Release Failed 
                   - Failed Checksum Validation. 
                   Childtraps  : 
                   Description : Upgrade Deliver Release Failed - 
                   Failed Checksum Validation"
             ::= { alarmsAndEvents 0 583 }

      trapUpgradeDeliverReleaseFTPFailed NOTIFICATION-TYPE
      OBJECTS {
                    objectNameTrapArg,
                    lctNameTrapArg,
                    trapCountTrapArg,
                    slotNumberTrapArg
                }
      STATUS  current
      DESCRIPTION "Severity    : zilch 
                   Format      :  $1 Upgrade Deliver Release Failed 
                   - FTP Protocol Error. 
                   Childtraps  : 
                   Description : Upgrade Deliver Release Failed - 
                   FTP Protocol Error"
             ::= { alarmsAndEvents 0 584 }

      trapUpgradeDeliverReleaseDiskSpaceFailed NOTIFICATION-TYPE
      OBJECTS {
                    objectNameTrapArg,
                    lctNameTrapArg,
                    trapCountTrapArg,
                    slotNumberTrapArg
                }
      STATUS  current
      DESCRIPTION "Severity    : zilch 
                   Format      :  $1 Upgrade Deliver Release Failed 
                   - Insufficient Disk Space for Release 
                   Childtraps  : 
                   Description : Upgrade Deliver Release Failed - 
                   Insufficient Disk Space for Release"
             ::= { alarmsAndEvents 0 585 }

      trapUpgradeDeliverReleaseNoReleaseFound NOTIFICATION-TYPE
      OBJECTS {
                    objectNameTrapArg,
                    lctNameTrapArg,
                    trapCountTrapArg,
                    slotNumberTrapArg
                }
      STATUS  current
      DESCRIPTION "Severity    : zilch 
                   Format      :  $1 Upgrade Deliver Release Failed 
                   - Release does not exist on Release Server 
                   Childtraps  : 
                   Description : Upgrade Deliver Release Failed - 
                   Release does not exist on release server"
             ::= { alarmsAndEvents 0 586 }

      trapUpgradeCheckReleaseServerUnreachable NOTIFICATION-TYPE
      OBJECTS {
                    objectNameTrapArg,
                    lctNameTrapArg,
                    trapCountTrapArg,
                    slotNumberTrapArg
                }
      STATUS  current
      DESCRIPTION "Severity    : zilch 
                   Format      :  $1 Upgrade Check Release Failed - 
                   Cannot Reach Release Server. 
                   Childtraps  : 
                   Description : Upgrade Check Release Failed - 
                   Cannot Reach Release Server"
             ::= { alarmsAndEvents 0 587 }

      trapUpgradeCheckChecksumFailed NOTIFICATION-TYPE
      OBJECTS {
                    objectNameTrapArg,
                    lctNameTrapArg,
                    trapCountTrapArg,
                    slotNumberTrapArg
                }
      STATUS  current
      DESCRIPTION "Severity    : zilch 
                   Format      :  $1 Upgrade Check Failed - Failed 
                   Checksum Validation. 
                   Childtraps  : 
                   Description : Upgrade Check  Failed - Failed 
                   Checksum Validation"
             ::= { alarmsAndEvents 0 588 }

      trapUpgradeCheckAlreadyRunningRelease NOTIFICATION-TYPE
      OBJECTS {
                    objectNameTrapArg,
                    lctNameTrapArg,
                    trapCountTrapArg,
                    slotNumberTrapArg
                }
      STATUS  current
      DESCRIPTION "Severity    : zilch 
                   Format      :  $1 Upgrade Check Failed - NE 
                   Already Running Release. 
                   Childtraps  : 
                   Description : Upgrade Check  Failed - NE already 
                   running Release"
             ::= { alarmsAndEvents 0 589 }

      trapUpgradeCheckRelNotFound NOTIFICATION-TYPE
      OBJECTS {
                    objectNameTrapArg,
                    lctNameTrapArg,
                    trapCountTrapArg,
                    slotNumberTrapArg
                }
      STATUS  current
      DESCRIPTION "Severity    : zilch 
                   Format      :  $1 Upgrade Check Failed - Release 
                   does not exist on release server 
                   Childtraps  : 
                   Description : Upgrade Check Failed - Release does 
                   not exist on release server"
             ::= { alarmsAndEvents 0 590 }

      trapUpgradeCheckUpgradeNotSupported NOTIFICATION-TYPE
      OBJECTS {
                    objectNameTrapArg,
                    lctNameTrapArg,
                    trapCountTrapArg,
                    slotNumberTrapArg
                }
      STATUS  current
      DESCRIPTION "Severity    : zilch 
                   Format      :  $1 Upgrade Check Failed - Upgrade 
                   to Release not supported 
                   Childtraps  : 
                   Description : Upgrade Check Failed - Upgrade to 
                   Release not supported"
             ::= { alarmsAndEvents 0 591 }

      trapUpgradeLoadRelNotFound NOTIFICATION-TYPE
      OBJECTS {
                    objectNameTrapArg,
                    lctNameTrapArg,
                    trapCountTrapArg,
                    slotNumberTrapArg
                }
      STATUS  current
      DESCRIPTION "Severity    : zilch 
                   Format      :  $1 Upgrade Load Failed - Release 
                   does not exist on NE. 
                   Childtraps  : 
                   Description : Upgrade Load Failed - Release does 
                   not exist on NE"
             ::= { alarmsAndEvents 0 592 }

      trapFirmwareVersionMismatch NOTIFICATION-TYPE
      OBJECTS {
                    objectNameTrapArg,
                    lctNameTrapArg,
                    trapCountTrapArg,
                    slotNumberTrapArg
                }
      STATUS  current
      DESCRIPTION "Severity    : minor 
                   Format      :  $1 Firmware Version Mismatch / 
                   Invalid with Software Version 
                   Childtraps  : 
                   Description : Firmware Version Mismatch / Invalid 
                   with Software Version"
             ::= { alarmsAndEvents 0 594 }

      trapFirmwareVersionMismatchClear NOTIFICATION-TYPE
      OBJECTS {
                    objectNameTrapArg,
                    lctNameTrapArg,
                    trapCountTrapArg,
                    slotNumberTrapArg
                }
      STATUS  current
      DESCRIPTION "Severity    : minor 
                   Format      :  $1 Firmware Version Mismatch / 
                   Invalid with Software Version 
                   Childtraps  : 
                   Description : Firmware Version Mismatch / Invalid 
                   with Software Version"
             ::= { alarmsAndEvents 0 10594 }

      trapDocumentationVersionMismatch NOTIFICATION-TYPE
      OBJECTS {
                    objectNameTrapArg,
                    lctNameTrapArg,
                    trapCountTrapArg,
                    slotNumberTrapArg
                }
      STATUS  current
      DESCRIPTION "Severity    : minor 
                   Format      :  $1 Documentation Version Mismatch 
                   / Invalid with Software Version 
                   Childtraps  : 
                   Description : Documentation Version Mismatch / 
                   Invalid with Software Version"
             ::= { alarmsAndEvents 0 595 }

      trapDocumentationVersionMismatchClear NOTIFICATION-TYPE
      OBJECTS {
                    objectNameTrapArg,
                    lctNameTrapArg,
                    trapCountTrapArg,
                    slotNumberTrapArg
                }
      STATUS  current
      DESCRIPTION "Severity    : minor 
                   Format      :  $1 Documentation Version Mismatch 
                   / Invalid with Software Version 
                   Childtraps  : 
                   Description : Documentation Version Mismatch / 
                   Invalid with Software Version"
             ::= { alarmsAndEvents 0 10595 }

      trapHardwareSuspect NOTIFICATION-TYPE
      OBJECTS {
                    objectNameTrapArg,
                    lctNameTrapArg,
                    trapCountTrapArg,
                    slotNumberTrapArg
                }
      STATUS  current
      DESCRIPTION "Severity    : major 
                   Format      :  $1 Hardware Failure Suspected on  
                   $2 . 
                   Childtraps  : 
                   Description : Intercard Suspected"
             ::= { alarmsAndEvents 0 607 }

      trapHardwareSuspectClear NOTIFICATION-TYPE
      OBJECTS {
                    objectNameTrapArg,
                    lctNameTrapArg,
                    trapCountTrapArg,
                    slotNumberTrapArg
                }
      STATUS  current
      DESCRIPTION "Severity    : major 
                   Format      :  $1 Hardware Failure Suspected on  
                   $2 . 
                   Childtraps  : 
                   Description : Intercard Suspected"
             ::= { alarmsAndEvents 0 10607 }

      trapWorkFanFailure NOTIFICATION-TYPE
      OBJECTS {
                    objectNameTrapArg,
                    lctNameTrapArg,
                    trapCountTrapArg,
                    fanNumberTrapArg
                }
      STATUS  current
      DESCRIPTION "Severity    : major 
                   Format      :  $1 Work Fan Failed in slot  $2 . 
                   Childtraps  : 
                   Description : Work Fan Failed"
             ::= { alarmsAndEvents 0 608 }

      trapWorkFanFailureClear NOTIFICATION-TYPE
      OBJECTS {
                    objectNameTrapArg,
                    lctNameTrapArg,
                    trapCountTrapArg,
                    fanNumberTrapArg
                }
      STATUS  current
      DESCRIPTION "Severity    : major 
                   Format      :  $1 Work Fan Failed in slot  $2 . 
                   Childtraps  : 
                   Description : Work Fan Failed"
             ::= { alarmsAndEvents 0 10608 }

      trapFPGAVersionBelowBaseline NOTIFICATION-TYPE
      OBJECTS {
                    objectNameTrapArg,
                    lctNameTrapArg,
                    trapCountTrapArg,
                    slotNumberTrapArg
                }
      STATUS  current
      DESCRIPTION "Severity    : major 
                   Format      :  $1 FPGA Below Baseline on 
                   Childtraps  : 
                   Description : Cold Restart Required: FPGA Changed"
             ::= { alarmsAndEvents 0 614 }

      trapFPGAVersionBelowBaselineClear NOTIFICATION-TYPE
      OBJECTS {
                    objectNameTrapArg,
                    lctNameTrapArg,
                    trapCountTrapArg,
                    slotNumberTrapArg
                }
      STATUS  current
      DESCRIPTION "Severity    : major 
                   Format      :  $1 FPGA Below Baseline on 
                   Childtraps  : 
                   Description : Cold Restart Required: FPGA Changed"
             ::= { alarmsAndEvents 0 10614 }

      trapCpldVersionBelowBaseline NOTIFICATION-TYPE
      OBJECTS {
                    objectNameTrapArg,
                    lctNameTrapArg,
                    trapCountTrapArg,
                    slotNumberTrapArg,
                    cardTypeTrapArg
                }
      STATUS  current
      DESCRIPTION "Severity    : major 
                   Format      :  $1 CPLD version of card in slot  
                   $2  is below baseline. 
                   Childtraps  : 
                   Description : Circuit Pack Below Baseline"
             ::= { alarmsAndEvents 0 615 }

      trapCpldVersionBelowBaselineClear NOTIFICATION-TYPE
      OBJECTS {
                    objectNameTrapArg,
                    lctNameTrapArg,
                    trapCountTrapArg,
                    slotNumberTrapArg,
                    cardTypeTrapArg
                }
      STATUS  current
      DESCRIPTION "Severity    : major 
                   Format      :  $1 CPLD version of card in slot  
                   $2  is below baseline. 
                   Childtraps  : 
                   Description : Circuit Pack Below Baseline"
             ::= { alarmsAndEvents 0 10615 }

      trapCardUnusable NOTIFICATION-TYPE
      OBJECTS {
                    objectNameTrapArg,
                    lctNameTrapArg,
                    trapCountTrapArg,
                    cardTypeTrapArg
                }
      STATUS  current
      DESCRIPTION "Severity    : major 
                   Format      :  $1 Card Unusable 
                   Childtraps  : 
                   Description : Card Unusable"
             ::= { alarmsAndEvents 0 618 }

      trapCardUnusableClear NOTIFICATION-TYPE
      OBJECTS {
                    objectNameTrapArg,
                    lctNameTrapArg,
                    trapCountTrapArg,
                    cardTypeTrapArg
                }
      STATUS  current
      DESCRIPTION "Severity    : major 
                   Format      :  $1 Card Unusable 
                   Childtraps  : 
                   Description : Card Unusable"
             ::= { alarmsAndEvents 0 10618 }

      trapCardForcedSwitchToProtect NOTIFICATION-TYPE
      OBJECTS {
                    objectNameTrapArg,
                    lctNameTrapArg,
                    trapCountTrapArg
                }
      STATUS  current
      DESCRIPTION "Severity    : minor 
                   Format      :  $1 Forced switch to the protect 
                   card  $2 . 
                   Childtraps  : 
                   Description : Forced Switch to protect card"
             ::= { alarmsAndEvents 0 651 }

      trapCardForcedSwitchToProtectClear NOTIFICATION-TYPE
      OBJECTS {
                    objectNameTrapArg,
                    lctNameTrapArg,
                    trapCountTrapArg
                }
      STATUS  current
      DESCRIPTION "Severity    : minor 
                   Format      :  $1 Forced switch to the protect 
                   card  $2 . 
                   Childtraps  : 
                   Description : Forced Switch to protect card"
             ::= { alarmsAndEvents 0 10651 }

      trapCardManualSwitchToProtect NOTIFICATION-TYPE
      OBJECTS {
                    objectNameTrapArg,
                    lctNameTrapArg,
                    trapCountTrapArg
                }
      STATUS  current
      DESCRIPTION "Severity    : minor 
                   Format      :  $1 Manual switch to the protect 
                   card $2 . 
                   Childtraps  : 
                   Description : Manual Switch to protect card"
             ::= { alarmsAndEvents 0 652 }

      trapCardManualSwitchToProtectClear NOTIFICATION-TYPE
      OBJECTS {
                    objectNameTrapArg,
                    lctNameTrapArg,
                    trapCountTrapArg
                }
      STATUS  current
      DESCRIPTION "Severity    : minor 
                   Format      :  $1 Manual switch to the protect 
                   card $2 . 
                   Childtraps  : 
                   Description : Manual Switch to protect card"
             ::= { alarmsAndEvents 0 10652 }

      trapCardLockOut NOTIFICATION-TYPE
      OBJECTS {
                    objectNameTrapArg,
                    lctNameTrapArg,
                    trapCountTrapArg
                }
      STATUS  current
      DESCRIPTION "Severity    : minor 
                   Format      :  $1 Lockout of protection, switch 
                   to the work 
                   Childtraps  : 
                   Description : Card Lockout from protection"
             ::= { alarmsAndEvents 0 653 }

      trapCardLockOutClear NOTIFICATION-TYPE
      OBJECTS {
                    objectNameTrapArg,
                    lctNameTrapArg,
                    trapCountTrapArg
                }
      STATUS  current
      DESCRIPTION "Severity    : minor 
                   Format      :  $1 Lockout of protection, switch 
                   to the work 
                   Childtraps  : 
                   Description : Card Lockout from protection"
             ::= { alarmsAndEvents 0 10653 }

      trapInventoryRemoved NOTIFICATION-TYPE
      OBJECTS {
                    objectNameTrapArg,
                    lctNameTrapArg,
                    trapCountTrapArg,
                    slotNumberTrapArg,
                    cardTypeTrapArg
                }
      STATUS  current
      DESCRIPTION "Severity    : zilch 
                   Format      :  $1  $2  missing or removed. 
                   Childtraps  : 
                   Description : Inventory missing or removed"
             ::= { alarmsAndEvents 0 654 }

      trapFirmwareDownloadSucceeded NOTIFICATION-TYPE
      OBJECTS {
                    objectNameTrapArg,
                    lctNameTrapArg,
                    trapCountTrapArg,
                    slotNumberTrapArg
                }
      STATUS  current
      DESCRIPTION "Severity    : zilch 
                   Format      :  $1 Firmware Download on  $2  
                   succeeded. 
                   Childtraps  : 
                   Description : Firmware Download succeeded."
             ::= { alarmsAndEvents 0 656 }

      trapFirmwareDownloadFailed NOTIFICATION-TYPE
      OBJECTS {
                    objectNameTrapArg,
                    lctNameTrapArg,
                    trapCountTrapArg,
                    slotNumberTrapArg
                }
      STATUS  current
      DESCRIPTION "Severity    : zilch 
                   Format      :  $1 Firmware Download on  $2  
                   failed. 
                   Childtraps  : 
                   Description : Firmware Download failed."
             ::= { alarmsAndEvents 0 657 }

      trapCardNotSupported NOTIFICATION-TYPE
      OBJECTS {
                    objectNameTrapArg,
                    lctNameTrapArg,
                    trapCountTrapArg,
                    cardTypeTrapArg
                }
      STATUS  current
      DESCRIPTION "Severity    : critical 
                   Format      :  $1 Card Type  $2  not supported in 
                   slot. 
                   Childtraps  : 
                   Description : Card not supported in this slot"
             ::= { alarmsAndEvents 0 676 }

      trapCardNotSupportedClear NOTIFICATION-TYPE
      OBJECTS {
                    objectNameTrapArg,
                    lctNameTrapArg,
                    trapCountTrapArg,
                    cardTypeTrapArg
                }
      STATUS  current
      DESCRIPTION "Severity    : critical 
                   Format      :  $1 Card Type  $2  not supported in 
                   slot. 
                   Childtraps  : 
                   Description : Card not supported in this slot"
             ::= { alarmsAndEvents 0 10676 }

      trapHardwareUpgrade NOTIFICATION-TYPE
      OBJECTS {
                    objectNameTrapArg,
                    lctNameTrapArg,
                    trapCountTrapArg,
                    slotNumberTrapArg
                }
      STATUS  current
      DESCRIPTION "Severity    : critical 
                   Format      :  $1 Provisiong Disabled Since 
                   Hardware upgrade process on  $2 . 
                   Childtraps  : 
                   Description : Provisioning Disabled Hardware 
                   Upgrade in progress"
             ::= { alarmsAndEvents 0 677 }

      trapHardwareUpgradeClear NOTIFICATION-TYPE
      OBJECTS {
                    objectNameTrapArg,
                    lctNameTrapArg,
                    trapCountTrapArg,
                    slotNumberTrapArg
                }
      STATUS  current
      DESCRIPTION "Severity    : critical 
                   Format      :  $1 Provisiong Disabled Since 
                   Hardware upgrade process on  $2 . 
                   Childtraps  : 
                   Description : Provisioning Disabled Hardware 
                   Upgrade in progress"
             ::= { alarmsAndEvents 0 10677 }

      trapImproperCardJackIn NOTIFICATION-TYPE
      OBJECTS {
                    objectNameTrapArg,
                    lctNameTrapArg,
                    trapCountTrapArg
                }
      STATUS  current
      DESCRIPTION "Severity    : major 
                   Format      :  $1 Check Card Jackin/Ejector 
                   switches. 
                   Childtraps  : 
                   Description : Improper Card Jackin"
             ::= { alarmsAndEvents 0 695 }

      trapImproperCardJackInClear NOTIFICATION-TYPE
      OBJECTS {
                    objectNameTrapArg,
                    lctNameTrapArg,
                    trapCountTrapArg
                }
      STATUS  current
      DESCRIPTION "Severity    : major 
                   Format      :  $1 Check Card Jackin/Ejector 
                   switches. 
                   Childtraps  : 
                   Description : Improper Card Jackin"
             ::= { alarmsAndEvents 0 10695 }

      trapDebugInfoUploadSucceeded NOTIFICATION-TYPE
      OBJECTS {
                    objectNameTrapArg,
                    lctNameTrapArg,
                    trapCountTrapArg,
                    slotNumberTrapArg
                }
      STATUS  current
      DESCRIPTION "Severity    : zilch 
                   Format      :  $1 Uploading config file on  $2 . 
                   Childtraps  : 
                   Description : DebugInfo Upload Completed"
             ::= { alarmsAndEvents 0 697 }

      trapDebugInfoUploadFailed NOTIFICATION-TYPE
      OBJECTS {
                    objectNameTrapArg,
                    lctNameTrapArg,
                    trapCountTrapArg,
                    slotNumberTrapArg
                }
      STATUS  current
      DESCRIPTION "Severity    : zilch 
                   Format      :  $1 Uploading DebugInfo failed on  
                   $2  failed. 
                   Childtraps  : 
                   Description : Uploading DebugInfo failed."
             ::= { alarmsAndEvents 0 698 }

      trapPluginCard1Removed NOTIFICATION-TYPE
      OBJECTS {
                    objectNameTrapArg,
                    lctNameTrapArg,
                    trapCountTrapArg,
                    slotNumberTrapArg,
                    cardTypeTrapArg
                }
      STATUS  current
      DESCRIPTION "Severity    : critical 
                   Format      :  $1  $2  missing or removed. 
                   Childtraps  : 
                   Description : Plugin card 1 is missing or removed"
             ::= { alarmsAndEvents 0 701 }

      trapPluginCard1RemovedClear NOTIFICATION-TYPE
      OBJECTS {
                    objectNameTrapArg,
                    lctNameTrapArg,
                    trapCountTrapArg,
                    slotNumberTrapArg,
                    cardTypeTrapArg
                }
      STATUS  current
      DESCRIPTION "Severity    : critical 
                   Format      :  $1  $2  missing or removed. 
                   Childtraps  : 
                   Description : Plugin card 1 is missing or removed"
             ::= { alarmsAndEvents 0 10701 }

      trapPluginCard2Removed NOTIFICATION-TYPE
      OBJECTS {
                    objectNameTrapArg,
                    lctNameTrapArg,
                    trapCountTrapArg,
                    slotNumberTrapArg,
                    cardTypeTrapArg
                }
      STATUS  current
      DESCRIPTION "Severity    : critical 
                   Format      :  $1  $2  missing or removed. 
                   Childtraps  : 
                   Description : Plugin card 2 is missing or removed"
             ::= { alarmsAndEvents 0 702 }

      trapPluginCard2RemovedClear NOTIFICATION-TYPE
      OBJECTS {
                    objectNameTrapArg,
                    lctNameTrapArg,
                    trapCountTrapArg,
                    slotNumberTrapArg,
                    cardTypeTrapArg
                }
      STATUS  current
      DESCRIPTION "Severity    : critical 
                   Format      :  $1  $2  missing or removed. 
                   Childtraps  : 
                   Description : Plugin card 2 is missing or removed"
             ::= { alarmsAndEvents 0 10702 }

      trapSourceAutomaticSwitchToProtect NOTIFICATION-TYPE
      OBJECTS {
                    objectNameTrapArg,
                    lctNameTrapArg,
                    trapCountTrapArg
                }
      STATUS  current
      DESCRIPTION "Severity    : zilch 
                   Format      :  $1 Automatic switch to the source 
                   protect channel on crossconnect  $2 . 
                   Childtraps  : 
                   Description : Switch to source protect channel"
             ::= { alarmsAndEvents 0 232 }

      trapSourceAutomaticSwitchToWork NOTIFICATION-TYPE
      OBJECTS {
                    objectNameTrapArg,
                    lctNameTrapArg,
                    trapCountTrapArg
                }
      STATUS  current
      DESCRIPTION "Severity    : zilch 
                   Format      :  $1 Automatic switch to the source 
                   work channel on crossconnect  $2 . 
                   Childtraps  : 
                   Description : Switch to source work channel"
             ::= { alarmsAndEvents 0 233 }

      trapSourceRevertToWork NOTIFICATION-TYPE
      OBJECTS {
                    objectNameTrapArg,
                    lctNameTrapArg,
                    trapCountTrapArg
                }
      STATUS  current
      DESCRIPTION "Severity    : zilch 
                   Format      :  $1 Revert to the source work 
                   channel on crossconnect  $2  complete. 
                   Childtraps  : 
                   Description : Revert to the source work channel"
             ::= { alarmsAndEvents 0 234 }

      trapSourceManualSwitchFailed NOTIFICATION-TYPE
      OBJECTS {
                    objectNameTrapArg,
                    lctNameTrapArg,
                    trapCountTrapArg
                }
      STATUS  current
      DESCRIPTION "Severity    : zilch 
                   Format      :  $1 Manual switch for source 
                   channel on crossconnect  $2  failed. 
                   Childtraps  : 
                   Description : Manual switch for source channel 
                   failed"
             ::= { alarmsAndEvents 0 235 }

      trapDestAutomaticSwitchToProtect NOTIFICATION-TYPE
      OBJECTS {
                    objectNameTrapArg,
                    lctNameTrapArg,
                    trapCountTrapArg
                }
      STATUS  current
      DESCRIPTION "Severity    : zilch 
                   Childtraps  : 
                   Description : Switch to destination protect 
                   channel"
             ::= { alarmsAndEvents 0 236 }

      trapDestAutomaticSwitchToWork NOTIFICATION-TYPE
      OBJECTS {
                    objectNameTrapArg,
                    lctNameTrapArg,
                    trapCountTrapArg
                }
      STATUS  current
      DESCRIPTION "Severity    : zilch 
                   Format      :  $1 Automatic switch to the 
                   destination work channel on crossconnect  $2 . 
                   Childtraps  : 
                   Description : Switch to destination work channel"
             ::= { alarmsAndEvents 0 237 }

      trapDestRevertToWork NOTIFICATION-TYPE
      OBJECTS {
                    objectNameTrapArg,
                    lctNameTrapArg,
                    trapCountTrapArg
                }
      STATUS  current
      DESCRIPTION "Severity    : zilch 
                   Format      :  $1 Revert to the destination work 
                   channel on crossconnect  $2  complete. 
                   Childtraps  : 
                   Description : Revert to the destination work 
                   channel"
             ::= { alarmsAndEvents 0 238 }

      trapDestManualSwitchFailed NOTIFICATION-TYPE
      OBJECTS {
                    objectNameTrapArg,
                    lctNameTrapArg,
                    trapCountTrapArg
                }
      STATUS  current
      DESCRIPTION "Severity    : zilch 
                   Format      :  $1 Manual switch for destination 
                   channel on crossconnect  $2  failed. 
                   Childtraps  : 
                   Description : Manual switch for destination 
                   channel failed"
             ::= { alarmsAndEvents 0 239 }

      trapSourceLockOut NOTIFICATION-TYPE
      OBJECTS {
                    objectNameTrapArg,
                    lctNameTrapArg,
                    trapCountTrapArg
                }
      STATUS  current
      DESCRIPTION "Severity    : zilch 
                   Childtraps  : 
                   Description : Lockout of protection"
             ::= { alarmsAndEvents 0 328 }

      trapSourceForcedSwitchToProtect NOTIFICATION-TYPE
      OBJECTS {
                    objectNameTrapArg,
                    lctNameTrapArg,
                    trapCountTrapArg
                }
      STATUS  current
      DESCRIPTION "Severity    : zilch 
                   Format      :  $1 Forced switch to the source 
                   protect channel on crossconnect  $2 . 
                   Childtraps  : 
                   Description : Forced switch to source protect 
                   channel"
             ::= { alarmsAndEvents 0 329 }

      trapSourceForcedSwitchToWork NOTIFICATION-TYPE
      OBJECTS {
                    objectNameTrapArg,
                    lctNameTrapArg,
                    trapCountTrapArg
                }
      STATUS  current
      DESCRIPTION "Severity    : zilch 
                   Format      :  $1 Forced switch to the source 
                   work channel on crossconnect  $2 . 
                   Childtraps  : 
                   Description : Forced switch to source work 
                   channel"
             ::= { alarmsAndEvents 0 330 }

      trapSourceManualSwitchToProtect NOTIFICATION-TYPE
      OBJECTS {
                    objectNameTrapArg,
                    lctNameTrapArg,
                    trapCountTrapArg
                }
      STATUS  current
      DESCRIPTION "Severity    : zilch 
                   Format      :  $1 Manual switch to the source 
                   protect channel on crossconnect  $2 . 
                   Childtraps  : 
                   Description : Manual switch to source protect 
                   channel"
             ::= { alarmsAndEvents 0 331 }

      trapSourceManualSwitchToWork NOTIFICATION-TYPE
      OBJECTS {
                    objectNameTrapArg,
                    lctNameTrapArg,
                    trapCountTrapArg
                }
      STATUS  current
      DESCRIPTION "Severity    : zilch 
                   Format      :  $1 Manual switch to the source 
                   work channel on crossconnect  $2 . 
                   Childtraps  : 
                   Description : Manual switch to source work 
                   channel"
             ::= { alarmsAndEvents 0 332 }

      trapDestLockOut NOTIFICATION-TYPE
      OBJECTS {
                    objectNameTrapArg,
                    lctNameTrapArg,
                    trapCountTrapArg
                }
      STATUS  current
      DESCRIPTION "Severity    : zilch 
                   Format      :  $1 Lockout of protection, Switch 
                   to the destination work channel on crossconnect  
                   $2  . 
                   Childtraps  : 
                   Description : Lockout of protection"
             ::= { alarmsAndEvents 0 333 }

      trapDestForcedSwitchToProtect NOTIFICATION-TYPE
      OBJECTS {
                    objectNameTrapArg,
                    lctNameTrapArg,
                    trapCountTrapArg
                }
      STATUS  current
      DESCRIPTION "Severity    : zilch 
                   Childtraps  : 
                   Description : Forced switch to destination 
                   protect channel"
             ::= { alarmsAndEvents 0 334 }

      trapDestForcedSwitchToWork NOTIFICATION-TYPE
      OBJECTS {
                    objectNameTrapArg,
                    lctNameTrapArg,
                    trapCountTrapArg
                }
      STATUS  current
      DESCRIPTION "Severity    : zilch 
                   Format      :  $1 Forced switch to the 
                   destination work channel on crossconnect  $2 . 
                   Childtraps  : 
                   Description : Forced switch to destination work 
                   channel"
             ::= { alarmsAndEvents 0 335 }

      trapDestManualSwitchToProtect NOTIFICATION-TYPE
      OBJECTS {
                    objectNameTrapArg,
                    lctNameTrapArg,
                    trapCountTrapArg
                }
      STATUS  current
      DESCRIPTION "Severity    : zilch 
                   Childtraps  : 
                   Description : Manual switch to destination 
                   protect channel"
             ::= { alarmsAndEvents 0 336 }

      trapDestManualSwitchToWork NOTIFICATION-TYPE
      OBJECTS {
                    objectNameTrapArg,
                    lctNameTrapArg,
                    trapCountTrapArg
                }
      STATUS  current
      DESCRIPTION "Severity    : zilch 
                   Format      :  $1 Manual switch to the 
                   destination work channel on crossconnect  $2 . 
                   Childtraps  : 
                   Description : Manual switch to destination work 
                   channel"
             ::= { alarmsAndEvents 0 337 }

      trapLaserFailure NOTIFICATION-TYPE
      OBJECTS {
                    objectNameTrapArg,
                    lctNameTrapArg,
                    trapCountTrapArg,
                    portNumberTrapArg
                }
      STATUS  current
      DESCRIPTION "Severity    : major 
                   Format      :  $1 Laser Failure on  $2 . 
                   Childtraps  : 
                   Description : Laser Failure"
             ::= { alarmsAndEvents 0 24 }

      trapLaserFailureClear NOTIFICATION-TYPE
      OBJECTS {
                    objectNameTrapArg,
                    lctNameTrapArg,
                    trapCountTrapArg,
                    portNumberTrapArg
                }
      STATUS  current
      DESCRIPTION "Severity    : major 
                   Format      :  $1 Laser Failure on  $2 . 
                   Childtraps  : 
                   Description : Laser Failure"
             ::= { alarmsAndEvents 0 10024 }

      trapLaserShutdown NOTIFICATION-TYPE
      OBJECTS {
                    objectNameTrapArg,
                    lctNameTrapArg,
                    trapCountTrapArg,
                    portNumberTrapArg
                }
      STATUS  current
      DESCRIPTION "Severity    : major 
                   Format      :  $1 Laser Shutdown on  $2 . 
                   Childtraps  : 
                   Description : ALS Triggered - Laser is shutdown"
             ::= { alarmsAndEvents 0 25 }

      trapLaserShutdownClear NOTIFICATION-TYPE
      OBJECTS {
                    objectNameTrapArg,
                    lctNameTrapArg,
                    trapCountTrapArg,
                    portNumberTrapArg
                }
      STATUS  current
      DESCRIPTION "Severity    : major 
                   Format      :  $1 Laser Shutdown on  $2 . 
                   Childtraps  : 
                   Description : ALS Triggered - Laser is shutdown"
             ::= { alarmsAndEvents 0 10025 }

      trapLossOfLight NOTIFICATION-TYPE
      OBJECTS {
                    objectNameTrapArg,
                    lctNameTrapArg,
                    trapCountTrapArg,
                    portNumberTrapArg
                }
      STATUS  current
      DESCRIPTION "Severity    : major 
                   Format      :  $1 Loss of Light on  $2 . 
                   Childtraps  : 
                   Description : Loss of Light"
             ::= { alarmsAndEvents 0 26 }

      trapLossOfLightClear NOTIFICATION-TYPE
      OBJECTS {
                    objectNameTrapArg,
                    lctNameTrapArg,
                    trapCountTrapArg,
                    portNumberTrapArg
                }
      STATUS  current
      DESCRIPTION "Severity    : major 
                   Format      :  $1 Loss of Light on  $2 . 
                   Childtraps  : 
                   Description : Loss of Light"
             ::= { alarmsAndEvents 0 10026 }

      trapTxPowerLow NOTIFICATION-TYPE
      OBJECTS {
                    objectNameTrapArg,
                    lctNameTrapArg,
                    trapCountTrapArg,
                    portNumberTrapArg
                }
      STATUS  current
      DESCRIPTION "Severity    : major 
                   Format      :  $1 TxPowerLow on  $2 . 
                   Childtraps  : 
                   Description : Transmitted Power lower threshold 
                   crossed."
             ::= { alarmsAndEvents 0 392 }

      trapTxPowerLowClear NOTIFICATION-TYPE
      OBJECTS {
                    objectNameTrapArg,
                    lctNameTrapArg,
                    trapCountTrapArg,
                    portNumberTrapArg
                }
      STATUS  current
      DESCRIPTION "Severity    : major 
                   Format      :  $1 TxPowerLow on  $2 . 
                   Childtraps  : 
                   Description : Transmitted Power lower threshold 
                   crossed."
             ::= { alarmsAndEvents 0 10392 }

      trapTxPowerHigh NOTIFICATION-TYPE
      OBJECTS {
                    objectNameTrapArg,
                    lctNameTrapArg,
                    trapCountTrapArg,
                    portNumberTrapArg
                }
      STATUS  current
      DESCRIPTION "Severity    : major 
                   Format      :  $1 TxPowerHigh on  $2 . 
                   Childtraps  : 
                   Description : Transmitted Power upper threshold 
                   crossed."
             ::= { alarmsAndEvents 0 393 }

      trapTxPowerHighClear NOTIFICATION-TYPE
      OBJECTS {
                    objectNameTrapArg,
                    lctNameTrapArg,
                    trapCountTrapArg,
                    portNumberTrapArg
                }
      STATUS  current
      DESCRIPTION "Severity    : major 
                   Format      :  $1 TxPowerHigh on  $2 . 
                   Childtraps  : 
                   Description : Transmitted Power upper threshold 
                   crossed."
             ::= { alarmsAndEvents 0 10393 }

      trapLaserBiasLow NOTIFICATION-TYPE
      OBJECTS {
                    objectNameTrapArg,
                    lctNameTrapArg,
                    trapCountTrapArg,
                    portNumberTrapArg
                }
      STATUS  current
      DESCRIPTION "Severity    : major 
                   Format      :  $1 LaserBiasLow on  $2 . 
                   Childtraps  : 
                   Description : Laser Bias current  lower threshold 
                   crossed."
             ::= { alarmsAndEvents 0 394 }

      trapLaserBiasLowClear NOTIFICATION-TYPE
      OBJECTS {
                    objectNameTrapArg,
                    lctNameTrapArg,
                    trapCountTrapArg,
                    portNumberTrapArg
                }
      STATUS  current
      DESCRIPTION "Severity    : major 
                   Format      :  $1 LaserBiasLow on  $2 . 
                   Childtraps  : 
                   Description : Laser Bias current  lower threshold 
                   crossed."
             ::= { alarmsAndEvents 0 10394 }

      trapLaserBiasHigh NOTIFICATION-TYPE
      OBJECTS {
                    objectNameTrapArg,
                    lctNameTrapArg,
                    trapCountTrapArg,
                    portNumberTrapArg
                }
      STATUS  current
      DESCRIPTION "Severity    : major 
                   Format      :  $1 LaserBiasHigh on  $2 . 
                   Childtraps  : 
                   Description : Laser Bias current upper threshold 
                   crossed."
             ::= { alarmsAndEvents 0 395 }

      trapLaserBiasHighClear NOTIFICATION-TYPE
      OBJECTS {
                    objectNameTrapArg,
                    lctNameTrapArg,
                    trapCountTrapArg,
                    portNumberTrapArg
                }
      STATUS  current
      DESCRIPTION "Severity    : major 
                   Format      :  $1 LaserBiasHigh on  $2 . 
                   Childtraps  : 
                   Description : Laser Bias current upper threshold 
                   crossed."
             ::= { alarmsAndEvents 0 10395 }

      trapRxPowerLow NOTIFICATION-TYPE
      OBJECTS {
                    objectNameTrapArg,
                    lctNameTrapArg,
                    trapCountTrapArg,
                    portNumberTrapArg
                }
      STATUS  current
      DESCRIPTION "Severity    : major 
                   Format      :  $1 RxPowerLow on  $2 . 
                   Childtraps  : 
                   Description : Received Power lower threshold 
                   crossed."
             ::= { alarmsAndEvents 0 400 }

      trapRxPowerLowClear NOTIFICATION-TYPE
      OBJECTS {
                    objectNameTrapArg,
                    lctNameTrapArg,
                    trapCountTrapArg,
                    portNumberTrapArg
                }
      STATUS  current
      DESCRIPTION "Severity    : major 
                   Format      :  $1 RxPowerLow on  $2 . 
                   Childtraps  : 
                   Description : Received Power lower threshold 
                   crossed."
             ::= { alarmsAndEvents 0 10400 }

      trapRxPowerHigh NOTIFICATION-TYPE
      OBJECTS {
                    objectNameTrapArg,
                    lctNameTrapArg,
                    trapCountTrapArg,
                    portNumberTrapArg
                }
      STATUS  current
      DESCRIPTION "Severity    : major 
                   Format      :  $1 RxPowerHigh on  $2 . 
                   Childtraps  : 
                   Description : Received Power upper threshold 
                   crossed."
             ::= { alarmsAndEvents 0 401 }

      trapRxPowerHighClear NOTIFICATION-TYPE
      OBJECTS {
                    objectNameTrapArg,
                    lctNameTrapArg,
                    trapCountTrapArg,
                    portNumberTrapArg
                }
      STATUS  current
      DESCRIPTION "Severity    : major 
                   Format      :  $1 RxPowerHigh on  $2 . 
                   Childtraps  : 
                   Description : Received Power upper threshold 
                   crossed."
             ::= { alarmsAndEvents 0 10401 }

      trapLaserTempHigh NOTIFICATION-TYPE
      OBJECTS {
                    objectNameTrapArg,
                    lctNameTrapArg,
                    trapCountTrapArg,
                    portNumberTrapArg
                }
      STATUS  current
      DESCRIPTION "Severity    : major 
                   Format      :  $1 LaserTempHigh on  $2 . 
                   Childtraps  : 
                   Description : Laser temperature high threshold 
                   crossed."
             ::= { alarmsAndEvents 0 429 }

      trapLaserTempHighClear NOTIFICATION-TYPE
      OBJECTS {
                    objectNameTrapArg,
                    lctNameTrapArg,
                    trapCountTrapArg,
                    portNumberTrapArg
                }
      STATUS  current
      DESCRIPTION "Severity    : major 
                   Format      :  $1 LaserTempHigh on  $2 . 
                   Childtraps  : 
                   Description : Laser temperature high threshold 
                   crossed."
             ::= { alarmsAndEvents 0 10429 }

      trapLaserTempLow NOTIFICATION-TYPE
      OBJECTS {
                    objectNameTrapArg,
                    lctNameTrapArg,
                    trapCountTrapArg,
                    portNumberTrapArg
                }
      STATUS  current
      DESCRIPTION "Severity    : major 
                   Format      :  $1 LaserTempLow on  $2 . 
                   Childtraps  : 
                   Description : Laser temperature low threshold 
                   crossed."
             ::= { alarmsAndEvents 0 430 }

      trapLaserTempLowClear NOTIFICATION-TYPE
      OBJECTS {
                    objectNameTrapArg,
                    lctNameTrapArg,
                    trapCountTrapArg,
                    portNumberTrapArg
                }
      STATUS  current
      DESCRIPTION "Severity    : major 
                   Format      :  $1 LaserTempLow on  $2 . 
                   Childtraps  : 
                   Description : Laser temperature low threshold 
                   crossed."
             ::= { alarmsAndEvents 0 10430 }

      trapLaserSupplyVoltageHigh NOTIFICATION-TYPE
      OBJECTS {
                    objectNameTrapArg,
                    lctNameTrapArg,
                    trapCountTrapArg,
                    portNumberTrapArg
                }
      STATUS  current
      DESCRIPTION "Severity    : major 
                   Childtraps  : 
                   Description : Laser supply voltage high threshold 
                   crossed."
             ::= { alarmsAndEvents 0 431 }

      trapLaserSupplyVoltageHighClear NOTIFICATION-TYPE
      OBJECTS {
                    objectNameTrapArg,
                    lctNameTrapArg,
                    trapCountTrapArg,
                    portNumberTrapArg
                }
      STATUS  current
      DESCRIPTION "Severity    : major 
                   Childtraps  : 
                   Description : Laser supply voltage high threshold 
                   crossed."
             ::= { alarmsAndEvents 0 10431 }

      trapLaserSupplyVoltageLow NOTIFICATION-TYPE
      OBJECTS {
                    objectNameTrapArg,
                    lctNameTrapArg,
                    trapCountTrapArg,
                    portNumberTrapArg
                }
      STATUS  current
      DESCRIPTION "Severity    : major 
                   Format      :  $1 LaserSupplyVoltageLow on  $2 . 
                   Childtraps  : 
                   Description : Laser supply voltage low threshold 
                   crossed."
             ::= { alarmsAndEvents 0 432 }

      trapLaserSupplyVoltageLowClear NOTIFICATION-TYPE
      OBJECTS {
                    objectNameTrapArg,
                    lctNameTrapArg,
                    trapCountTrapArg,
                    portNumberTrapArg
                }
      STATUS  current
      DESCRIPTION "Severity    : major 
                   Format      :  $1 LaserSupplyVoltageLow on  $2 . 
                   Childtraps  : 
                   Description : Laser supply voltage low threshold 
                   crossed."
             ::= { alarmsAndEvents 0 10432 }

      trapRingSwitchEast NOTIFICATION-TYPE
      OBJECTS {
                    objectNameTrapArg,
                    lctNameTrapArg,
                    trapCountTrapArg
                }
      STATUS  current
      DESCRIPTION "Severity    : major 
                   Format      :  $1 Ring Switch East on  $2 . 
                   Childtraps  : 
                   Description : Ring Switch East"
             ::= { alarmsAndEvents 0 423 }

      trapRingSwitchEastClear NOTIFICATION-TYPE
      OBJECTS {
                    objectNameTrapArg,
                    lctNameTrapArg,
                    trapCountTrapArg
                }
      STATUS  current
      DESCRIPTION "Severity    : major 
                   Format      :  $1 Ring Switch East on  $2 . 
                   Childtraps  : 
                   Description : Ring Switch East"
             ::= { alarmsAndEvents 0 10423 }

      trapRingSwitchWest NOTIFICATION-TYPE
      OBJECTS {
                    objectNameTrapArg,
                    lctNameTrapArg,
                    trapCountTrapArg
                }
      STATUS  current
      DESCRIPTION "Severity    : major 
                   Format      :  $1 Ring Switch West on  $2 . 
                   Childtraps  : 
                   Description : Ring Switch West"
             ::= { alarmsAndEvents 0 424 }

      trapRingSwitchWestClear NOTIFICATION-TYPE
      OBJECTS {
                    objectNameTrapArg,
                    lctNameTrapArg,
                    trapCountTrapArg
                }
      STATUS  current
      DESCRIPTION "Severity    : major 
                   Format      :  $1 Ring Switch West on  $2 . 
                   Childtraps  : 
                   Description : Ring Switch West"
             ::= { alarmsAndEvents 0 10424 }

      trapSpanSwitchEast NOTIFICATION-TYPE
      OBJECTS {
                    objectNameTrapArg,
                    lctNameTrapArg,
                    trapCountTrapArg
                }
      STATUS  current
      DESCRIPTION "Severity    : major 
                   Format      :  $1 Span Switch East on  $2 . 
                   Childtraps  : 
                   Description : Span Switch East"
             ::= { alarmsAndEvents 0 425 }

      trapSpanSwitchEastClear NOTIFICATION-TYPE
      OBJECTS {
                    objectNameTrapArg,
                    lctNameTrapArg,
                    trapCountTrapArg
                }
      STATUS  current
      DESCRIPTION "Severity    : major 
                   Format      :  $1 Span Switch East on  $2 . 
                   Childtraps  : 
                   Description : Span Switch East"
             ::= { alarmsAndEvents 0 10425 }

      trapSpanSwitchWest NOTIFICATION-TYPE
      OBJECTS {
                    objectNameTrapArg,
                    lctNameTrapArg,
                    trapCountTrapArg
                }
      STATUS  current
      DESCRIPTION "Severity    : major 
                   Format      :  $1 Span Switch West on  $2 . 
                   Childtraps  : 
                   Description : Span Switch West"
             ::= { alarmsAndEvents 0 426 }

      trapSpanSwitchWestClear NOTIFICATION-TYPE
      OBJECTS {
                    objectNameTrapArg,
                    lctNameTrapArg,
                    trapCountTrapArg
                }
      STATUS  current
      DESCRIPTION "Severity    : major 
                   Format      :  $1 Span Switch West on  $2 . 
                   Childtraps  : 
                   Description : Span Switch West"
             ::= { alarmsAndEvents 0 10426 }

      trapInvalidKByteEast NOTIFICATION-TYPE
      OBJECTS {
                    objectNameTrapArg,
                    lctNameTrapArg,
                    trapCountTrapArg
                }
      STATUS  current
      DESCRIPTION "Severity    : major 
                   Format      :  $1 Invalid K byte East on  $2 . 
                   Childtraps  : 
                   Description : Invalid Kbyte East"
             ::= { alarmsAndEvents 0 626 }

      trapInvalidKByteEastClear NOTIFICATION-TYPE
      OBJECTS {
                    objectNameTrapArg,
                    lctNameTrapArg,
                    trapCountTrapArg
                }
      STATUS  current
      DESCRIPTION "Severity    : major 
                   Format      :  $1 Invalid K byte East on  $2 . 
                   Childtraps  : 
                   Description : Invalid Kbyte East"
             ::= { alarmsAndEvents 0 10626 }

      trapInvalidKByteWest NOTIFICATION-TYPE
      OBJECTS {
                    objectNameTrapArg,
                    lctNameTrapArg,
                    trapCountTrapArg
                }
      STATUS  current
      DESCRIPTION "Severity    : major 
                   Format      :  $1 Invalid K byte West on  $2 . 
                   Childtraps  : 
                   Description : Invalid Kbyte West"
             ::= { alarmsAndEvents 0 627 }

      trapInvalidKByteWestClear NOTIFICATION-TYPE
      OBJECTS {
                    objectNameTrapArg,
                    lctNameTrapArg,
                    trapCountTrapArg
                }
      STATUS  current
      DESCRIPTION "Severity    : major 
                   Format      :  $1 Invalid K byte West on  $2 . 
                   Childtraps  : 
                   Description : Invalid Kbyte West"
             ::= { alarmsAndEvents 0 10627 }

      trapEastExerciserFailed NOTIFICATION-TYPE
      OBJECTS {
                    objectNameTrapArg,
                    lctNameTrapArg,
                    trapCountTrapArg
                }
      STATUS  current
      DESCRIPTION "Severity    : zilch 
                   Format      :  $1 Issued Exerciser Failed On East 
                    $2 . 
                   Childtraps  : 
                   Description : Issued Exerciser Failed On East"
             ::= { alarmsAndEvents 0 628 }

      trapEastExerciserSuccess NOTIFICATION-TYPE
      OBJECTS {
                    objectNameTrapArg,
                    lctNameTrapArg,
                    trapCountTrapArg
                }
      STATUS  current
      DESCRIPTION "Severity    : zilch 
                   Format      :  $1 Issued Exerciser Succeced On 
                   East  $2 . 
                   Childtraps  : 
                   Description : Issued Exerciser Succeeced On East"
             ::= { alarmsAndEvents 0 629 }

      trapWestExerciserFailed NOTIFICATION-TYPE
      OBJECTS {
                    objectNameTrapArg,
                    lctNameTrapArg,
                    trapCountTrapArg
                }
      STATUS  current
      DESCRIPTION "Severity    : zilch 
                   Format      :  $1 Issued Exerciser Failed On West 
                    $2 . 
                   Childtraps  : 
                   Description : Issued Exerciser Failed On West"
             ::= { alarmsAndEvents 0 630 }

      trapWestExerciserSuccess NOTIFICATION-TYPE
      OBJECTS {
                    objectNameTrapArg,
                    lctNameTrapArg,
                    trapCountTrapArg
                }
      STATUS  current
      DESCRIPTION "Severity    : zilch 
                   Format      :  $1 Issued Exerciser Succeced On 
                   West  $2 . 
                   Childtraps  : 
                   Description : Issued Exerciser Succeeced On West"
             ::= { alarmsAndEvents 0 631 }

      trapEastManualSwitch NOTIFICATION-TYPE
      OBJECTS {
                    objectNameTrapArg,
                    lctNameTrapArg,
                    trapCountTrapArg
                }
      STATUS  current
      DESCRIPTION "Severity    : minor 
                   Format      :  $1 Manual Switch Active On East  
                   $2 . 
                   Childtraps  : 
                   Description : Manual Switch Active On East"
             ::= { alarmsAndEvents 0 632 }

      trapEastManualSwitchClear NOTIFICATION-TYPE
      OBJECTS {
                    objectNameTrapArg,
                    lctNameTrapArg,
                    trapCountTrapArg
                }
      STATUS  current
      DESCRIPTION "Severity    : minor 
                   Format      :  $1 Manual Switch Active On East  
                   $2 . 
                   Childtraps  : 
                   Description : Manual Switch Active On East"
             ::= { alarmsAndEvents 0 10632 }

      trapEastForceSwitch NOTIFICATION-TYPE
      OBJECTS {
                    objectNameTrapArg,
                    lctNameTrapArg,
                    trapCountTrapArg
                }
      STATUS  current
      DESCRIPTION "Severity    : minor 
                   Format      :  $1 Force Switch Active On East  $2 
                   . 
                   Childtraps  : 
                   Description : Force Switch Active On East"
             ::= { alarmsAndEvents 0 633 }

      trapEastForceSwitchClear NOTIFICATION-TYPE
      OBJECTS {
                    objectNameTrapArg,
                    lctNameTrapArg,
                    trapCountTrapArg
                }
      STATUS  current
      DESCRIPTION "Severity    : minor 
                   Format      :  $1 Force Switch Active On East  $2 
                   . 
                   Childtraps  : 
                   Description : Force Switch Active On East"
             ::= { alarmsAndEvents 0 10633 }

      trapWestManualSwitch NOTIFICATION-TYPE
      OBJECTS {
                    objectNameTrapArg,
                    lctNameTrapArg,
                    trapCountTrapArg
                }
      STATUS  current
      DESCRIPTION "Severity    : minor 
                   Format      :  $1 Manual Switch Active On West  
                   $2 . 
                   Childtraps  : 
                   Description : Manual Switch Active On West"
             ::= { alarmsAndEvents 0 634 }

      trapWestManualSwitchClear NOTIFICATION-TYPE
      OBJECTS {
                    objectNameTrapArg,
                    lctNameTrapArg,
                    trapCountTrapArg
                }
      STATUS  current
      DESCRIPTION "Severity    : minor 
                   Format      :  $1 Manual Switch Active On West  
                   $2 . 
                   Childtraps  : 
                   Description : Manual Switch Active On West"
             ::= { alarmsAndEvents 0 10634 }

      trapWestForceSwitch NOTIFICATION-TYPE
      OBJECTS {
                    objectNameTrapArg,
                    lctNameTrapArg,
                    trapCountTrapArg
                }
      STATUS  current
      DESCRIPTION "Severity    : minor 
                   Format      :  $1 Force Switch Active On West  $2 
                   . 
                   Childtraps  : 
                   Description : Force Switch Active On West"
             ::= { alarmsAndEvents 0 635 }

      trapWestForceSwitchClear NOTIFICATION-TYPE
      OBJECTS {
                    objectNameTrapArg,
                    lctNameTrapArg,
                    trapCountTrapArg
                }
      STATUS  current
      DESCRIPTION "Severity    : minor 
                   Format      :  $1 Force Switch Active On West  $2 
                   . 
                   Childtraps  : 
                   Description : Force Switch Active On West"
             ::= { alarmsAndEvents 0 10635 }

      trapTUAis NOTIFICATION-TYPE
      OBJECTS {
                    objectNameTrapArg,
                    lctNameTrapArg,
                    trapCountTrapArg
                }
      STATUS  current
      DESCRIPTION "Severity    : major 
                   Format      : 
                   Childtraps  : 
                   Description : Alarm Indication Signal"
             ::= { alarmsAndEvents 0 362 }

      trapTUAisClear NOTIFICATION-TYPE
      OBJECTS {
                    objectNameTrapArg,
                    lctNameTrapArg,
                    trapCountTrapArg
                }
      STATUS  current
      DESCRIPTION "Severity    : major 
                   Format      : 
                   Childtraps  : 
                   Description : Alarm Indication Signal"
             ::= { alarmsAndEvents 0 10362 }

      trapTURdi NOTIFICATION-TYPE
      OBJECTS {
                    objectNameTrapArg,
                    lctNameTrapArg,
                    trapCountTrapArg
                }
      STATUS  current
      DESCRIPTION "Severity    : major 
                   Format      : 
                   Childtraps  : 
                   Description : Remote Defect Indication"
             ::= { alarmsAndEvents 0 363 }

      trapTURdiClear NOTIFICATION-TYPE
      OBJECTS {
                    objectNameTrapArg,
                    lctNameTrapArg,
                    trapCountTrapArg
                }
      STATUS  current
      DESCRIPTION "Severity    : major 
                   Format      : 
                   Childtraps  : 
                   Description : Remote Defect Indication"
             ::= { alarmsAndEvents 0 10363 }

      trapTULop NOTIFICATION-TYPE
      OBJECTS {
                    objectNameTrapArg,
                    lctNameTrapArg,
                    trapCountTrapArg
                }
      STATUS  current
      DESCRIPTION "Severity    : major 
                   Format      : 
                   Childtraps  : 
                   Description : Loss of Pointer"
             ::= { alarmsAndEvents 0 364 }

      trapTULopClear NOTIFICATION-TYPE
      OBJECTS {
                    objectNameTrapArg,
                    lctNameTrapArg,
                    trapCountTrapArg
                }
      STATUS  current
      DESCRIPTION "Severity    : major 
                   Format      : 
                   Childtraps  : 
                   Description : Loss of Pointer"
             ::= { alarmsAndEvents 0 10364 }

      trapTUUneq NOTIFICATION-TYPE
      OBJECTS {
                    objectNameTrapArg,
                    lctNameTrapArg,
                    trapCountTrapArg
                }
      STATUS  current
      DESCRIPTION "Severity    : major 
                   Format      : 
                   Childtraps  : 
                   Description : Signal Label Unequipped"
             ::= { alarmsAndEvents 0 365 }

      trapTUUneqClear NOTIFICATION-TYPE
      OBJECTS {
                    objectNameTrapArg,
                    lctNameTrapArg,
                    trapCountTrapArg
                }
      STATUS  current
      DESCRIPTION "Severity    : major 
                   Format      : 
                   Childtraps  : 
                   Description : Signal Label Unequipped"
             ::= { alarmsAndEvents 0 10365 }

      trapTUTIM NOTIFICATION-TYPE
      OBJECTS {
                    objectNameTrapArg,
                    lctNameTrapArg,
                    trapCountTrapArg
                }
      STATUS  current
      DESCRIPTION "Severity    : major 
                   Format      : 
                   Childtraps  : 
                   Description : Trace Identifier Mismatch"
             ::= { alarmsAndEvents 0 366 }

      trapTUTIMClear NOTIFICATION-TYPE
      OBJECTS {
                    objectNameTrapArg,
                    lctNameTrapArg,
                    trapCountTrapArg
                }
      STATUS  current
      DESCRIPTION "Severity    : major 
                   Format      : 
                   Childtraps  : 
                   Description : Trace Identifier Mismatch"
             ::= { alarmsAndEvents 0 10366 }

      trapTUPLM NOTIFICATION-TYPE
      OBJECTS {
                    objectNameTrapArg,
                    lctNameTrapArg,
                    trapCountTrapArg
                }
      STATUS  current
      DESCRIPTION "Severity    : major 
                   Format      : 
                   Childtraps  : 
                   Description : Path Label Mismatch"
             ::= { alarmsAndEvents 0 367 }

      trapTUPLMClear NOTIFICATION-TYPE
      OBJECTS {
                    objectNameTrapArg,
                    lctNameTrapArg,
                    trapCountTrapArg
                }
      STATUS  current
      DESCRIPTION "Severity    : major 
                   Format      : 
                   Childtraps  : 
                   Description : Path Label Mismatch"
             ::= { alarmsAndEvents 0 10367 }

      trapTUSD NOTIFICATION-TYPE
      OBJECTS {
                    objectNameTrapArg,
                    lctNameTrapArg,
                    trapCountTrapArg
                }
      STATUS  current
      DESCRIPTION "Severity    : major 
                   Format      : 
                   Childtraps  : 
                   Description : Signal Degrade"
             ::= { alarmsAndEvents 0 368 }

      trapTUSDClear NOTIFICATION-TYPE
      OBJECTS {
                    objectNameTrapArg,
                    lctNameTrapArg,
                    trapCountTrapArg
                }
      STATUS  current
      DESCRIPTION "Severity    : major 
                   Format      : 
                   Childtraps  : 
                   Description : Signal Degrade"
             ::= { alarmsAndEvents 0 10368 }

      trapTUSF NOTIFICATION-TYPE
      OBJECTS {
                    objectNameTrapArg,
                    lctNameTrapArg,
                    trapCountTrapArg
                }
      STATUS  current
      DESCRIPTION "Severity    : major 
                   Format      : 
                   Childtraps  : 
                   Description : Excessive Error"
             ::= { alarmsAndEvents 0 391 }

      trapTUSFClear NOTIFICATION-TYPE
      OBJECTS {
                    objectNameTrapArg,
                    lctNameTrapArg,
                    trapCountTrapArg
                }
      STATUS  current
      DESCRIPTION "Severity    : major 
                   Format      : 
                   Childtraps  : 
                   Description : Excessive Error"
             ::= { alarmsAndEvents 0 10391 }

      trapCCTUAutomaticSwitchToChannel NOTIFICATION-TYPE
      OBJECTS {
                    objectNameTrapArg,
                    lctNameTrapArg,
                    trapCountTrapArg
                }
      STATUS  current
      DESCRIPTION "Severity    : zilch 
                   Format      :  $1 Non Revertive switch from 
                   channel  $2 . 
                   Childtraps  : 
                   Description : Protection Switch Complete"
             ::= { alarmsAndEvents 0 457 }

      trapCCTULockOut NOTIFICATION-TYPE
      OBJECTS {
                    objectNameTrapArg,
                    lctNameTrapArg,
                    trapCountTrapArg
                }
      STATUS  current
      DESCRIPTION "Severity    : minor 
                   Format      :  $1 Lockout of protection, Switch 
                   from the protect channel  $2  . 
                   Childtraps  : 
                   Description : Lockout Active"
             ::= { alarmsAndEvents 0 458 }

      trapCCTULockOutClear NOTIFICATION-TYPE
      OBJECTS {
                    objectNameTrapArg,
                    lctNameTrapArg,
                    trapCountTrapArg
                }
      STATUS  current
      DESCRIPTION "Severity    : minor 
                   Format      :  $1 Lockout of protection, Switch 
                   from the protect channel  $2  . 
                   Childtraps  : 
                   Description : Lockout Active"
             ::= { alarmsAndEvents 0 10458 }

      trapCCTUForcedSwitchToChannel NOTIFICATION-TYPE
      OBJECTS {
                    objectNameTrapArg,
                    lctNameTrapArg,
                    trapCountTrapArg
                }
      STATUS  current
      DESCRIPTION "Severity    : minor 
                   Format      :  $1 Forced switch from channel  $2 
                   . 
                   Childtraps  : 
                   Description : Forced Switch Active"
             ::= { alarmsAndEvents 0 459 }

      trapCCTUForcedSwitchToChannelClear NOTIFICATION-TYPE
      OBJECTS {
                    objectNameTrapArg,
                    lctNameTrapArg,
                    trapCountTrapArg
                }
      STATUS  current
      DESCRIPTION "Severity    : minor 
                   Format      :  $1 Forced switch from channel  $2 
                   . 
                   Childtraps  : 
                   Description : Forced Switch Active"
             ::= { alarmsAndEvents 0 10459 }

      trapCCTUManualSwitchToChannel NOTIFICATION-TYPE
      OBJECTS {
                    objectNameTrapArg,
                    lctNameTrapArg,
                    trapCountTrapArg
                }
      STATUS  current
      DESCRIPTION "Severity    : minor 
                   Format      :  $1 Manual switch from channel  $2 
                   . 
                   Childtraps  : 
                   Description : Manual Switch Active"
             ::= { alarmsAndEvents 0 460 }

      trapCCTUManualSwitchToChannelClear NOTIFICATION-TYPE
      OBJECTS {
                    objectNameTrapArg,
                    lctNameTrapArg,
                    trapCountTrapArg
                }
      STATUS  current
      DESCRIPTION "Severity    : minor 
                   Format      :  $1 Manual switch from channel  $2 
                   . 
                   Childtraps  : 
                   Description : Manual Switch Active"
             ::= { alarmsAndEvents 0 10460 }

      trapCCTURevertToWork NOTIFICATION-TYPE
      OBJECTS {
                    objectNameTrapArg,
                    lctNameTrapArg,
                    trapCountTrapArg
                }
      STATUS  current
      DESCRIPTION "Severity    : warning 
                   Format      :  $1 Revertive switch from channel 
                   Childtraps  : 
                   Description : Protection Switch Active"
             ::= { alarmsAndEvents 0 461 }

      trapCCTURevertToWorkClear NOTIFICATION-TYPE
      OBJECTS {
                    objectNameTrapArg,
                    lctNameTrapArg,
                    trapCountTrapArg
                }
      STATUS  current
      DESCRIPTION "Severity    : warning 
                   Format      :  $1 Revertive switch from channel 
                   Childtraps  : 
                   Description : Protection Switch Active"
             ::= { alarmsAndEvents 0 10461 }

      trapCCTUManualSwitchFailed NOTIFICATION-TYPE
      OBJECTS {
                    objectNameTrapArg,
                    lctNameTrapArg,
                    trapCountTrapArg
                }
      STATUS  current
      DESCRIPTION "Severity    : zilch 
                   Format      :  $1 Manual switch for channel  $2  
                   failed. 
                   Childtraps  : 
                   Description : Manual Switch Fail"
             ::= { alarmsAndEvents 0 462 }

      trapTURSD NOTIFICATION-TYPE
      OBJECTS {
                    objectNameTrapArg,
                    lctNameTrapArg,
                    trapCountTrapArg
                }
      STATUS  current
      DESCRIPTION "Severity    : major 
                   Format      : 
                   Childtraps  : 
                   Description : Far End Signal Degrade"
             ::= { alarmsAndEvents 0 485 }

      trapTURSDClear NOTIFICATION-TYPE
      OBJECTS {
                    objectNameTrapArg,
                    lctNameTrapArg,
                    trapCountTrapArg
                }
      STATUS  current
      DESCRIPTION "Severity    : major 
                   Format      : 
                   Childtraps  : 
                   Description : Far End Signal Degrade"
             ::= { alarmsAndEvents 0 10485 }

      trapTURSF NOTIFICATION-TYPE
      OBJECTS {
                    objectNameTrapArg,
                    lctNameTrapArg,
                    trapCountTrapArg
                }
      STATUS  current
      DESCRIPTION "Severity    : major 
                   Format      : 
                   Childtraps  : 
                   Description : Far End Excessive Error"
             ::= { alarmsAndEvents 0 486 }

      trapTURSFClear NOTIFICATION-TYPE
      OBJECTS {
                    objectNameTrapArg,
                    lctNameTrapArg,
                    trapCountTrapArg
                }
      STATUS  current
      DESCRIPTION "Severity    : major 
                   Format      : 
                   Childtraps  : 
                   Description : Far End Excessive Error"
             ::= { alarmsAndEvents 0 10486 }

      trapTermTUAis NOTIFICATION-TYPE
      OBJECTS {
                    objectNameTrapArg,
                    lctNameTrapArg,
                    trapCountTrapArg
                }
      STATUS  current
      DESCRIPTION "Severity    : major 
                   Format      : 
                   Childtraps  : 
                   Description : Alarm Indication Signal 
                   (Terminating)"
             ::= { alarmsAndEvents 0 487 }

      trapTermTUAisClear NOTIFICATION-TYPE
      OBJECTS {
                    objectNameTrapArg,
                    lctNameTrapArg,
                    trapCountTrapArg
                }
      STATUS  current
      DESCRIPTION "Severity    : major 
                   Format      : 
                   Childtraps  : 
                   Description : Alarm Indication Signal 
                   (Terminating)"
             ::= { alarmsAndEvents 0 10487 }

      trapTermTURdi NOTIFICATION-TYPE
      OBJECTS {
                    objectNameTrapArg,
                    lctNameTrapArg,
                    trapCountTrapArg
                }
      STATUS  current
      DESCRIPTION "Severity    : major 
                   Format      : 
                   Childtraps  : 
                   Description : Remote Defect Indication 
                   (Terminating)"
             ::= { alarmsAndEvents 0 488 }

      trapTermTURdiClear NOTIFICATION-TYPE
      OBJECTS {
                    objectNameTrapArg,
                    lctNameTrapArg,
                    trapCountTrapArg
                }
      STATUS  current
      DESCRIPTION "Severity    : major 
                   Format      : 
                   Childtraps  : 
                   Description : Remote Defect Indication 
                   (Terminating)"
             ::= { alarmsAndEvents 0 10488 }

      trapTuVCATLoM NOTIFICATION-TYPE
      OBJECTS {
                    objectNameTrapArg,
                    lctNameTrapArg,
                    trapCountTrapArg
                }
      STATUS  current
      DESCRIPTION "Severity    : critical 
                   Format      :  $1 Loss of VCAT Multiframe: 
                   Childtraps  : 
                   Description : Loss of VCAT Multiframe"
             ::= { alarmsAndEvents 0 500 }

      trapTuVCATLoMClear NOTIFICATION-TYPE
      OBJECTS {
                    objectNameTrapArg,
                    lctNameTrapArg,
                    trapCountTrapArg
                }
      STATUS  current
      DESCRIPTION "Severity    : critical 
                   Format      :  $1 Loss of VCAT Multiframe: 
                   Childtraps  : 
                   Description : Loss of VCAT Multiframe"
             ::= { alarmsAndEvents 0 10500 }

      trapTuSQM NOTIFICATION-TYPE
      OBJECTS {
                    objectNameTrapArg,
                    lctNameTrapArg,
                    trapCountTrapArg
                }
      STATUS  current
      DESCRIPTION "Severity    : critical 
                   Format      :  $1 Sequence Number Mismatch: 
                   Childtraps  : 
                   Description : Sequence Number Mismatch"
             ::= { alarmsAndEvents 0 501 }

      trapTuSQMClear NOTIFICATION-TYPE
      OBJECTS {
                    objectNameTrapArg,
                    lctNameTrapArg,
                    trapCountTrapArg
                }
      STATUS  current
      DESCRIPTION "Severity    : critical 
                   Format      :  $1 Sequence Number Mismatch: 
                   Childtraps  : 
                   Description : Sequence Number Mismatch"
             ::= { alarmsAndEvents 0 10501 }

      trapTuTxLTC NOTIFICATION-TYPE
      OBJECTS {
                    objectNameTrapArg,
                    lctNameTrapArg,
                    trapCountTrapArg
                }
      STATUS  current
      DESCRIPTION "Severity    : major 
                   Format      :  $1 Tx Loss of Capacity - LCAS: 
                   Childtraps  : 
                   Description : Tx Loss of Capacity - LCAS"
             ::= { alarmsAndEvents 0 502 }

      trapTuTxLTCClear NOTIFICATION-TYPE
      OBJECTS {
                    objectNameTrapArg,
                    lctNameTrapArg,
                    trapCountTrapArg
                }
      STATUS  current
      DESCRIPTION "Severity    : major 
                   Format      :  $1 Tx Loss of Capacity - LCAS: 
                   Childtraps  : 
                   Description : Tx Loss of Capacity - LCAS"
             ::= { alarmsAndEvents 0 10502 }

      trapTuRxLTC NOTIFICATION-TYPE
      OBJECTS {
                    objectNameTrapArg,
                    lctNameTrapArg,
                    trapCountTrapArg
                }
      STATUS  current
      DESCRIPTION "Severity    : major 
                   Format      :  $1 Rx Loss of Capacity - LCAS: 
                   Childtraps  : 
                   Description : Rx Loss of Capacity - LCAS"
             ::= { alarmsAndEvents 0 503 }

      trapTuRxLTCClear NOTIFICATION-TYPE
      OBJECTS {
                    objectNameTrapArg,
                    lctNameTrapArg,
                    trapCountTrapArg
                }
      STATUS  current
      DESCRIPTION "Severity    : major 
                   Format      :  $1 Rx Loss of Capacity - LCAS: 
                   Childtraps  : 
                   Description : Rx Loss of Capacity - LCAS"
             ::= { alarmsAndEvents 0 10503 }

      trapTuMND NOTIFICATION-TYPE
      OBJECTS {
                    objectNameTrapArg,
                    lctNameTrapArg,
                    trapCountTrapArg
                }
      STATUS  current
      DESCRIPTION "Severity    : major 
                   Format      :  $1 Member Not Deskewable-LCAS: 
                   Childtraps  : 
                   Description : Member Not Deskewable-LCAS"
             ::= { alarmsAndEvents 0 504 }

      trapTuMNDClear NOTIFICATION-TYPE
      OBJECTS {
                    objectNameTrapArg,
                    lctNameTrapArg,
                    trapCountTrapArg
                }
      STATUS  current
      DESCRIPTION "Severity    : major 
                   Format      :  $1 Member Not Deskewable-LCAS: 
                   Childtraps  : 
                   Description : Member Not Deskewable-LCAS"
             ::= { alarmsAndEvents 0 10504 }

      trapTuPCRC NOTIFICATION-TYPE
      OBJECTS {
                    objectNameTrapArg,
                    lctNameTrapArg,
                    trapCountTrapArg
                }
      STATUS  current
      DESCRIPTION "Severity    : minor 
                   Format      :  $1 Persistent CRC errors - LCAS: 
                   Childtraps  : 
                   Description : Persistent CRC errors - LCAS"
             ::= { alarmsAndEvents 0 505 }

      trapTuPCRCClear NOTIFICATION-TYPE
      OBJECTS {
                    objectNameTrapArg,
                    lctNameTrapArg,
                    trapCountTrapArg
                }
      STATUS  current
      DESCRIPTION "Severity    : minor 
                   Format      :  $1 Persistent CRC errors - LCAS: 
                   Childtraps  : 
                   Description : Persistent CRC errors - LCAS"
             ::= { alarmsAndEvents 0 10505 }

      trapTuPUMST NOTIFICATION-TYPE
      OBJECTS {
                    objectNameTrapArg,
                    lctNameTrapArg,
                    trapCountTrapArg
                }
      STATUS  current
      DESCRIPTION "Severity    : minor 
                   Childtraps  : 
                   Description : Persistent Unexepcted MST"
             ::= { alarmsAndEvents 0 506 }

      trapTuPUMSTClear NOTIFICATION-TYPE
      OBJECTS {
                    objectNameTrapArg,
                    lctNameTrapArg,
                    trapCountTrapArg
                }
      STATUS  current
      DESCRIPTION "Severity    : minor 
                   Childtraps  : 
                   Description : Persistent Unexepcted MST"
             ::= { alarmsAndEvents 0 10506 }

      trapTuDDE NOTIFICATION-TYPE
      OBJECTS {
                    objectNameTrapArg,
                    lctNameTrapArg,
                    trapCountTrapArg
                }
      STATUS  current
      DESCRIPTION "Severity    : critical 
                   Format      :  $1 Differential Delay Exceeded: 
                   Childtraps  : 
                   Description : Differential Delay Exceeded"
             ::= { alarmsAndEvents 0 507 }

      trapTuDDEClear NOTIFICATION-TYPE
      OBJECTS {
                    objectNameTrapArg,
                    lctNameTrapArg,
                    trapCountTrapArg
                }
      STATUS  current
      DESCRIPTION "Severity    : critical 
                   Format      :  $1 Differential Delay Exceeded: 
                   Childtraps  : 
                   Description : Differential Delay Exceeded"
             ::= { alarmsAndEvents 0 10507 }

      trapNewRoot NOTIFICATION-TYPE
      OBJECTS {
                    objectNameTrapArg,
                    lctNameTrapArg,
                    trapCountTrapArg
                }
      STATUS  current
      DESCRIPTION "Severity    : minor 
                   Format      :  $1 The Bridge has become Root 
                   Childtraps  : 
                   Description : The Bridge has become Root"
             ::= { alarmsAndEvents 0 427 }

      trapTopologyChange NOTIFICATION-TYPE
      OBJECTS {
                    objectNameTrapArg,
                    lctNameTrapArg,
                    trapCountTrapArg
                }
      STATUS  current
      DESCRIPTION "Severity    : minor 
                   Format      :  $1 Bridge detected a toplogy 
                   change 
                   Childtraps  : 
                   Description : Bridge detected a toplogy change"
             ::= { alarmsAndEvents 0 428 }

      trapStpInstanceNewRoot NOTIFICATION-TYPE
      OBJECTS {
                    objectNameTrapArg,
                    lctNameTrapArg,
                    trapCountTrapArg
                }
      STATUS  current
      DESCRIPTION "Severity    : zilch 
                   Format      :  $1 The Bridge has become Root of 
                   the CIST or in any MSTI. 
                   Childtraps  : 
                   Description : The Bridge has become Root of the 
                   CIST or in any MSTI."
             ::= { alarmsAndEvents 0 600 }

      trapStpInstanceTopologyChange NOTIFICATION-TYPE
      OBJECTS {
                    objectNameTrapArg,
                    lctNameTrapArg,
                    trapCountTrapArg
                }
      STATUS  current
      DESCRIPTION "Severity    : zilch 
                   Format      :  $1 Bridge detected a toplogy 
                   change in CIST or in any MSTI 
                   Childtraps  : 
                   Description : Bridge detected a toplogy change"
             ::= { alarmsAndEvents 0 601 }

      trapSecOOR NOTIFICATION-TYPE
      OBJECTS {
                    objectNameTrapArg,
                    lctNameTrapArg,
                    trapCountTrapArg,
                    portNumberTrapArg
                }
      STATUS  current
      DESCRIPTION "Severity    : major 
                   Format      :  $1 Secondary reference out of 
                   range 
                   Childtraps  : 
                   Description : Secondary reference out of range"
             ::= { alarmsAndEvents 0 412 }

      trapSecOORClear NOTIFICATION-TYPE
      OBJECTS {
                    objectNameTrapArg,
                    lctNameTrapArg,
                    trapCountTrapArg,
                    portNumberTrapArg
                }
      STATUS  current
      DESCRIPTION "Severity    : major 
                   Format      :  $1 Secondary reference out of 
                   range 
                   Childtraps  : 
                   Description : Secondary reference out of range"
             ::= { alarmsAndEvents 0 10412 }

      trapPriOOR NOTIFICATION-TYPE
      OBJECTS {
                    objectNameTrapArg,
                    lctNameTrapArg,
                    trapCountTrapArg,
                    portNumberTrapArg
                }
      STATUS  current
      DESCRIPTION "Severity    : major 
                   Format      :  $1 Primary reference clock PPM out 
                   of range 
                   Childtraps  : 
                   Description : Primary reference clock PPM out of 
                   range"
             ::= { alarmsAndEvents 0 526 }

      trapPriOORClear NOTIFICATION-TYPE
      OBJECTS {
                    objectNameTrapArg,
                    lctNameTrapArg,
                    trapCountTrapArg,
                    portNumberTrapArg
                }
      STATUS  current
      DESCRIPTION "Severity    : major 
                   Format      :  $1 Primary reference clock PPM out 
                   of range 
                   Childtraps  : 
                   Description : Primary reference clock PPM out of 
                   range"
             ::= { alarmsAndEvents 0 10526 }

      trapExcessCollisions NOTIFICATION-TYPE
      OBJECTS {
                    objectNameTrapArg,
                    lctNameTrapArg,
                    trapCountTrapArg,
                    portNumberTrapArg
                }
      STATUS  current
      DESCRIPTION "Severity    : zilch 
                   Format      :  $1  $2 : Excessive Collisions 
                   Childtraps  : 
                   Description : Excessive Collisions"
             ::= { alarmsAndEvents 0 306 }

      trapLateCollisions NOTIFICATION-TYPE
      OBJECTS {
                    objectNameTrapArg,
                    lctNameTrapArg,
                    trapCountTrapArg,
                    portNumberTrapArg
                }
      STATUS  current
      DESCRIPTION "Severity    : zilch 
                   Format      :  $1  $2 : Late Collisions 
                   Childtraps  : 
                   Description : Late Collisions on port"
             ::= { alarmsAndEvents 0 307 }

      trapLinkFailureEmulation NOTIFICATION-TYPE
      OBJECTS {
                    objectNameTrapArg,
                    lctNameTrapArg,
                    trapCountTrapArg,
                    portNumberTrapArg
                }
      STATUS  current
      DESCRIPTION "Severity    : major 
                   Format      :  $1  $2 : Link Integrity on~ $3 : 
                   Link Integrity off 
                   Childtraps  : 
                   Description : Link Integrity on"
             ::= { alarmsAndEvents 0 402 }

      trapLinkFailureEmulationClear NOTIFICATION-TYPE
      OBJECTS {
                    objectNameTrapArg,
                    lctNameTrapArg,
                    trapCountTrapArg,
                    portNumberTrapArg
                }
      STATUS  current
      DESCRIPTION "Severity    : major 
                   Format      :  $1  $2 : Link Integrity on~ $3 : 
                   Link Integrity off 
                   Childtraps  : 
                   Description : Link Integrity on"
             ::= { alarmsAndEvents 0 10402 }

      trapTcaCRCErrors NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      :  $1  $2 : TCA:Excessive CRC Errors 
                   Childtraps  : 
                   Description : TCA: Excessive CRC Errors"
             ::= { tcas 0 413 }

      trapANFail NOTIFICATION-TYPE
      OBJECTS {
                    objectNameTrapArg,
                    lctNameTrapArg,
                    trapCountTrapArg
                }
      STATUS  current
      DESCRIPTION "Severity    : critical 
                   Format      :  $1  $2 : Auto Negotiation Failed 
                   Childtraps  : 
                   Description : Auto Negotiation Failed"
             ::= { alarmsAndEvents 0 516 }

      trapANFailClear NOTIFICATION-TYPE
      OBJECTS {
                    objectNameTrapArg,
                    lctNameTrapArg,
                    trapCountTrapArg
                }
      STATUS  current
      DESCRIPTION "Severity    : critical 
                   Format      :  $1  $2 : Auto Negotiation Failed 
                   Childtraps  : 
                   Description : Auto Negotiation Failed"
             ::= { alarmsAndEvents 0 10516 }

      trapFDLI NOTIFICATION-TYPE
      OBJECTS {
                    objectNameTrapArg,
                    lctNameTrapArg,
                    trapCountTrapArg
                }
      STATUS  current
      DESCRIPTION "Severity    : major 
                   Format      :  $1  $2 : Forced Down - Link 
                   Integrity 
                   Childtraps  : 
                   Description : Forced Down - Link Integrity"
             ::= { alarmsAndEvents 0 517 }

      trapFDLIClear NOTIFICATION-TYPE
      OBJECTS {
                    objectNameTrapArg,
                    lctNameTrapArg,
                    trapCountTrapArg
                }
      STATUS  current
      DESCRIPTION "Severity    : major 
                   Format      :  $1  $2 : Forced Down - Link 
                   Integrity 
                   Childtraps  : 
                   Description : Forced Down - Link Integrity"
             ::= { alarmsAndEvents 0 10517 }

      trapEthEER NOTIFICATION-TYPE
      OBJECTS {
                    objectNameTrapArg,
                    lctNameTrapArg,
                    trapCountTrapArg,
                    portNumberTrapArg
                }
      STATUS  current
      DESCRIPTION "Severity    : major 
                   Format      :  $1  $2 : Excessive Error Ratio 
                   Childtraps  : 
                   Description : Excessive Error Ratio"
             ::= { alarmsAndEvents 0 518 }

      trapEthEERClear NOTIFICATION-TYPE
      OBJECTS {
                    objectNameTrapArg,
                    lctNameTrapArg,
                    trapCountTrapArg,
                    portNumberTrapArg
                }
      STATUS  current
      DESCRIPTION "Severity    : major 
                   Format      :  $1  $2 : Excessive Error Ratio 
                   Childtraps  : 
                   Description : Excessive Error Ratio"
             ::= { alarmsAndEvents 0 10518 }

      trapEthSD NOTIFICATION-TYPE
      OBJECTS {
                    objectNameTrapArg,
                    lctNameTrapArg,
                    trapCountTrapArg,
                    portNumberTrapArg
                }
      STATUS  current
      DESCRIPTION "Severity    : minor 
                   Format      :  $1  $2 : Signal Degrade 
                   Childtraps  : 
                   Description : Signal Degrade"
             ::= { alarmsAndEvents 0 519 }

      trapEthSDClear NOTIFICATION-TYPE
      OBJECTS {
                    objectNameTrapArg,
                    lctNameTrapArg,
                    trapCountTrapArg,
                    portNumberTrapArg
                }
      STATUS  current
      DESCRIPTION "Severity    : minor 
                   Format      :  $1  $2 : Signal Degrade 
                   Childtraps  : 
                   Description : Signal Degrade"
             ::= { alarmsAndEvents 0 10519 }

      trapEthLOS NOTIFICATION-TYPE
      OBJECTS {
                    objectNameTrapArg,
                    lctNameTrapArg,
                    trapCountTrapArg,
                    portNumberTrapArg
                }
      STATUS  current
      DESCRIPTION "Severity    : critical 
                   Format      :  $1 Loss of Signal on  $2 . 
                   Childtraps  : 
                   Description : Loss of Signal"
             ::= { alarmsAndEvents 0 611 }

      trapEthLOSClear NOTIFICATION-TYPE
      OBJECTS {
                    objectNameTrapArg,
                    lctNameTrapArg,
                    trapCountTrapArg,
                    portNumberTrapArg
                }
      STATUS  current
      DESCRIPTION "Severity    : critical 
                   Format      :  $1 Loss of Signal on  $2 . 
                   Childtraps  : 
                   Description : Loss of Signal"
             ::= { alarmsAndEvents 0 10611 }

      trapEfmRemoteFramesSymEvent NOTIFICATION-TYPE
      OBJECTS {
                    objectNameTrapArg,
                    lctNameTrapArg,
                    trapCountTrapArg,
                    portNumberTrapArg
                }
      STATUS  current
      DESCRIPTION "Severity    : zilch 
                   Format      :  $1  $2 : EFM Remote Frame Symbol 
                   Event 
                   Childtraps  : 
                   Description : EFM Remote Frame Symbol Event"
             ::= { alarmsAndEvents 0 621 }

      trapEfmRemoteFrameEvent NOTIFICATION-TYPE
      OBJECTS {
                    objectNameTrapArg,
                    lctNameTrapArg,
                    trapCountTrapArg,
                    portNumberTrapArg
                }
      STATUS  current
      DESCRIPTION "Severity    : zilch 
                   Format      :  $1  $2 : EFM Remote Frame Event 
                   Childtraps  : 
                   Description : EFM Remote Frame Event"
             ::= { alarmsAndEvents 0 622 }

      trapEfmRemoteFramePeriodEvent NOTIFICATION-TYPE
      OBJECTS {
                    objectNameTrapArg,
                    lctNameTrapArg,
                    trapCountTrapArg,
                    portNumberTrapArg
                }
      STATUS  current
      DESCRIPTION "Severity    : zilch 
                   Format      :  $1  $2 : EFM Remote Frame Period 
                   Event 
                   Childtraps  : 
                   Description : EFM Remote Frame Period Event"
             ::= { alarmsAndEvents 0 623 }

      trapEfmRemoteFrameSecondsSummaryEvent NOTIFICATION-TYPE
      OBJECTS {
                    objectNameTrapArg,
                    lctNameTrapArg,
                    trapCountTrapArg,
                    portNumberTrapArg
                }
      STATUS  current
      DESCRIPTION "Severity    : zilch 
                   Format      :  $1  $2 : EFM Remote Frame Seconds 
                   Summary Event 
                   Childtraps  : 
                   Description : EFM Remote Frame Seconds Summary 
                   Event"
             ::= { alarmsAndEvents 0 624 }

      trapTcaEthES NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      :  $1  $2 : TCA:Errored Seconds - 
                   ETHPort 
                   Childtraps  : 
                   Description : TCA: Errored Seconds - ETHPort"
             ::= { tcas 0 733 }

      trapTcaEthSES NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      :  $1  $2 : TCA:Severely Errored 
                   Seconds - ETHPort 
                   Childtraps  : 
                   Description : TCA: Severely Errored Seconds - 
                   ETHPort"
             ::= { tcas 0 734 }

      trapTcaEthUAS NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      :  $1  $2 : TCA:Unavailable Seconds - 
                   ETHPort 
                   Childtraps  : 
                   Description : TCA: Unavailable Seconds - ETHPort"
             ::= { tcas 0 735 }

      trapStpTopologyChange NOTIFICATION-TYPE
      OBJECTS {
                    objectNameTrapArg,
                    lctNameTrapArg,
                    trapCountTrapArg
                }
      STATUS  current
      DESCRIPTION "Severity    : zilch 
                   Format      :  $1 Bridge detected a toplogy 
                   change in CIST or in any MSTI 
                   Childtraps  : 
                   Description : Bridge detected a toplogy change"
             ::= { alarmsAndEvents 0 687 }

      trapVTLom NOTIFICATION-TYPE
      OBJECTS {
                    objectNameTrapArg,
                    lctNameTrapArg,
                    trapCountTrapArg
                }
      STATUS  current
      DESCRIPTION "Severity    : major 
                   Format      :  $1 LOM on  $2 . 
                   Childtraps  : 
                   Description : Loss of Multiframe"
             ::= { alarmsAndEvents 0 104 }

      trapVTLomClear NOTIFICATION-TYPE
      OBJECTS {
                    objectNameTrapArg,
                    lctNameTrapArg,
                    trapCountTrapArg
                }
      STATUS  current
      DESCRIPTION "Severity    : major 
                   Format      :  $1 LOM on  $2 . 
                   Childtraps  : 
                   Description : Loss of Multiframe"
             ::= { alarmsAndEvents 0 10104 }

      trapAUAis NOTIFICATION-TYPE
      OBJECTS {
                    objectNameTrapArg,
                    lctNameTrapArg,
                    trapCountTrapArg
                }
      STATUS  current
      DESCRIPTION "Severity    : major 
                   Format      : 
                   Childtraps  : 
                   Description : Alarm Indication Signal"
             ::= { alarmsAndEvents 0 352 }

      trapAUAisClear NOTIFICATION-TYPE
      OBJECTS {
                    objectNameTrapArg,
                    lctNameTrapArg,
                    trapCountTrapArg
                }
      STATUS  current
      DESCRIPTION "Severity    : major 
                   Format      : 
                   Childtraps  : 
                   Description : Alarm Indication Signal"
             ::= { alarmsAndEvents 0 10352 }

      trapAURdi NOTIFICATION-TYPE
      OBJECTS {
                    objectNameTrapArg,
                    lctNameTrapArg,
                    trapCountTrapArg
                }
      STATUS  current
      DESCRIPTION "Severity    : major 
                   Format      : 
                   Childtraps  : 
                   Description : Remote Defect Indication"
             ::= { alarmsAndEvents 0 353 }

      trapAURdiClear NOTIFICATION-TYPE
      OBJECTS {
                    objectNameTrapArg,
                    lctNameTrapArg,
                    trapCountTrapArg
                }
      STATUS  current
      DESCRIPTION "Severity    : major 
                   Format      : 
                   Childtraps  : 
                   Description : Remote Defect Indication"
             ::= { alarmsAndEvents 0 10353 }

      trapAULop NOTIFICATION-TYPE
      OBJECTS {
                    objectNameTrapArg,
                    lctNameTrapArg,
                    trapCountTrapArg
                }
      STATUS  current
      DESCRIPTION "Severity    : major 
                   Format      : 
                   Childtraps  : 
                   Description : Loss of Pointer"
             ::= { alarmsAndEvents 0 354 }

      trapAULopClear NOTIFICATION-TYPE
      OBJECTS {
                    objectNameTrapArg,
                    lctNameTrapArg,
                    trapCountTrapArg
                }
      STATUS  current
      DESCRIPTION "Severity    : major 
                   Format      : 
                   Childtraps  : 
                   Description : Loss of Pointer"
             ::= { alarmsAndEvents 0 10354 }

      trapAUUneq NOTIFICATION-TYPE
      OBJECTS {
                    objectNameTrapArg,
                    lctNameTrapArg,
                    trapCountTrapArg
                }
      STATUS  current
      DESCRIPTION "Severity    : major 
                   Format      : 
                   Childtraps  : 
                   Description : Signal Label Unequipped"
             ::= { alarmsAndEvents 0 355 }

      trapAUUneqClear NOTIFICATION-TYPE
      OBJECTS {
                    objectNameTrapArg,
                    lctNameTrapArg,
                    trapCountTrapArg
                }
      STATUS  current
      DESCRIPTION "Severity    : major 
                   Format      : 
                   Childtraps  : 
                   Description : Signal Label Unequipped"
             ::= { alarmsAndEvents 0 10355 }

      trapAUTIM NOTIFICATION-TYPE
      OBJECTS {
                    objectNameTrapArg,
                    lctNameTrapArg,
                    trapCountTrapArg
                }
      STATUS  current
      DESCRIPTION "Severity    : major 
                   Format      : 
                   Childtraps  : 
                   Description : Trace Identifier Mismatch"
             ::= { alarmsAndEvents 0 356 }

      trapAUTIMClear NOTIFICATION-TYPE
      OBJECTS {
                    objectNameTrapArg,
                    lctNameTrapArg,
                    trapCountTrapArg
                }
      STATUS  current
      DESCRIPTION "Severity    : major 
                   Format      : 
                   Childtraps  : 
                   Description : Trace Identifier Mismatch"
             ::= { alarmsAndEvents 0 10356 }

      trapAUPLM NOTIFICATION-TYPE
      OBJECTS {
                    objectNameTrapArg,
                    lctNameTrapArg,
                    trapCountTrapArg
                }
      STATUS  current
      DESCRIPTION "Severity    : major 
                   Format      : 
                   Childtraps  : 
                   Description : Path Label Mismatch"
             ::= { alarmsAndEvents 0 357 }

      trapAUPLMClear NOTIFICATION-TYPE
      OBJECTS {
                    objectNameTrapArg,
                    lctNameTrapArg,
                    trapCountTrapArg
                }
      STATUS  current
      DESCRIPTION "Severity    : major 
                   Format      : 
                   Childtraps  : 
                   Description : Path Label Mismatch"
             ::= { alarmsAndEvents 0 10357 }

      trapAUSD NOTIFICATION-TYPE
      OBJECTS {
                    objectNameTrapArg,
                    lctNameTrapArg,
                    trapCountTrapArg
                }
      STATUS  current
      DESCRIPTION "Severity    : major 
                   Format      : 
                   Childtraps  : 
                   Description : Signal Degrade"
             ::= { alarmsAndEvents 0 358 }

      trapAUSDClear NOTIFICATION-TYPE
      OBJECTS {
                    objectNameTrapArg,
                    lctNameTrapArg,
                    trapCountTrapArg
                }
      STATUS  current
      DESCRIPTION "Severity    : major 
                   Format      : 
                   Childtraps  : 
                   Description : Signal Degrade"
             ::= { alarmsAndEvents 0 10358 }

      trapAUSF NOTIFICATION-TYPE
      OBJECTS {
                    objectNameTrapArg,
                    lctNameTrapArg,
                    trapCountTrapArg
                }
      STATUS  current
      DESCRIPTION "Severity    : major 
                   Format      : 
                   Childtraps  : 
                   Description : Excessive Error"
             ::= { alarmsAndEvents 0 390 }

      trapAUSFClear NOTIFICATION-TYPE
      OBJECTS {
                    objectNameTrapArg,
                    lctNameTrapArg,
                    trapCountTrapArg
                }
      STATUS  current
      DESCRIPTION "Severity    : major 
                   Format      : 
                   Childtraps  : 
                   Description : Excessive Error"
             ::= { alarmsAndEvents 0 10390 }

      trapTCUNEQ NOTIFICATION-TYPE
      OBJECTS {
                    objectNameTrapArg,
                    lctNameTrapArg,
                    trapCountTrapArg
                }
      STATUS  current
      DESCRIPTION "Severity    : major 
                   Format      :  $1 TC-UNEQ on  $2 . 
                   Childtraps  : 
                   Description : Tandem Connection - Signal Label 
                   Unequipped"
             ::= { alarmsAndEvents 0 414 }

      trapTCUNEQClear NOTIFICATION-TYPE
      OBJECTS {
                    objectNameTrapArg,
                    lctNameTrapArg,
                    trapCountTrapArg
                }
      STATUS  current
      DESCRIPTION "Severity    : major 
                   Format      :  $1 TC-UNEQ on  $2 . 
                   Childtraps  : 
                   Description : Tandem Connection - Signal Label 
                   Unequipped"
             ::= { alarmsAndEvents 0 10414 }

      trapTCIncAIS NOTIFICATION-TYPE
      OBJECTS {
                    objectNameTrapArg,
                    lctNameTrapArg,
                    trapCountTrapArg
                }
      STATUS  current
      DESCRIPTION "Severity    : major 
                   Format      :  $1 TC-IncAIS on  $2 . 
                   Childtraps  : 
                   Description : Tandem Connection - Incoming Alarm 
                   Indication Signal"
             ::= { alarmsAndEvents 0 415 }

      trapTCIncAISClear NOTIFICATION-TYPE
      OBJECTS {
                    objectNameTrapArg,
                    lctNameTrapArg,
                    trapCountTrapArg
                }
      STATUS  current
      DESCRIPTION "Severity    : major 
                   Format      :  $1 TC-IncAIS on  $2 . 
                   Childtraps  : 
                   Description : Tandem Connection - Incoming Alarm 
                   Indication Signal"
             ::= { alarmsAndEvents 0 10415 }

      trapTCDEG NOTIFICATION-TYPE
      OBJECTS {
                    objectNameTrapArg,
                    lctNameTrapArg,
                    trapCountTrapArg
                }
      STATUS  current
      DESCRIPTION "Severity    : major 
                   Format      :  $1 TC-DEG on  $2 . 
                   Childtraps  : 
                   Description : Tandem Connection - Signal Degrade"
             ::= { alarmsAndEvents 0 416 }

      trapTCDEGClear NOTIFICATION-TYPE
      OBJECTS {
                    objectNameTrapArg,
                    lctNameTrapArg,
                    trapCountTrapArg
                }
      STATUS  current
      DESCRIPTION "Severity    : major 
                   Format      :  $1 TC-DEG on  $2 . 
                   Childtraps  : 
                   Description : Tandem Connection - Signal Degrade"
             ::= { alarmsAndEvents 0 10416 }

      trapTCAIS NOTIFICATION-TYPE
      OBJECTS {
                    objectNameTrapArg,
                    lctNameTrapArg,
                    trapCountTrapArg
                }
      STATUS  current
      DESCRIPTION "Severity    : major 
                   Format      :  $1 TC-AIS on  $2 . 
                   Childtraps  : 
                   Description : Tandem Connection - Alarm 
                   Indication Signal"
             ::= { alarmsAndEvents 0 417 }

      trapTCAISClear NOTIFICATION-TYPE
      OBJECTS {
                    objectNameTrapArg,
                    lctNameTrapArg,
                    trapCountTrapArg
                }
      STATUS  current
      DESCRIPTION "Severity    : major 
                   Format      :  $1 TC-AIS on  $2 . 
                   Childtraps  : 
                   Description : Tandem Connection - Alarm 
                   Indication Signal"
             ::= { alarmsAndEvents 0 10417 }

      trapTCLOP NOTIFICATION-TYPE
      OBJECTS {
                    objectNameTrapArg,
                    lctNameTrapArg,
                    trapCountTrapArg
                }
      STATUS  current
      DESCRIPTION "Severity    : major 
                   Format      :  $1 TC-LOP on  $2 . 
                   Childtraps  : 
                   Description : Tandem Connection - Loss of Pointer"
             ::= { alarmsAndEvents 0 418 }

      trapTCLOPClear NOTIFICATION-TYPE
      OBJECTS {
                    objectNameTrapArg,
                    lctNameTrapArg,
                    trapCountTrapArg
                }
      STATUS  current
      DESCRIPTION "Severity    : major 
                   Format      :  $1 TC-LOP on  $2 . 
                   Childtraps  : 
                   Description : Tandem Connection - Loss of Pointer"
             ::= { alarmsAndEvents 0 10418 }

      trapTCLTC NOTIFICATION-TYPE
      OBJECTS {
                    objectNameTrapArg,
                    lctNameTrapArg,
                    trapCountTrapArg
                }
      STATUS  current
      DESCRIPTION "Severity    : major 
                   Format      :  $1 TC-LTC on  $2 . 
                   Childtraps  : 
                   Description : Loss of Tandem Connection"
             ::= { alarmsAndEvents 0 419 }

      trapTCLTCClear NOTIFICATION-TYPE
      OBJECTS {
                    objectNameTrapArg,
                    lctNameTrapArg,
                    trapCountTrapArg
                }
      STATUS  current
      DESCRIPTION "Severity    : major 
                   Format      :  $1 TC-LTC on  $2 . 
                   Childtraps  : 
                   Description : Loss of Tandem Connection"
             ::= { alarmsAndEvents 0 10419 }

      trapTCTIM NOTIFICATION-TYPE
      OBJECTS {
                    objectNameTrapArg,
                    lctNameTrapArg,
                    trapCountTrapArg
                }
      STATUS  current
      DESCRIPTION "Severity    : major 
                   Format      :  $1 TC-TIM on  $2 . 
                   Childtraps  : 
                   Description : Tandem Connection - Trace 
                   Identifier Mismatch"
             ::= { alarmsAndEvents 0 420 }

      trapTCTIMClear NOTIFICATION-TYPE
      OBJECTS {
                    objectNameTrapArg,
                    lctNameTrapArg,
                    trapCountTrapArg
                }
      STATUS  current
      DESCRIPTION "Severity    : major 
                   Format      :  $1 TC-TIM on  $2 . 
                   Childtraps  : 
                   Description : Tandem Connection - Trace 
                   Identifier Mismatch"
             ::= { alarmsAndEvents 0 10420 }

      trapTCODI NOTIFICATION-TYPE
      OBJECTS {
                    objectNameTrapArg,
                    lctNameTrapArg,
                    trapCountTrapArg
                }
      STATUS  current
      DESCRIPTION "Severity    : major 
                   Format      :  $1 TC-ODI on  $2 . 
                   Childtraps  : 
                   Description : Tandem Connection - Defect 
                   Indication"
             ::= { alarmsAndEvents 0 421 }

      trapTCODIClear NOTIFICATION-TYPE
      OBJECTS {
                    objectNameTrapArg,
                    lctNameTrapArg,
                    trapCountTrapArg
                }
      STATUS  current
      DESCRIPTION "Severity    : major 
                   Format      :  $1 TC-ODI on  $2 . 
                   Childtraps  : 
                   Description : Tandem Connection - Defect 
                   Indication"
             ::= { alarmsAndEvents 0 10421 }

      trapTCRDI NOTIFICATION-TYPE
      OBJECTS {
                    objectNameTrapArg,
                    lctNameTrapArg,
                    trapCountTrapArg
                }
      STATUS  current
      DESCRIPTION "Severity    : major 
                   Format      :  $1 TC-RDI on  $2 . 
                   Childtraps  : 
                   Description : Tandem Connection - Remote Defect 
                   Indication"
             ::= { alarmsAndEvents 0 422 }

      trapTCRDIClear NOTIFICATION-TYPE
      OBJECTS {
                    objectNameTrapArg,
                    lctNameTrapArg,
                    trapCountTrapArg
                }
      STATUS  current
      DESCRIPTION "Severity    : major 
                   Format      :  $1 TC-RDI on  $2 . 
                   Childtraps  : 
                   Description : Tandem Connection - Remote Defect 
                   Indication"
             ::= { alarmsAndEvents 0 10422 }

      trapCCAUAutomaticSwitchToChannel NOTIFICATION-TYPE
      OBJECTS {
                    objectNameTrapArg,
                    lctNameTrapArg,
                    trapCountTrapArg
                }
      STATUS  current
      DESCRIPTION "Severity    : zilch 
                   Format      :  $1 Non Revertive switch from 
                   channel  $2 . 
                   Childtraps  : 
                   Description : Protection Switch Complete"
             ::= { alarmsAndEvents 0 451 }

      trapCCAULockOut NOTIFICATION-TYPE
      OBJECTS {
                    objectNameTrapArg,
                    lctNameTrapArg,
                    trapCountTrapArg
                }
      STATUS  current
      DESCRIPTION "Severity    : minor 
                   Format      :  $1 Lockout of protection, Switch 
                   from the protect channel  $2  . 
                   Childtraps  : 
                   Description : Lockout Active"
             ::= { alarmsAndEvents 0 452 }

      trapCCAULockOutClear NOTIFICATION-TYPE
      OBJECTS {
                    objectNameTrapArg,
                    lctNameTrapArg,
                    trapCountTrapArg
                }
      STATUS  current
      DESCRIPTION "Severity    : minor 
                   Format      :  $1 Lockout of protection, Switch 
                   from the protect channel  $2  . 
                   Childtraps  : 
                   Description : Lockout Active"
             ::= { alarmsAndEvents 0 10452 }

      trapCCAUForcedSwitchToChannel NOTIFICATION-TYPE
      OBJECTS {
                    objectNameTrapArg,
                    lctNameTrapArg,
                    trapCountTrapArg
                }
      STATUS  current
      DESCRIPTION "Severity    : minor 
                   Format      :  $1 Forced switch from channel  $2 
                   . 
                   Childtraps  : 
                   Description : Forced Switch Active"
             ::= { alarmsAndEvents 0 453 }

      trapCCAUForcedSwitchToChannelClear NOTIFICATION-TYPE
      OBJECTS {
                    objectNameTrapArg,
                    lctNameTrapArg,
                    trapCountTrapArg
                }
      STATUS  current
      DESCRIPTION "Severity    : minor 
                   Format      :  $1 Forced switch from channel  $2 
                   . 
                   Childtraps  : 
                   Description : Forced Switch Active"
             ::= { alarmsAndEvents 0 10453 }

      trapCCAUManualSwitchToChannel NOTIFICATION-TYPE
      OBJECTS {
                    objectNameTrapArg,
                    lctNameTrapArg,
                    trapCountTrapArg
                }
      STATUS  current
      DESCRIPTION "Severity    : minor 
                   Format      :  $1 Manual switch from channel  $2 
                   . 
                   Childtraps  : 
                   Description : Manual Switch Active"
             ::= { alarmsAndEvents 0 454 }

      trapCCAUManualSwitchToChannelClear NOTIFICATION-TYPE
      OBJECTS {
                    objectNameTrapArg,
                    lctNameTrapArg,
                    trapCountTrapArg
                }
      STATUS  current
      DESCRIPTION "Severity    : minor 
                   Format      :  $1 Manual switch from channel  $2 
                   . 
                   Childtraps  : 
                   Description : Manual Switch Active"
             ::= { alarmsAndEvents 0 10454 }

      trapCCAURevertToWork NOTIFICATION-TYPE
      OBJECTS {
                    objectNameTrapArg,
                    lctNameTrapArg,
                    trapCountTrapArg
                }
      STATUS  current
      DESCRIPTION "Severity    : warning 
                   Format      :  $1 Revertive switch from channel 
                   Childtraps  : 
                   Description : Protection Switch Active"
             ::= { alarmsAndEvents 0 455 }

      trapCCAURevertToWorkClear NOTIFICATION-TYPE
      OBJECTS {
                    objectNameTrapArg,
                    lctNameTrapArg,
                    trapCountTrapArg
                }
      STATUS  current
      DESCRIPTION "Severity    : warning 
                   Format      :  $1 Revertive switch from channel 
                   Childtraps  : 
                   Description : Protection Switch Active"
             ::= { alarmsAndEvents 0 10455 }

      trapCCAUManualSwitchFailed NOTIFICATION-TYPE
      OBJECTS {
                    objectNameTrapArg,
                    lctNameTrapArg,
                    trapCountTrapArg
                }
      STATUS  current
      DESCRIPTION "Severity    : zilch 
                   Format      :  $1 Manual switch for channel  $2  
                   failed. 
                   Childtraps  : 
                   Description : Manual Switch Fail"
             ::= { alarmsAndEvents 0 456 }

      trapHPExError NOTIFICATION-TYPE
      OBJECTS {
                    objectNameTrapArg,
                    lctNameTrapArg,
                    trapCountTrapArg
                }
      STATUS  current
      DESCRIPTION "Severity    : major 
                   Format      : 
                   Childtraps  : 
                   Description : Excessive Error"
             ::= { alarmsAndEvents 0 472 }

      trapHPExErrorClear NOTIFICATION-TYPE
      OBJECTS {
                    objectNameTrapArg,
                    lctNameTrapArg,
                    trapCountTrapArg
                }
      STATUS  current
      DESCRIPTION "Severity    : major 
                   Format      : 
                   Childtraps  : 
                   Description : Excessive Error"
             ::= { alarmsAndEvents 0 10472 }

      trapTCOEI NOTIFICATION-TYPE
      OBJECTS {
                    objectNameTrapArg,
                    lctNameTrapArg,
                    trapCountTrapArg
                }
      STATUS  current
      DESCRIPTION "Severity    : major 
                   Format      :  $1 TC-OEI on  $2 . 
                   Childtraps  : 
                   Description : Tandem Connection - Outgoing Error 
                   Indication"
             ::= { alarmsAndEvents 0 475 }

      trapTCOEIClear NOTIFICATION-TYPE
      OBJECTS {
                    objectNameTrapArg,
                    lctNameTrapArg,
                    trapCountTrapArg
                }
      STATUS  current
      DESCRIPTION "Severity    : major 
                   Format      :  $1 TC-OEI on  $2 . 
                   Childtraps  : 
                   Description : Tandem Connection - Outgoing Error 
                   Indication"
             ::= { alarmsAndEvents 0 10475 }

      trapTCREI NOTIFICATION-TYPE
      OBJECTS {
                    objectNameTrapArg,
                    lctNameTrapArg,
                    trapCountTrapArg
                }
      STATUS  current
      DESCRIPTION "Severity    : major 
                   Format      :  $1 TC-REI on  $2 . 
                   Childtraps  : 
                   Description : Tandem Connection - Remote Error 
                   Indication"
             ::= { alarmsAndEvents 0 476 }

      trapTCREIClear NOTIFICATION-TYPE
      OBJECTS {
                    objectNameTrapArg,
                    lctNameTrapArg,
                    trapCountTrapArg
                }
      STATUS  current
      DESCRIPTION "Severity    : major 
                   Format      :  $1 TC-REI on  $2 . 
                   Childtraps  : 
                   Description : Tandem Connection - Remote Error 
                   Indication"
             ::= { alarmsAndEvents 0 10476 }

      trapAURSD NOTIFICATION-TYPE
      OBJECTS {
                    objectNameTrapArg,
                    lctNameTrapArg,
                    trapCountTrapArg
                }
      STATUS  current
      DESCRIPTION "Severity    : major 
                   Format      : 
                   Childtraps  : 
                   Description : Far End Signal Degrade"
             ::= { alarmsAndEvents 0 483 }

      trapAURSDClear NOTIFICATION-TYPE
      OBJECTS {
                    objectNameTrapArg,
                    lctNameTrapArg,
                    trapCountTrapArg
                }
      STATUS  current
      DESCRIPTION "Severity    : major 
                   Format      : 
                   Childtraps  : 
                   Description : Far End Signal Degrade"
             ::= { alarmsAndEvents 0 10483 }

      trapAURSF NOTIFICATION-TYPE
      OBJECTS {
                    objectNameTrapArg,
                    lctNameTrapArg,
                    trapCountTrapArg
                }
      STATUS  current
      DESCRIPTION "Severity    : major 
                   Format      : 
                   Childtraps  : 
                   Description : Far End Excessive Error"
             ::= { alarmsAndEvents 0 484 }

      trapAURSFClear NOTIFICATION-TYPE
      OBJECTS {
                    objectNameTrapArg,
                    lctNameTrapArg,
                    trapCountTrapArg
                }
      STATUS  current
      DESCRIPTION "Severity    : major 
                   Format      : 
                   Childtraps  : 
                   Description : Far End Excessive Error"
             ::= { alarmsAndEvents 0 10484 }

      trapAuVCATLoM NOTIFICATION-TYPE
      OBJECTS {
                    objectNameTrapArg,
                    lctNameTrapArg,
                    trapCountTrapArg
                }
      STATUS  current
      DESCRIPTION "Severity    : critical 
                   Format      :  $1 Loss of VCAT Multiframe: 
                   Childtraps  : 
                   Description : Loss of VCAT Multiframe"
             ::= { alarmsAndEvents 0 508 }

      trapAuVCATLoMClear NOTIFICATION-TYPE
      OBJECTS {
                    objectNameTrapArg,
                    lctNameTrapArg,
                    trapCountTrapArg
                }
      STATUS  current
      DESCRIPTION "Severity    : critical 
                   Format      :  $1 Loss of VCAT Multiframe: 
                   Childtraps  : 
                   Description : Loss of VCAT Multiframe"
             ::= { alarmsAndEvents 0 10508 }

      trapAuSQM NOTIFICATION-TYPE
      OBJECTS {
                    objectNameTrapArg,
                    lctNameTrapArg,
                    trapCountTrapArg
                }
      STATUS  current
      DESCRIPTION "Severity    : critical 
                   Format      :  $1 Sqeuence Number Mismatch: 
                   Childtraps  : 
                   Description : Sequence Number Mismatch"
             ::= { alarmsAndEvents 0 509 }

      trapAuSQMClear NOTIFICATION-TYPE
      OBJECTS {
                    objectNameTrapArg,
                    lctNameTrapArg,
                    trapCountTrapArg
                }
      STATUS  current
      DESCRIPTION "Severity    : critical 
                   Format      :  $1 Sqeuence Number Mismatch: 
                   Childtraps  : 
                   Description : Sequence Number Mismatch"
             ::= { alarmsAndEvents 0 10509 }

      trapAuTxLTC NOTIFICATION-TYPE
      OBJECTS {
                    objectNameTrapArg,
                    lctNameTrapArg,
                    trapCountTrapArg
                }
      STATUS  current
      DESCRIPTION "Severity    : major 
                   Format      :  $1 Tx Loss of Capacity - LCAS: 
                   Childtraps  : 
                   Description : Tx Loss of Capacity - LCAS"
             ::= { alarmsAndEvents 0 510 }

      trapAuTxLTCClear NOTIFICATION-TYPE
      OBJECTS {
                    objectNameTrapArg,
                    lctNameTrapArg,
                    trapCountTrapArg
                }
      STATUS  current
      DESCRIPTION "Severity    : major 
                   Format      :  $1 Tx Loss of Capacity - LCAS: 
                   Childtraps  : 
                   Description : Tx Loss of Capacity - LCAS"
             ::= { alarmsAndEvents 0 10510 }

      trapAuRxLTC NOTIFICATION-TYPE
      OBJECTS {
                    objectNameTrapArg,
                    lctNameTrapArg,
                    trapCountTrapArg
                }
      STATUS  current
      DESCRIPTION "Severity    : major 
                   Format      :  $1 Rx Loss of Capacity - LCAS: 
                   Childtraps  : 
                   Description : Rx Loss of Capacity - LCAS"
             ::= { alarmsAndEvents 0 511 }

      trapAuRxLTCClear NOTIFICATION-TYPE
      OBJECTS {
                    objectNameTrapArg,
                    lctNameTrapArg,
                    trapCountTrapArg
                }
      STATUS  current
      DESCRIPTION "Severity    : major 
                   Format      :  $1 Rx Loss of Capacity - LCAS: 
                   Childtraps  : 
                   Description : Rx Loss of Capacity - LCAS"
             ::= { alarmsAndEvents 0 10511 }

      trapAuMND NOTIFICATION-TYPE
      OBJECTS {
                    objectNameTrapArg,
                    lctNameTrapArg,
                    trapCountTrapArg
                }
      STATUS  current
      DESCRIPTION "Severity    : major 
                   Format      :  $1 Member Not Deskewable-LCAS: 
                   Childtraps  : 
                   Description : Member Not Deskewable-LCAS"
             ::= { alarmsAndEvents 0 512 }

      trapAuMNDClear NOTIFICATION-TYPE
      OBJECTS {
                    objectNameTrapArg,
                    lctNameTrapArg,
                    trapCountTrapArg
                }
      STATUS  current
      DESCRIPTION "Severity    : major 
                   Format      :  $1 Member Not Deskewable-LCAS: 
                   Childtraps  : 
                   Description : Member Not Deskewable-LCAS"
             ::= { alarmsAndEvents 0 10512 }

      trapAuPCRC NOTIFICATION-TYPE
      OBJECTS {
                    objectNameTrapArg,
                    lctNameTrapArg,
                    trapCountTrapArg
                }
      STATUS  current
      DESCRIPTION "Severity    : minor 
                   Format      :  $1 Persistent CRC errors - LCAS: 
                   Childtraps  : 
                   Description : Persistent CRC errors - LCAS"
             ::= { alarmsAndEvents 0 513 }

      trapAuPCRCClear NOTIFICATION-TYPE
      OBJECTS {
                    objectNameTrapArg,
                    lctNameTrapArg,
                    trapCountTrapArg
                }
      STATUS  current
      DESCRIPTION "Severity    : minor 
                   Format      :  $1 Persistent CRC errors - LCAS: 
                   Childtraps  : 
                   Description : Persistent CRC errors - LCAS"
             ::= { alarmsAndEvents 0 10513 }

      trapAuPUMST NOTIFICATION-TYPE
      OBJECTS {
                    objectNameTrapArg,
                    lctNameTrapArg,
                    trapCountTrapArg
                }
      STATUS  current
      DESCRIPTION "Severity    : minor 
                   Childtraps  : 
                   Description : Persistent Unexpected MST-LCAS"
             ::= { alarmsAndEvents 0 514 }

      trapAuPUMSTClear NOTIFICATION-TYPE
      OBJECTS {
                    objectNameTrapArg,
                    lctNameTrapArg,
                    trapCountTrapArg
                }
      STATUS  current
      DESCRIPTION "Severity    : minor 
                   Childtraps  : 
                   Description : Persistent Unexpected MST-LCAS"
             ::= { alarmsAndEvents 0 10514 }

      trapAuDDE NOTIFICATION-TYPE
      OBJECTS {
                    objectNameTrapArg,
                    lctNameTrapArg,
                    trapCountTrapArg
                }
      STATUS  current
      DESCRIPTION "Severity    : critical 
                   Format      :  $1 Differential Delay Exceeded: 
                   Childtraps  : 
                   Description : Differential Delay Exceeded"
             ::= { alarmsAndEvents 0 515 }

      trapAuDDEClear NOTIFICATION-TYPE
      OBJECTS {
                    objectNameTrapArg,
                    lctNameTrapArg,
                    trapCountTrapArg
                }
      STATUS  current
      DESCRIPTION "Severity    : critical 
                   Format      :  $1 Differential Delay Exceeded: 
                   Childtraps  : 
                   Description : Differential Delay Exceeded"
             ::= { alarmsAndEvents 0 10515 }

      trapAUSSF NOTIFICATION-TYPE
      OBJECTS {
                    objectNameTrapArg,
                    lctNameTrapArg,
                    trapCountTrapArg
                }
      STATUS  current
      DESCRIPTION "Severity    : major 
                   Format      : 
                   Childtraps  : 
                   Description : Server Signal Failure"
             ::= { alarmsAndEvents 0 704 }

      trapAUSSFClear NOTIFICATION-TYPE
      OBJECTS {
                    objectNameTrapArg,
                    lctNameTrapArg,
                    trapCountTrapArg
                }
      STATUS  current
      DESCRIPTION "Severity    : major 
                   Format      : 
                   Childtraps  : 
                   Description : Server Signal Failure"
             ::= { alarmsAndEvents 0 10704 }

      trapLOA NOTIFICATION-TYPE
      OBJECTS {
                    objectNameTrapArg,
                    lctNameTrapArg,
                    trapCountTrapArg,
                    portNumberTrapArg
                }
      STATUS  current
      DESCRIPTION "Severity    : major 
                   Format      :  $1  $2 : Loss of Alignment 
                   Childtraps  : 
                   Description : Loss of Alignment"
             ::= { alarmsAndEvents 0 343 }

      trapLOAClear NOTIFICATION-TYPE
      OBJECTS {
                    objectNameTrapArg,
                    lctNameTrapArg,
                    trapCountTrapArg,
                    portNumberTrapArg
                }
      STATUS  current
      DESCRIPTION "Severity    : major 
                   Format      :  $1  $2 : Loss of Alignment 
                   Childtraps  : 
                   Description : Loss of Alignment"
             ::= { alarmsAndEvents 0 10343 }

      trapMDLERROR NOTIFICATION-TYPE
      OBJECTS {
                    objectNameTrapArg,
                    lctNameTrapArg,
                    trapCountTrapArg
                }
      STATUS  current
      DESCRIPTION "Severity    : zilch 
                   Format      :  $1  $2 : MDL-ERROR 
                   Childtraps  : 
                   Description : MDL-ERROR"
             ::= { alarmsAndEvents 0 348 }

      trapDiffDelay NOTIFICATION-TYPE
      OBJECTS {
                    objectNameTrapArg,
                    lctNameTrapArg,
                    trapCountTrapArg,
                    portNumberTrapArg
                }
      STATUS  current
      DESCRIPTION "Severity    : major 
                   Format      :  $1  $2 : Differential Delay 
                   Exceeded 
                   Childtraps  : 
                   Description : Differential Delay Exceeded"
             ::= { alarmsAndEvents 0 404 }

      trapDiffDelayClear NOTIFICATION-TYPE
      OBJECTS {
                    objectNameTrapArg,
                    lctNameTrapArg,
                    trapCountTrapArg,
                    portNumberTrapArg
                }
      STATUS  current
      DESCRIPTION "Severity    : major 
                   Format      :  $1  $2 : Differential Delay 
                   Exceeded 
                   Childtraps  : 
                   Description : Differential Delay Exceeded"
             ::= { alarmsAndEvents 0 10404 }

      trapLCASModeMismatch NOTIFICATION-TYPE
      OBJECTS {
                    objectNameTrapArg,
                    lctNameTrapArg,
                    trapCountTrapArg,
                    portNumberTrapArg
                }
      STATUS  current
      DESCRIPTION "Severity    : minor 
                   Format      :  $1  $2 : LCAS Mode Mismatch 
                   Childtraps  : 
                   Description : LCAS Mode Mismatch"
             ::= { alarmsAndEvents 0 405 }

      trapLCASModeMismatchClear NOTIFICATION-TYPE
      OBJECTS {
                    objectNameTrapArg,
                    lctNameTrapArg,
                    trapCountTrapArg,
                    portNumberTrapArg
                }
      STATUS  current
      DESCRIPTION "Severity    : minor 
                   Format      :  $1  $2 : LCAS Mode Mismatch 
                   Childtraps  : 
                   Description : LCAS Mode Mismatch"
             ::= { alarmsAndEvents 0 10405 }

      trapTxLTC NOTIFICATION-TYPE
      OBJECTS {
                    objectNameTrapArg,
                    lctNameTrapArg,
                    trapCountTrapArg,
                    portNumberTrapArg
                }
      STATUS  current
      DESCRIPTION "Severity    : major 
                   Format      :  $1  $2 : Tx Total Loss of Capacity 
                   - LCAS 
                   Childtraps  : 
                   Description : Tx Total Loss of Capacity - LCAS"
             ::= { alarmsAndEvents 0 406 }

      trapTxLTCClear NOTIFICATION-TYPE
      OBJECTS {
                    objectNameTrapArg,
                    lctNameTrapArg,
                    trapCountTrapArg,
                    portNumberTrapArg
                }
      STATUS  current
      DESCRIPTION "Severity    : major 
                   Format      :  $1  $2 : Tx Total Loss of Capacity 
                   - LCAS 
                   Childtraps  : 
                   Description : Tx Total Loss of Capacity - LCAS"
             ::= { alarmsAndEvents 0 10406 }

      trapPLTC NOTIFICATION-TYPE
      OBJECTS {
                    objectNameTrapArg,
                    lctNameTrapArg,
                    trapCountTrapArg,
                    portNumberTrapArg
                }
      STATUS  current
      DESCRIPTION "Severity    : minor 
                   Format      :  $1  $2 : Rx Partial Loss of 
                   Capacity - LCAS 
                   Childtraps  : 
                   Description : Rx Partial Loss of Capacity - LCAS"
             ::= { alarmsAndEvents 0 407 }

      trapPLTCClear NOTIFICATION-TYPE
      OBJECTS {
                    objectNameTrapArg,
                    lctNameTrapArg,
                    trapCountTrapArg,
                    portNumberTrapArg
                }
      STATUS  current
      DESCRIPTION "Severity    : minor 
                   Format      :  $1  $2 : Rx Partial Loss of 
                   Capacity - LCAS 
                   Childtraps  : 
                   Description : Rx Partial Loss of Capacity - LCAS"
             ::= { alarmsAndEvents 0 10407 }

      trapSQNCRX NOTIFICATION-TYPE
      OBJECTS {
                    objectNameTrapArg,
                    lctNameTrapArg,
                    trapCountTrapArg,
                    portNumberTrapArg
                }
      STATUS  current
      DESCRIPTION "Severity    : major 
                   Format      :  $1  $2 :Rx Inconsistent Sequence 
                   Number 
                   Childtraps  : 
                   Description : Rx Inconsistent Sequence Number"
             ::= { alarmsAndEvents 0 408 }

      trapSQNCRXClear NOTIFICATION-TYPE
      OBJECTS {
                    objectNameTrapArg,
                    lctNameTrapArg,
                    trapCountTrapArg,
                    portNumberTrapArg
                }
      STATUS  current
      DESCRIPTION "Severity    : major 
                   Format      :  $1  $2 :Rx Inconsistent Sequence 
                   Number 
                   Childtraps  : 
                   Description : Rx Inconsistent Sequence Number"
             ::= { alarmsAndEvents 0 10408 }

      trapCSF NOTIFICATION-TYPE
      OBJECTS {
                    objectNameTrapArg,
                    lctNameTrapArg,
                    trapCountTrapArg,
                    portNumberTrapArg
                }
      STATUS  current
      DESCRIPTION "Severity    : major 
                   Format      :  $1  $2 : Far End Client Signal 
                   Failure 
                   Childtraps  : 
                   Description : Far End Client Signal Failure"
             ::= { alarmsAndEvents 0 409 }

      trapCSFClear NOTIFICATION-TYPE
      OBJECTS {
                    objectNameTrapArg,
                    lctNameTrapArg,
                    trapCountTrapArg,
                    portNumberTrapArg
                }
      STATUS  current
      DESCRIPTION "Severity    : major 
                   Format      :  $1  $2 : Far End Client Signal 
                   Failure 
                   Childtraps  : 
                   Description : Far End Client Signal Failure"
             ::= { alarmsAndEvents 0 10409 }

      trapLFD NOTIFICATION-TYPE
      OBJECTS {
                    objectNameTrapArg,
                    lctNameTrapArg,
                    trapCountTrapArg,
                    portNumberTrapArg
                }
      STATUS  current
      DESCRIPTION "Severity    : critical 
                   Format      :  $1  $2 : Loss of Frame 
                   Delineation-GFP 
                   Childtraps  : 
                   Description : Loss of Frame Delineation"
             ::= { alarmsAndEvents 0 410 }

      trapLFDClear NOTIFICATION-TYPE
      OBJECTS {
                    objectNameTrapArg,
                    lctNameTrapArg,
                    trapCountTrapArg,
                    portNumberTrapArg
                }
      STATUS  current
      DESCRIPTION "Severity    : critical 
                   Format      :  $1  $2 : Loss of Frame 
                   Delineation-GFP 
                   Childtraps  : 
                   Description : Loss of Frame Delineation"
             ::= { alarmsAndEvents 0 10410 }

      trapRxLTC NOTIFICATION-TYPE
      OBJECTS {
                    objectNameTrapArg,
                    lctNameTrapArg,
                    trapCountTrapArg,
                    portNumberTrapArg
                }
      STATUS  current
      DESCRIPTION "Severity    : major 
                   Childtraps  : 
                   Description : Rx Total Loss of Capacity"
             ::= { alarmsAndEvents 0 411 }

      trapRxLTCClear NOTIFICATION-TYPE
      OBJECTS {
                    objectNameTrapArg,
                    lctNameTrapArg,
                    trapCountTrapArg,
                    portNumberTrapArg
                }
      STATUS  current
      DESCRIPTION "Severity    : major 
                   Childtraps  : 
                   Description : Rx Total Loss of Capacity"
             ::= { alarmsAndEvents 0 10411 }

      trapLinkDown NOTIFICATION-TYPE
      OBJECTS {
                    objectNameTrapArg,
                    lctNameTrapArg,
                    trapCountTrapArg,
                    portNumberTrapArg
                }
      STATUS  current
      DESCRIPTION "Severity    : critical 
                   Format      :  $1  $2 : Link Down 
                   Childtraps  : 
                   Description : Link Down"
             ::= { alarmsAndEvents 0 493 }

      trapLinkDownClear NOTIFICATION-TYPE
      OBJECTS {
                    objectNameTrapArg,
                    lctNameTrapArg,
                    trapCountTrapArg,
                    portNumberTrapArg
                }
      STATUS  current
      DESCRIPTION "Severity    : critical 
                   Format      :  $1  $2 : Link Down 
                   Childtraps  : 
                   Description : Link Down"
             ::= { alarmsAndEvents 0 10493 }

      trapVCGEER NOTIFICATION-TYPE
      OBJECTS {
                    objectNameTrapArg,
                    lctNameTrapArg,
                    trapCountTrapArg,
                    portNumberTrapArg
                }
      STATUS  current
      DESCRIPTION "Severity    : major 
                   Format      :  $1  $2 : Excessive Error Ratio 
                   Childtraps  : 
                   Description : Excessive Error Ratio"
             ::= { alarmsAndEvents 0 495 }

      trapVCGEERClear NOTIFICATION-TYPE
      OBJECTS {
                    objectNameTrapArg,
                    lctNameTrapArg,
                    trapCountTrapArg,
                    portNumberTrapArg
                }
      STATUS  current
      DESCRIPTION "Severity    : major 
                   Format      :  $1  $2 : Excessive Error Ratio 
                   Childtraps  : 
                   Description : Excessive Error Ratio"
             ::= { alarmsAndEvents 0 10495 }

      trapVCGSD NOTIFICATION-TYPE
      OBJECTS {
                    objectNameTrapArg,
                    lctNameTrapArg,
                    trapCountTrapArg,
                    portNumberTrapArg
                }
      STATUS  current
      DESCRIPTION "Severity    : minor 
                   Format      :  $1  $2 : Signal Degrade 
                   Childtraps  : 
                   Description : Signal Degrade"
             ::= { alarmsAndEvents 0 496 }

      trapVCGSDClear NOTIFICATION-TYPE
      OBJECTS {
                    objectNameTrapArg,
                    lctNameTrapArg,
                    trapCountTrapArg,
                    portNumberTrapArg
                }
      STATUS  current
      DESCRIPTION "Severity    : minor 
                   Format      :  $1  $2 : Signal Degrade 
                   Childtraps  : 
                   Description : Signal Degrade"
             ::= { alarmsAndEvents 0 10496 }

      trapPTxLTC NOTIFICATION-TYPE
      OBJECTS {
                    objectNameTrapArg,
                    lctNameTrapArg,
                    trapCountTrapArg,
                    portNumberTrapArg
                }
      STATUS  current
      DESCRIPTION "Severity    : minor 
                   Format      :  $1  $2 : Tx Partial Loss of 
                   Capacity - LCAS 
                   Childtraps  : 
                   Description : Tx Partial Loss of Capacity - LCAS"
             ::= { alarmsAndEvents 0 497 }

      trapPTxLTCClear NOTIFICATION-TYPE
      OBJECTS {
                    objectNameTrapArg,
                    lctNameTrapArg,
                    trapCountTrapArg,
                    portNumberTrapArg
                }
      STATUS  current
      DESCRIPTION "Severity    : minor 
                   Format      :  $1  $2 : Tx Partial Loss of 
                   Capacity - LCAS 
                   Childtraps  : 
                   Description : Tx Partial Loss of Capacity - LCAS"
             ::= { alarmsAndEvents 0 10497 }

      trapUPM NOTIFICATION-TYPE
      OBJECTS {
                    objectNameTrapArg,
                    lctNameTrapArg,
                    trapCountTrapArg,
                    portNumberTrapArg
                }
      STATUS  current
      DESCRIPTION "Severity    : critical 
                   Childtraps  : 
                   Description : User Payload Mismatch"
             ::= { alarmsAndEvents 0 498 }

      trapUPMClear NOTIFICATION-TYPE
      OBJECTS {
                    objectNameTrapArg,
                    lctNameTrapArg,
                    trapCountTrapArg,
                    portNumberTrapArg
                }
      STATUS  current
      DESCRIPTION "Severity    : critical 
                   Childtraps  : 
                   Description : User Payload Mismatch"
             ::= { alarmsAndEvents 0 10498 }

      trapEXM NOTIFICATION-TYPE
      OBJECTS {
                    objectNameTrapArg,
                    lctNameTrapArg,
                    trapCountTrapArg,
                    portNumberTrapArg
                }
      STATUS  current
      DESCRIPTION "Severity    : major 
                   Format      :  $1  $2 : Extended Header 
                   Mismatch-GFP 
                   Childtraps  : 
                   Description : Extended Header Mismatch"
             ::= { alarmsAndEvents 0 499 }

      trapEXMClear NOTIFICATION-TYPE
      OBJECTS {
                    objectNameTrapArg,
                    lctNameTrapArg,
                    trapCountTrapArg,
                    portNumberTrapArg
                }
      STATUS  current
      DESCRIPTION "Severity    : major 
                   Format      :  $1  $2 : Extended Header 
                   Mismatch-GFP 
                   Childtraps  : 
                   Description : Extended Header Mismatch"
             ::= { alarmsAndEvents 0 10499 }

      trapCCSF NOTIFICATION-TYPE
      OBJECTS {
                    objectNameTrapArg,
                    lctNameTrapArg,
                    trapCountTrapArg,
                    portNumberTrapArg
                }
      STATUS  current
      DESCRIPTION "Severity    : critical 
                   Format      :  $1  $2 : Far End Client Character 
                   Synchronization Failure 
                   Childtraps  : 
                   Description : Far End Client Character 
                   Synchronization Failure"
             ::= { alarmsAndEvents 0 543 }

      trapCCSFClear NOTIFICATION-TYPE
      OBJECTS {
                    objectNameTrapArg,
                    lctNameTrapArg,
                    trapCountTrapArg,
                    portNumberTrapArg
                }
      STATUS  current
      DESCRIPTION "Severity    : critical 
                   Format      :  $1  $2 : Far End Client Character 
                   Synchronization Failure 
                   Childtraps  : 
                   Description : Far End Client Character 
                   Synchronization Failure"
             ::= { alarmsAndEvents 0 10543 }

      trapLLC NOTIFICATION-TYPE
      OBJECTS {
                    objectNameTrapArg,
                    lctNameTrapArg,
                    trapCountTrapArg,
                    portNumberTrapArg
                }
      STATUS  current
      DESCRIPTION "Severity    : major 
                   Format      :  $1  $2 : Loss of LCAS Capability 
                   Childtraps  : 
                   Description : Loss of LCAS Capability"
             ::= { alarmsAndEvents 0 593 }

      trapLLCClear NOTIFICATION-TYPE
      OBJECTS {
                    objectNameTrapArg,
                    lctNameTrapArg,
                    trapCountTrapArg,
                    portNumberTrapArg
                }
      STATUS  current
      DESCRIPTION "Severity    : major 
                   Format      :  $1  $2 : Loss of LCAS Capability 
                   Childtraps  : 
                   Description : Loss of LCAS Capability"
             ::= { alarmsAndEvents 0 10593 }

      trapSQNCTX NOTIFICATION-TYPE
      OBJECTS {
                    objectNameTrapArg,
                    lctNameTrapArg,
                    trapCountTrapArg,
                    portNumberTrapArg
                }
      STATUS  current
      DESCRIPTION "Severity    : major 
                   Format      :  $1  $2 :Tx Inconsistent Sequence 
                   Number-LCAS 
                   Childtraps  : 
                   Description : Tx Inconsistent Sequence 
                   Number-LCAS"
             ::= { alarmsAndEvents 0 609 }

      trapSQNCTXClear NOTIFICATION-TYPE
      OBJECTS {
                    objectNameTrapArg,
                    lctNameTrapArg,
                    trapCountTrapArg,
                    portNumberTrapArg
                }
      STATUS  current
      DESCRIPTION "Severity    : major 
                   Format      :  $1  $2 :Tx Inconsistent Sequence 
                   Number-LCAS 
                   Childtraps  : 
                   Description : Tx Inconsistent Sequence 
                   Number-LCAS"
             ::= { alarmsAndEvents 0 10609 }

      trapGIDMismatch NOTIFICATION-TYPE
      OBJECTS {
                    objectNameTrapArg,
                    lctNameTrapArg,
                    trapCountTrapArg,
                    portNumberTrapArg
                }
      STATUS  current
      DESCRIPTION "Severity    : major 
                   Format      :  $1  $2 :Group Identifier 
                   Mismatch-LCAS 
                   Childtraps  : 
                   Description : Group Identifier Mismatch-LCAS"
             ::= { alarmsAndEvents 0 610 }

      trapGIDMismatchClear NOTIFICATION-TYPE
      OBJECTS {
                    objectNameTrapArg,
                    lctNameTrapArg,
                    trapCountTrapArg,
                    portNumberTrapArg
                }
      STATUS  current
      DESCRIPTION "Severity    : major 
                   Format      :  $1  $2 :Group Identifier 
                   Mismatch-LCAS 
                   Childtraps  : 
                   Description : Group Identifier Mismatch-LCAS"
             ::= { alarmsAndEvents 0 10610 }

      trapTcaVCGES NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      :  $1  $2 : TCA:Errored Seconds - 
                   VCGPort 
                   Childtraps  : 
                   Description : TCA: Errored Seconds - VCGPort"
             ::= { tcas 0 736 }

      trapTcaVCGSES NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      :  $1  $2 : TCA:Severely Errored 
                   Seconds - VCGPort 
                   Childtraps  : 
                   Description : TCA: Severely Errored Seconds - 
                   VCGPort"
             ::= { tcas 0 737 }

      trapTcaVCGUAS NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      :  $1  $2 : TCA:Unavailable Seconds - 
                   VCGPort 
                   Childtraps  : 
                   Description : TCA: Unavailable Seconds - VCGPort"
             ::= { tcas 0 738 }

      trapNeighborChange NOTIFICATION-TYPE
      OBJECTS {
                    objectNameTrapArg,
                    lctNameTrapArg,
                    trapCountTrapArg
                }
      STATUS  current
      DESCRIPTION "Severity    : zilch 
                   Format      :  $1 Trunk  $2  neighbor information 
                   changed 
                   Childtraps  : 
                   Description : Trunk neighbor information changed"
             ::= { alarmsAndEvents 0 372 }

      trapTrunkOperDown NOTIFICATION-TYPE
      OBJECTS {
                    objectNameTrapArg,
                    lctNameTrapArg,
                    trapCountTrapArg,
                    serviceIdTrapArg
                }
      STATUS  current
      DESCRIPTION "Severity    : minor 
                   Format      :  $1  $2  is down.~ Trunk down 
                   cleared on 
                   Childtraps  : 
                   Description : Trunk oper down"
             ::= { alarmsAndEvents 0 389 }

      trapTrunkOperDownClear NOTIFICATION-TYPE
      OBJECTS {
                    objectNameTrapArg,
                    lctNameTrapArg,
                    trapCountTrapArg,
                    serviceIdTrapArg
                }
      STATUS  current
      DESCRIPTION "Severity    : minor 
                   Format      :  $1  $2  is down.~ Trunk down 
                   cleared on 
                   Childtraps  : 
                   Description : Trunk oper down"
             ::= { alarmsAndEvents 0 10389 }

      trapCardJackIn NOTIFICATION-TYPE
      OBJECTS {
                    objectNameTrapArg,
                    lctNameTrapArg,
                    trapCountTrapArg,
                    slotNumberTrapArg,
                    cardTypeTrapArg
                }
      STATUS  current
      DESCRIPTION "Severity    : zilch 
                   Format      :  $1 Card jacked in in  $2  slot  $3 
                    of type  $4 . 
                   Childtraps  : 
                   Description : Card jacked in"
             ::= { alarmsAndEvents 0 151 }

      trapCardJackOut NOTIFICATION-TYPE
      OBJECTS {
                    objectNameTrapArg,
                    lctNameTrapArg,
                    trapCountTrapArg,
                    slotNumberTrapArg,
                    cardTypeTrapArg
                }
      STATUS  current
      DESCRIPTION "Severity    : major 
                   Format      :  $1 Card jacked out in  $2  slot  
                   $3 . 
                   Childtraps  : 
                   Description : Card jacked out"
             ::= { alarmsAndEvents 0 152 }

      trapClockHoldOver NOTIFICATION-TYPE
      OBJECTS {
                    objectNameTrapArg,
                    lctNameTrapArg,
                    trapCountTrapArg
                }
      STATUS  current
      DESCRIPTION "Severity    : major 
                   Format      :  $1 System clock in holdover mode. 
                   Childtraps  : 
                   Description : System  clock in  holdover mode."
             ::= { alarmsAndEvents 0 373 }

      trapClockHoldOverClear NOTIFICATION-TYPE
      OBJECTS {
                    objectNameTrapArg,
                    lctNameTrapArg,
                    trapCountTrapArg
                }
      STATUS  current
      DESCRIPTION "Severity    : major 
                   Format      :  $1 System clock in holdover mode. 
                   Childtraps  : 
                   Description : System  clock in  holdover mode."
             ::= { alarmsAndEvents 0 10373 }

      trapTMGGenerationEntryFreeRun NOTIFICATION-TYPE
      OBJECTS {
                    objectNameTrapArg,
                    lctNameTrapArg,
                    trapCountTrapArg
                }
      STATUS  current
      DESCRIPTION "Severity    : major 
                   Format      :  $1 Timing Generation Entry to Free 
                   Run 
                   Childtraps  : 
                   Description : Timing Generation Entry to FreeRun"
             ::= { alarmsAndEvents 0 477 }

      trapTMGGenerationEntryFreeRunClear NOTIFICATION-TYPE
      OBJECTS {
                    objectNameTrapArg,
                    lctNameTrapArg,
                    trapCountTrapArg
                }
      STATUS  current
      DESCRIPTION "Severity    : major 
                   Format      :  $1 Timing Generation Entry to Free 
                   Run 
                   Childtraps  : 
                   Description : Timing Generation Entry to FreeRun"
             ::= { alarmsAndEvents 0 10477 }

      trapAllRadiusServersUnreachable NOTIFICATION-TYPE
      OBJECTS {
                    objectNameTrapArg,
                    lctNameTrapArg,
                    trapCountTrapArg
                }
      STATUS  current
      DESCRIPTION "Severity    : major 
                   Format      :  $1 All RADIUS Servers Are 
                   Unavailable 
                   Childtraps  : 
                   Description : All RADIUS Servers Are Unavailable"
             ::= { alarmsAndEvents 0 647 }

      trapAllRadiusServersUnreachableClear NOTIFICATION-TYPE
      OBJECTS {
                    objectNameTrapArg,
                    lctNameTrapArg,
                    trapCountTrapArg
                }
      STATUS  current
      DESCRIPTION "Severity    : major 
                   Format      :  $1 All RADIUS Servers Are 
                   Unavailable 
                   Childtraps  : 
                   Description : All RADIUS Servers Are Unavailable"
             ::= { alarmsAndEvents 0 10647 }

      trapInventoryInserted NOTIFICATION-TYPE
      OBJECTS {
                    objectNameTrapArg,
                    lctNameTrapArg,
                    trapCountTrapArg,
                    slotNumberTrapArg,
                    cardTypeTrapArg
                }
      STATUS  current
      DESCRIPTION "Severity    : zilch 
                   Format      :  $1 Card jacked in in  $2  slot  $3 
                    of type  $4 . 
                   Childtraps  : 
                   Description : Inventory Inserted"
             ::= { alarmsAndEvents 0 655 }

      trapTimMgrTimingInHoldOver NOTIFICATION-TYPE
      OBJECTS {
                    objectNameTrapArg,
                    lctNameTrapArg,
                    trapCountTrapArg
                }
      STATUS  current
      DESCRIPTION "Severity    : major 
                   Format      :  $1 System clock in holdover mode. 
                   Childtraps  : 
                   Description : System  clock in  holdover mode."
             ::= { alarmsAndEvents 0 96 }

      trapTimMgrTimingInHoldOverClear NOTIFICATION-TYPE
      OBJECTS {
                    objectNameTrapArg,
                    lctNameTrapArg,
                    trapCountTrapArg
                }
      STATUS  current
      DESCRIPTION "Severity    : major 
                   Format      :  $1 System clock in holdover mode. 
                   Childtraps  : 
                   Description : System  clock in  holdover mode."
             ::= { alarmsAndEvents 0 10096 }

      trapTimMgrTimingInInternal NOTIFICATION-TYPE
      OBJECTS {
                    objectNameTrapArg,
                    lctNameTrapArg,
                    trapCountTrapArg
                }
      STATUS  current
      DESCRIPTION "Severity    : major 
                   Format      :  $1 System clock in internal mode. 
                   Childtraps  : 
                   Description : System clock in internal mode."
             ::= { alarmsAndEvents 0 97 }

      trapTimMgrTimingInInternalClear NOTIFICATION-TYPE
      OBJECTS {
                    objectNameTrapArg,
                    lctNameTrapArg,
                    trapCountTrapArg
                }
      STATUS  current
      DESCRIPTION "Severity    : major 
                   Format      :  $1 System clock in internal mode. 
                   Childtraps  : 
                   Description : System clock in internal mode."
             ::= { alarmsAndEvents 0 10097 }

      trapTimMgrPrimaryRefFailed NOTIFICATION-TYPE
      OBJECTS {
                    objectNameTrapArg,
                    lctNameTrapArg,
                    trapCountTrapArg
                }
      STATUS  current
      DESCRIPTION "Severity    : major 
                   Format      :  $1 System primary timing reference 
                   failed. 
                   Childtraps  : 
                   Description : system primary timing reference 
                   failed"
             ::= { alarmsAndEvents 0 98 }

      trapTimMgrPrimaryRefFailedClear NOTIFICATION-TYPE
      OBJECTS {
                    objectNameTrapArg,
                    lctNameTrapArg,
                    trapCountTrapArg
                }
      STATUS  current
      DESCRIPTION "Severity    : major 
                   Format      :  $1 System primary timing reference 
                   failed. 
                   Childtraps  : 
                   Description : system primary timing reference 
                   failed"
             ::= { alarmsAndEvents 0 10098 }

      trapTimMgrSecondaryRefFailed NOTIFICATION-TYPE
      OBJECTS {
                    objectNameTrapArg,
                    lctNameTrapArg,
                    trapCountTrapArg
                }
      STATUS  current
      DESCRIPTION "Severity    : major 
                   Format      :  $1 System secondary timing 
                   reference failed. 
                   Childtraps  : 
                   Description : system secondary timing reference 
                   failed"
             ::= { alarmsAndEvents 0 99 }

      trapTimMgrSecondaryRefFailedClear NOTIFICATION-TYPE
      OBJECTS {
                    objectNameTrapArg,
                    lctNameTrapArg,
                    trapCountTrapArg
                }
      STATUS  current
      DESCRIPTION "Severity    : major 
                   Format      :  $1 System secondary timing 
                   reference failed. 
                   Childtraps  : 
                   Description : system secondary timing reference 
                   failed"
             ::= { alarmsAndEvents 0 10099 }

      trapTerminalLoopbackActive NOTIFICATION-TYPE
      OBJECTS {
                    objectNameTrapArg,
                    lctNameTrapArg,
                    trapCountTrapArg
                }
      STATUS  current
      DESCRIPTION "Severity    : minor 
                   Format      :  $1 Loopback Active - Terminal: 
                   Childtraps  : 
                   Description : Loopback Active - Terminal"
             ::= { alarmsAndEvents 0 361 }

      trapTerminalLoopbackActiveClear NOTIFICATION-TYPE
      OBJECTS {
                    objectNameTrapArg,
                    lctNameTrapArg,
                    trapCountTrapArg
                }
      STATUS  current
      DESCRIPTION "Severity    : minor 
                   Format      :  $1 Loopback Active - Terminal: 
                   Childtraps  : 
                   Description : Loopback Active - Terminal"
             ::= { alarmsAndEvents 0 10361 }

      trapFacilityLoopbackActive NOTIFICATION-TYPE
      OBJECTS {
                    objectNameTrapArg,
                    lctNameTrapArg,
                    trapCountTrapArg
                }
      STATUS  current
      DESCRIPTION "Severity    : minor 
                   Format      :  $1 Loopback Active - Facility 
                   Childtraps  : 
                   Description : Loopback Active - Facility"
             ::= { alarmsAndEvents 0 377 }

      trapFacilityLoopbackActiveClear NOTIFICATION-TYPE
      OBJECTS {
                    objectNameTrapArg,
                    lctNameTrapArg,
                    trapCountTrapArg
                }
      STATUS  current
      DESCRIPTION "Severity    : minor 
                   Format      :  $1 Loopback Active - Facility 
                   Childtraps  : 
                   Description : Loopback Active - Facility"
             ::= { alarmsAndEvents 0 10377 }

      trapTransparentLoopbackActive NOTIFICATION-TYPE
      OBJECTS {
                    objectNameTrapArg,
                    lctNameTrapArg,
                    trapCountTrapArg
                }
      STATUS  current
      DESCRIPTION "Severity    : minor 
                   Format      :  $1 Loopback Active - Transparent: 
                   Childtraps  : 
                   Description : Loopback Active - Transparent"
             ::= { alarmsAndEvents 0 692 }

      trapTransparentLoopbackActiveClear NOTIFICATION-TYPE
      OBJECTS {
                    objectNameTrapArg,
                    lctNameTrapArg,
                    trapCountTrapArg
                }
      STATUS  current
      DESCRIPTION "Severity    : minor 
                   Format      :  $1 Loopback Active - Transparent: 
                   Childtraps  : 
                   Description : Loopback Active - Transparent"
             ::= { alarmsAndEvents 0 10692 }

      trapNoRPLOwnerConfigured NOTIFICATION-TYPE
      OBJECTS {
                    objectNameTrapArg,
                    lctNameTrapArg,
                    trapCountTrapArg,
                    slotNumberTrapArg
                }
      STATUS  current
      DESCRIPTION "Severity    : critical 
                   Format      :  $1 No RPL Owner Configured 
                   Childtraps  : 
                   Description : No RPL Owner Configured"
             ::= { alarmsAndEvents 0 659 }

      trapNoRPLOwnerConfiguredClear NOTIFICATION-TYPE
      OBJECTS {
                    objectNameTrapArg,
                    lctNameTrapArg,
                    trapCountTrapArg,
                    slotNumberTrapArg
                }
      STATUS  current
      DESCRIPTION "Severity    : critical 
                   Format      :  $1 No RPL Owner Configured 
                   Childtraps  : 
                   Description : No RPL Owner Configured"
             ::= { alarmsAndEvents 0 10659 }

      trapMultipleRPLOwnersConfigured NOTIFICATION-TYPE
      OBJECTS {
                    objectNameTrapArg,
                    lctNameTrapArg,
                    trapCountTrapArg,
                    slotNumberTrapArg
                }
      STATUS  current
      DESCRIPTION "Severity    : critical 
                   Format      :  $1 Multiple RPLOwners Configured 
                   Childtraps  : 
                   Description : Multiple RPLOwners Configured"
             ::= { alarmsAndEvents 0 660 }

      trapMultipleRPLOwnersConfiguredClear NOTIFICATION-TYPE
      OBJECTS {
                    objectNameTrapArg,
                    lctNameTrapArg,
                    trapCountTrapArg,
                    slotNumberTrapArg
                }
      STATUS  current
      DESCRIPTION "Severity    : critical 
                   Format      :  $1 Multiple RPLOwners Configured 
                   Childtraps  : 
                   Description : Multiple RPLOwners Configured"
             ::= { alarmsAndEvents 0 10660 }

      trapRingletProtectStateChange NOTIFICATION-TYPE
      OBJECTS {
                    objectNameTrapArg,
                    lctNameTrapArg,
                    trapCountTrapArg,
                    slotNumberTrapArg
                }
      STATUS  current
      DESCRIPTION "Severity    : zilch 
                   Format      :  $1 Ringlet protection status 
                   Childtraps  : 
                   Description : Ringlet protection status"
             ::= { alarmsAndEvents 0 678 }

      trapEastPortStatusChange NOTIFICATION-TYPE
      OBJECTS {
                    objectNameTrapArg,
                    lctNameTrapArg,
                    trapCountTrapArg,
                    slotNumberTrapArg
                }
      STATUS  current
      DESCRIPTION "Severity    : zilch 
                   Format      :  $1 EastPort Status 
                   Childtraps  : 
                   Description : EastPort Status"
             ::= { alarmsAndEvents 0 679 }

      trapWestPortStatusChange NOTIFICATION-TYPE
      OBJECTS {
                    objectNameTrapArg,
                    lctNameTrapArg,
                    trapCountTrapArg,
                    slotNumberTrapArg
                }
      STATUS  current
      DESCRIPTION "Severity    : zilch 
                   Format      :  $1 WestPort Status 
                   Childtraps  : 
                   Description : WestPort Status"
             ::= { alarmsAndEvents 0 680 }

      trapBitsPdhLOS NOTIFICATION-TYPE
      OBJECTS {
                    objectNameTrapArg,
                    lctNameTrapArg,
                    trapCountTrapArg,
                    portNumberTrapArg
                }
      STATUS  current
      DESCRIPTION "Severity    : major 
                   Format      :  $1 Loss of Signal on BITS Port 
                   Childtraps  : 
                   Description : Loss Of Signal"
             ::= { alarmsAndEvents 0 539 }

      trapBitsPdhLOSClear NOTIFICATION-TYPE
      OBJECTS {
                    objectNameTrapArg,
                    lctNameTrapArg,
                    trapCountTrapArg,
                    portNumberTrapArg
                }
      STATUS  current
      DESCRIPTION "Severity    : major 
                   Format      :  $1 Loss of Signal on BITS Port 
                   Childtraps  : 
                   Description : Loss Of Signal"
             ::= { alarmsAndEvents 0 10539 }

      trapBitsPdhAis NOTIFICATION-TYPE
      OBJECTS {
                    objectNameTrapArg,
                    lctNameTrapArg,
                    trapCountTrapArg,
                    portNumberTrapArg
                }
      STATUS  current
      DESCRIPTION "Severity    : major 
                   Format      :  $1 Alarm Indication Signal on BITS 
                   Port 
                   Childtraps  : 
                   Description : Alarm Indication Signal"
             ::= { alarmsAndEvents 0 540 }

      trapBitsPdhAisClear NOTIFICATION-TYPE
      OBJECTS {
                    objectNameTrapArg,
                    lctNameTrapArg,
                    trapCountTrapArg,
                    portNumberTrapArg
                }
      STATUS  current
      DESCRIPTION "Severity    : major 
                   Format      :  $1 Alarm Indication Signal on BITS 
                   Port 
                   Childtraps  : 
                   Description : Alarm Indication Signal"
             ::= { alarmsAndEvents 0 10540 }

      trapBitsPdhLof NOTIFICATION-TYPE
      OBJECTS {
                    objectNameTrapArg,
                    lctNameTrapArg,
                    trapCountTrapArg,
                    portNumberTrapArg
                }
      STATUS  current
      DESCRIPTION "Severity    : major 
                   Format      :  $1 Loss Of Frame on BITS Port 
                   Childtraps  : 
                   Description : Loss Of Frame"
             ::= { alarmsAndEvents 0 541 }

      trapBitsPdhLofClear NOTIFICATION-TYPE
      OBJECTS {
                    objectNameTrapArg,
                    lctNameTrapArg,
                    trapCountTrapArg,
                    portNumberTrapArg
                }
      STATUS  current
      DESCRIPTION "Severity    : major 
                   Format      :  $1 Loss Of Frame on BITS Port 
                   Childtraps  : 
                   Description : Loss Of Frame"
             ::= { alarmsAndEvents 0 10541 }

      trapPrimaryRadiusServerUnreachable NOTIFICATION-TYPE
      OBJECTS {
                    objectNameTrapArg,
                    lctNameTrapArg,
                    trapCountTrapArg
                }
      STATUS  current
      DESCRIPTION "Severity    : minor 
                   Format      :  $1 Primary RADIUS Server 
                   Unavailable 
                   Childtraps  : 
                   Description : Primary RADIUS Server Unavailable"
             ::= { alarmsAndEvents 0 645 }

      trapPrimaryRadiusServerUnreachableClear NOTIFICATION-TYPE
      OBJECTS {
                    objectNameTrapArg,
                    lctNameTrapArg,
                    trapCountTrapArg
                }
      STATUS  current
      DESCRIPTION "Severity    : minor 
                   Format      :  $1 Primary RADIUS Server 
                   Unavailable 
                   Childtraps  : 
                   Description : Primary RADIUS Server Unavailable"
             ::= { alarmsAndEvents 0 10645 }

      trapSecondaryRadiusServerUnreachable NOTIFICATION-TYPE
      OBJECTS {
                    objectNameTrapArg,
                    lctNameTrapArg,
                    trapCountTrapArg
                }
      STATUS  current
      DESCRIPTION "Severity    : minor 
                   Format      :  $1 Secondary RADIUS Servers 
                   Unavailable 
                   Childtraps  : 
                   Description : Secondary RADIUS Servers 
                   Unavailable"
             ::= { alarmsAndEvents 0 646 }

      trapSecondaryRadiusServerUnreachableClear NOTIFICATION-TYPE
      OBJECTS {
                    objectNameTrapArg,
                    lctNameTrapArg,
                    trapCountTrapArg
                }
      STATUS  current
      DESCRIPTION "Severity    : minor 
                   Format      :  $1 Secondary RADIUS Servers 
                   Unavailable 
                   Childtraps  : 
                   Description : Secondary RADIUS Servers 
                   Unavailable"
             ::= { alarmsAndEvents 0 10646 }

      trapVoltageOverload NOTIFICATION-TYPE
      OBJECTS {
                    objectNameTrapArg,
                    lctNameTrapArg,
                    trapCountTrapArg,
                    slotNumberTrapArg
                }
      STATUS  current
      DESCRIPTION "Severity    : major 
                   Format      :  $1 Derived Voltage High 
                   Childtraps  : 
                   Description : Derived Voltage High"
             ::= { alarmsAndEvents 0 201 }

      trapVoltageOverloadClear NOTIFICATION-TYPE
      OBJECTS {
                    objectNameTrapArg,
                    lctNameTrapArg,
                    trapCountTrapArg,
                    slotNumberTrapArg
                }
      STATUS  current
      DESCRIPTION "Severity    : major 
                   Format      :  $1 Derived Voltage High 
                   Childtraps  : 
                   Description : Derived Voltage High"
             ::= { alarmsAndEvents 0 10201 }

      trapVoltageUnderload NOTIFICATION-TYPE
      OBJECTS {
                    objectNameTrapArg,
                    lctNameTrapArg,
                    trapCountTrapArg,
                    slotNumberTrapArg
                }
      STATUS  current
      DESCRIPTION "Severity    : major 
                   Format      :  $1 Derived Voltage Low 
                   Childtraps  : 
                   Description : Derived Voltage Low"
             ::= { alarmsAndEvents 0 369 }

      trapVoltageUnderloadClear NOTIFICATION-TYPE
      OBJECTS {
                    objectNameTrapArg,
                    lctNameTrapArg,
                    trapCountTrapArg,
                    slotNumberTrapArg
                }
      STATUS  current
      DESCRIPTION "Severity    : major 
                   Format      :  $1 Derived Voltage Low 
                   Childtraps  : 
                   Description : Derived Voltage Low"
             ::= { alarmsAndEvents 0 10369 }

      trapInputVoltageOverload NOTIFICATION-TYPE
      OBJECTS {
                    objectNameTrapArg,
                    lctNameTrapArg,
                    trapCountTrapArg,
                    slotNumberTrapArg
                }
      STATUS  current
      DESCRIPTION "Severity    : major 
                   Format      :  $1 Input Voltage High on  $2 . 
                   Childtraps  : 
                   Description : Input Voltage High on PSU Card"
             ::= { alarmsAndEvents 0 370 }

      trapInputVoltageOverloadClear NOTIFICATION-TYPE
      OBJECTS {
                    objectNameTrapArg,
                    lctNameTrapArg,
                    trapCountTrapArg,
                    slotNumberTrapArg
                }
      STATUS  current
      DESCRIPTION "Severity    : major 
                   Format      :  $1 Input Voltage High on  $2 . 
                   Childtraps  : 
                   Description : Input Voltage High on PSU Card"
             ::= { alarmsAndEvents 0 10370 }

      trapInputVoltageUnderload NOTIFICATION-TYPE
      OBJECTS {
                    objectNameTrapArg,
                    lctNameTrapArg,
                    trapCountTrapArg,
                    slotNumberTrapArg
                }
      STATUS  current
      DESCRIPTION "Severity    : major 
                   Format      :  $1 Input Voltage Low on  $2 . 
                   Childtraps  : 
                   Description : Input Voltage Low on PSU Card"
             ::= { alarmsAndEvents 0 371 }

      trapInputVoltageUnderloadClear NOTIFICATION-TYPE
      OBJECTS {
                    objectNameTrapArg,
                    lctNameTrapArg,
                    trapCountTrapArg,
                    slotNumberTrapArg
                }
      STATUS  current
      DESCRIPTION "Severity    : major 
                   Format      :  $1 Input Voltage Low on  $2 . 
                   Childtraps  : 
                   Description : Input Voltage Low on PSU Card"
             ::= { alarmsAndEvents 0 10371 }

      trapNoInputVoltage NOTIFICATION-TYPE
      OBJECTS {
                    objectNameTrapArg,
                    lctNameTrapArg,
                    trapCountTrapArg,
                    slotNumberTrapArg
                }
      STATUS  current
      DESCRIPTION "Severity    : major 
                   Format      :  $1  $2  Switched off/No Input 
                   Voltage. 
                   Childtraps  : 
                   Description : Switched off/No Input Voltage."
             ::= { alarmsAndEvents 0 388 }

      trapNoInputVoltageClear NOTIFICATION-TYPE
      OBJECTS {
                    objectNameTrapArg,
                    lctNameTrapArg,
                    trapCountTrapArg,
                    slotNumberTrapArg
                }
      STATUS  current
      DESCRIPTION "Severity    : major 
                   Format      :  $1  $2  Switched off/No Input 
                   Voltage. 
                   Childtraps  : 
                   Description : Switched off/No Input Voltage."
             ::= { alarmsAndEvents 0 10388 }

      trapFuseFailure NOTIFICATION-TYPE
      OBJECTS {
                    objectNameTrapArg,
                    lctNameTrapArg,
                    trapCountTrapArg,
                    slotNumberTrapArg
                }
      STATUS  current
      DESCRIPTION "Severity    : major 
                   Format      :  $1  $2  PSU Fuse Failed. 
                   Childtraps  : 
                   Description : Fuse Failed."
             ::= { alarmsAndEvents 0 703 }

      trapFuseFailureClear NOTIFICATION-TYPE
      OBJECTS {
                    objectNameTrapArg,
                    lctNameTrapArg,
                    trapCountTrapArg,
                    slotNumberTrapArg
                }
      STATUS  current
      DESCRIPTION "Severity    : major 
                   Format      :  $1  $2  PSU Fuse Failed. 
                   Childtraps  : 
                   Description : Fuse Failed."
             ::= { alarmsAndEvents 0 10703 }

      trapSQM NOTIFICATION-TYPE
      OBJECTS {
                    objectNameTrapArg,
                    lctNameTrapArg,
                    trapCountTrapArg
                }
      STATUS  current
      DESCRIPTION "Severity    : major 
                   Format      :  $1 Sequence indicator mismatch : 
                   Childtraps  : 
                   Description : VC Sequence Indicator Mismatch"
             ::= { alarmsAndEvents 0 382 }

      trapSQMClear NOTIFICATION-TYPE
      OBJECTS {
                    objectNameTrapArg,
                    lctNameTrapArg,
                    trapCountTrapArg
                }
      STATUS  current
      DESCRIPTION "Severity    : major 
                   Format      :  $1 Sequence indicator mismatch : 
                   Childtraps  : 
                   Description : VC Sequence Indicator Mismatch"
             ::= { alarmsAndEvents 0 10382 }

      trapLOM NOTIFICATION-TYPE
      OBJECTS {
                    objectNameTrapArg,
                    lctNameTrapArg,
                    trapCountTrapArg
                }
      STATUS  current
      DESCRIPTION "Severity    : major 
                   Format      :  $1 Loss of Multiframe Alignment : 
                   Childtraps  : 
                   Description : Loss of Multiframe Alignment Signal"
             ::= { alarmsAndEvents 0 383 }

      trapLOMClear NOTIFICATION-TYPE
      OBJECTS {
                    objectNameTrapArg,
                    lctNameTrapArg,
                    trapCountTrapArg
                }
      STATUS  current
      DESCRIPTION "Severity    : major 
                   Format      :  $1 Loss of Multiframe Alignment : 
                   Childtraps  : 
                   Description : Loss of Multiframe Alignment Signal"
             ::= { alarmsAndEvents 0 10383 }

      trapLOC NOTIFICATION-TYPE
      OBJECTS {
                    objectNameTrapArg,
                    lctNameTrapArg,
                    trapCountTrapArg
                }
      STATUS  current
      DESCRIPTION "Severity    : major 
                   Format      :  $1 Loss of Capacity: 
                   Childtraps  : 
                   Description : Loss of Capacity"
             ::= { alarmsAndEvents 0 403 }

      trapLOCClear NOTIFICATION-TYPE
      OBJECTS {
                    objectNameTrapArg,
                    lctNameTrapArg,
                    trapCountTrapArg
                }
      STATUS  current
      DESCRIPTION "Severity    : major 
                   Format      :  $1 Loss of Capacity: 
                   Childtraps  : 
                   Description : Loss of Capacity"
             ::= { alarmsAndEvents 0 10403 }

      trapLocalRemoteIPMatch NOTIFICATION-TYPE
      OBJECTS {
                    objectNameTrapArg,
                    lctNameTrapArg,
                    trapCountTrapArg,
                    slotNumberTrapArg
                }
      STATUS  current
      DESCRIPTION "Severity    : minor 
                   Format      :  $1  $2 :  Remote IP & Local IP 
                   Match 
                   Childtraps  : 
                   Description : Remote and Local IP Match"
             ::= { alarmsAndEvents 0 693 }

      trapLocalRemoteIPMatchClear NOTIFICATION-TYPE
      OBJECTS {
                    objectNameTrapArg,
                    lctNameTrapArg,
                    trapCountTrapArg,
                    slotNumberTrapArg
                }
      STATUS  current
      DESCRIPTION "Severity    : minor 
                   Format      :  $1  $2 :  Remote IP & Local IP 
                   Match 
                   Childtraps  : 
                   Description : Remote and Local IP Match"
             ::= { alarmsAndEvents 0 10693 }

      trapPacketTrunkOperStatus NOTIFICATION-TYPE
      OBJECTS {
                    objectNameTrapArg,
                    lctNameTrapArg,
                    trapCountTrapArg,
                    slotNumberTrapArg
                }
      STATUS  current
      DESCRIPTION "Severity    : minor 
                   Format      :  $1  $2 :  PacketTrunk OperStatus 
                   Down 
                   Childtraps  : 
                   Description : PacketTrunk OperStatus Down"
             ::= { alarmsAndEvents 0 694 }

      trapPacketTrunkOperStatusClear NOTIFICATION-TYPE
      OBJECTS {
                    objectNameTrapArg,
                    lctNameTrapArg,
                    trapCountTrapArg,
                    slotNumberTrapArg
                }
      STATUS  current
      DESCRIPTION "Severity    : minor 
                   Format      :  $1  $2 :  PacketTrunk OperStatus 
                   Down 
                   Childtraps  : 
                   Description : PacketTrunk OperStatus Down"
             ::= { alarmsAndEvents 0 10694 }

      trapRxSignatureUnreliable NOTIFICATION-TYPE
      OBJECTS {
                    objectNameTrapArg,
                    lctNameTrapArg,
                    trapCountTrapArg
                }
      STATUS  current
      DESCRIPTION "Severity    : major 
                   Format      :  $1 Received Auto discovery Tag is 
                   UNRELIABLE for Topology Adjacency object 
                   Childtraps  : 
                   Description : RX Actual Signature Unreliable"
             ::= { alarmsAndEvents 0 616 }

      trapRxSignatureUnreliableClear NOTIFICATION-TYPE
      OBJECTS {
                    objectNameTrapArg,
                    lctNameTrapArg,
                    trapCountTrapArg
                }
      STATUS  current
      DESCRIPTION "Severity    : major 
                   Format      :  $1 Received Auto discovery Tag is 
                   UNRELIABLE for Topology Adjacency object 
                   Childtraps  : 
                   Description : RX Actual Signature Unreliable"
             ::= { alarmsAndEvents 0 10616 }

      trapRxSignatureChanged NOTIFICATION-TYPE
      OBJECTS {
                    objectNameTrapArg,
                    lctNameTrapArg,
                    trapCountTrapArg
                }
      STATUS  current
      DESCRIPTION "Severity    : minor 
                   Format      :  $1 Receiving Auto discovery 
                   Signature 
                   Childtraps  : 
                   Description : RX Actual Signature changed"
             ::= { alarmsAndEvents 0 617 }

      trapSFPMismatch NOTIFICATION-TYPE
      OBJECTS {
                    objectNameTrapArg,
                    lctNameTrapArg,
                    trapCountTrapArg,
                    slotNumberTrapArg
                }
      STATUS  current
      DESCRIPTION "Severity    : critical 
                   Format      :  $1  $2  Mismatch. 
                   Childtraps  : 
                   Description : SFP Mismatch"
             ::= { alarmsAndEvents 0 359 }

      trapSFPMismatchClear NOTIFICATION-TYPE
      OBJECTS {
                    objectNameTrapArg,
                    lctNameTrapArg,
                    trapCountTrapArg,
                    slotNumberTrapArg
                }
      STATUS  current
      DESCRIPTION "Severity    : critical 
                   Format      :  $1  $2  Mismatch. 
                   Childtraps  : 
                   Description : SFP Mismatch"
             ::= { alarmsAndEvents 0 10359 }

      trapSFPAutoProvMismatch NOTIFICATION-TYPE
      OBJECTS {
                    objectNameTrapArg,
                    lctNameTrapArg,
                    trapCountTrapArg,
                    slotNumberTrapArg
                }
      STATUS  current
      DESCRIPTION "Severity    : critical 
                   Format      :  $1  $2  Auto Provision Mismatch. 
                   Childtraps  : 
                   Description : SFP Auto Provision Mismatch"
             ::= { alarmsAndEvents 0 360 }

      trapSFPAutoProvMismatchClear NOTIFICATION-TYPE
      OBJECTS {
                    objectNameTrapArg,
                    lctNameTrapArg,
                    trapCountTrapArg,
                    slotNumberTrapArg
                }
      STATUS  current
      DESCRIPTION "Severity    : critical 
                   Format      :  $1  $2  Auto Provision Mismatch. 
                   Childtraps  : 
                   Description : SFP Auto Provision Mismatch"
             ::= { alarmsAndEvents 0 10360 }

      trapSFPRemoved NOTIFICATION-TYPE
      OBJECTS {
                    objectNameTrapArg,
                    lctNameTrapArg,
                    trapCountTrapArg,
                    slotNumberTrapArg
                }
      STATUS  current
      DESCRIPTION "Severity    : critical 
                   Format      :  $1  $2  missing or removed. 
                   Childtraps  : 
                   Description : SFP missing or removed"
             ::= { alarmsAndEvents 0 489 }

      trapSFPRemovedClear NOTIFICATION-TYPE
      OBJECTS {
                    objectNameTrapArg,
                    lctNameTrapArg,
                    trapCountTrapArg,
                    slotNumberTrapArg
                }
      STATUS  current
      DESCRIPTION "Severity    : critical 
                   Format      :  $1  $2  missing or removed. 
                   Childtraps  : 
                   Description : SFP missing or removed"
             ::= { alarmsAndEvents 0 10489 }

      trapSFPFailure NOTIFICATION-TYPE
      OBJECTS {
                    objectNameTrapArg,
                    lctNameTrapArg,
                    trapCountTrapArg,
                    slotNumberTrapArg
                }
      STATUS  current
      DESCRIPTION "Severity    : critical 
                   Format      :  $1  $2  Failed. 
                   Childtraps  : 
                   Description : SFP Failure"
             ::= { alarmsAndEvents 0 490 }

      trapSFPFailureClear NOTIFICATION-TYPE
      OBJECTS {
                    objectNameTrapArg,
                    lctNameTrapArg,
                    trapCountTrapArg,
                    slotNumberTrapArg
                }
      STATUS  current
      DESCRIPTION "Severity    : critical 
                   Format      :  $1  $2  Failed. 
                   Childtraps  : 
                   Description : SFP Failure"
             ::= { alarmsAndEvents 0 10490 }

      trapSFPUnknown NOTIFICATION-TYPE
      OBJECTS {
                    objectNameTrapArg,
                    lctNameTrapArg,
                    trapCountTrapArg,
                    slotNumberTrapArg
                }
      STATUS  current
      DESCRIPTION "Severity    : critical 
                   Format      :  $1  $2  Unknown. 
                   Childtraps  : 
                   Description : SFP Unknown"
             ::= { alarmsAndEvents 0 491 }

      trapSFPUnknownClear NOTIFICATION-TYPE
      OBJECTS {
                    objectNameTrapArg,
                    lctNameTrapArg,
                    trapCountTrapArg,
                    slotNumberTrapArg
                }
      STATUS  current
      DESCRIPTION "Severity    : critical 
                   Format      :  $1  $2  Unknown. 
                   Childtraps  : 
                   Description : SFP Unknown"
             ::= { alarmsAndEvents 0 10491 }

      trapSFPAccessFailure NOTIFICATION-TYPE
      OBJECTS {
                    objectNameTrapArg,
                    lctNameTrapArg,
                    trapCountTrapArg,
                    slotNumberTrapArg
                }
      STATUS  current
      DESCRIPTION "Severity    : zilch 
                   Format      :  $1  $2  SFP Access Failure. 
                   Childtraps  : 
                   Description : SFP Access Failure"
             ::= { alarmsAndEvents 0 732 }

      trapSTMLossOfSignal NOTIFICATION-TYPE
      OBJECTS {
                    objectNameTrapArg,
                    lctNameTrapArg,
                    trapCountTrapArg,
                    portNumberTrapArg
                }
      STATUS  current
      DESCRIPTION "Severity    : critical 
                   Format      :  $1 Loss of Signal on  $2 . 
                   Childtraps  : 
                   Description : Loss of Signal"
             ::= { alarmsAndEvents 0 27 }

      trapSTMLossOfSignalClear NOTIFICATION-TYPE
      OBJECTS {
                    objectNameTrapArg,
                    lctNameTrapArg,
                    trapCountTrapArg,
                    portNumberTrapArg
                }
      STATUS  current
      DESCRIPTION "Severity    : critical 
                   Format      :  $1 Loss of Signal on  $2 . 
                   Childtraps  : 
                   Description : Loss of Signal"
             ::= { alarmsAndEvents 0 10027 }

      trapSTMLossOfFrame NOTIFICATION-TYPE
      OBJECTS {
                    objectNameTrapArg,
                    lctNameTrapArg,
                    trapCountTrapArg,
                    portNumberTrapArg
                }
      STATUS  current
      DESCRIPTION "Severity    : critical 
                   Format      :  $1 Loss of Frame on  $2 . 
                   Childtraps  : 
                   Description : Loss Of Frame"
             ::= { alarmsAndEvents 0 28 }

      trapSTMLossOfFrameClear NOTIFICATION-TYPE
      OBJECTS {
                    objectNameTrapArg,
                    lctNameTrapArg,
                    trapCountTrapArg,
                    portNumberTrapArg
                }
      STATUS  current
      DESCRIPTION "Severity    : critical 
                   Format      :  $1 Loss of Frame on  $2 . 
                   Childtraps  : 
                   Description : Loss Of Frame"
             ::= { alarmsAndEvents 0 10028 }

      trapSTMOutOfFrame NOTIFICATION-TYPE
      OBJECTS {
                    objectNameTrapArg,
                    lctNameTrapArg,
                    trapCountTrapArg,
                    portNumberTrapArg
                }
      STATUS  current
      DESCRIPTION "Severity    : critical 
                   Format      :  $1 Out of Frame on  $2 . 
                   Childtraps  : 
                   Description : Out Of Frame"
             ::= { alarmsAndEvents 0 29 }

      trapSTMOutOfFrameClear NOTIFICATION-TYPE
      OBJECTS {
                    objectNameTrapArg,
                    lctNameTrapArg,
                    trapCountTrapArg,
                    portNumberTrapArg
                }
      STATUS  current
      DESCRIPTION "Severity    : critical 
                   Format      :  $1 Out of Frame on  $2 . 
                   Childtraps  : 
                   Description : Out Of Frame"
             ::= { alarmsAndEvents 0 10029 }

      trapSTMLineAis NOTIFICATION-TYPE
      OBJECTS {
                    objectNameTrapArg,
                    lctNameTrapArg,
                    trapCountTrapArg,
                    portNumberTrapArg
                }
      STATUS  current
      DESCRIPTION "Severity    : critical 
                   Format      : 
                   Childtraps  : 
                   Description : Alarm Indication Signal"
             ::= { alarmsAndEvents 0 30 }

      trapSTMLineAisClear NOTIFICATION-TYPE
      OBJECTS {
                    objectNameTrapArg,
                    lctNameTrapArg,
                    trapCountTrapArg,
                    portNumberTrapArg
                }
      STATUS  current
      DESCRIPTION "Severity    : critical 
                   Format      : 
                   Childtraps  : 
                   Description : Alarm Indication Signal"
             ::= { alarmsAndEvents 0 10030 }

      trapSTMLineRdi NOTIFICATION-TYPE
      OBJECTS {
                    objectNameTrapArg,
                    lctNameTrapArg,
                    trapCountTrapArg,
                    portNumberTrapArg
                }
      STATUS  current
      DESCRIPTION "Severity    : critical 
                   Format      : 
                   Childtraps  : 
                   Description : Remote Defect Indication"
             ::= { alarmsAndEvents 0 31 }

      trapSTMLineRdiClear NOTIFICATION-TYPE
      OBJECTS {
                    objectNameTrapArg,
                    lctNameTrapArg,
                    trapCountTrapArg,
                    portNumberTrapArg
                }
      STATUS  current
      DESCRIPTION "Severity    : critical 
                   Format      : 
                   Childtraps  : 
                   Description : Remote Defect Indication"
             ::= { alarmsAndEvents 0 10031 }

      trapSTMTraceIdMismatch NOTIFICATION-TYPE
      OBJECTS {
                    objectNameTrapArg,
                    lctNameTrapArg,
                    trapCountTrapArg,
                    portNumberTrapArg
                }
      STATUS  current
      DESCRIPTION "Severity    : major 
                   Format      : 
                   Childtraps  : 
                   Description : Trace Identifier Mismatch"
             ::= { alarmsAndEvents 0 52 }

      trapSTMTraceIdMismatchClear NOTIFICATION-TYPE
      OBJECTS {
                    objectNameTrapArg,
                    lctNameTrapArg,
                    trapCountTrapArg,
                    portNumberTrapArg
                }
      STATUS  current
      DESCRIPTION "Severity    : major 
                   Format      : 
                   Childtraps  : 
                   Description : Trace Identifier Mismatch"
             ::= { alarmsAndEvents 0 10052 }

      trapTcaStmSectionES NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      :  $1 TCA:ES-S on  $2  for  $3  
                   interval 
                   Childtraps  : 
                   Description : TCA: Errored Seconds - Section"
             ::= { tcas 0 53 }

      trapTcaStmSectionSES NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      :  $1 TCA:SES-S on  $2  for  $3  
                   interval. 
                   Childtraps  : 
                   Description : TCA: Severely Errored Seconds - 
                   Section"
             ::= { tcas 0 54 }

      trapTcaStmSectionCV NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      : 
                   Childtraps  : 
                   Description : TCA: Code Violations - Section"
             ::= { tcas 0 55 }

      trapTcaStmSectionSEFS NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      :  $1 TCA:SEFS-S on  $2  for  $3  
                   interval. 
                   Childtraps  : 
                   Description : TCA: Severely Errored Frame Seconds 
                   - Section"
             ::= { tcas 0 59 }

      trapTcaStmLineES NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      :  $1 TCA:ES-L on  $2  for  $3  
                   interval. 
                   Childtraps  : 
                   Description : TCA: Errored Seconds - Line"
             ::= { tcas 0 60 }

      trapTcaStmLineSES NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      :  $1 TCA:SES-L on  $2  for  $3  
                   interval. 
                   Childtraps  : 
                   Description : TCA: Severely Errored Seconds - 
                   Line"
             ::= { tcas 0 61 }

      trapTcaStmLineCV NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      : 
                   Childtraps  : 
                   Description : TCA: Code Violations - Line"
             ::= { tcas 0 62 }

      trapSignalFail NOTIFICATION-TYPE
      OBJECTS {
                    objectNameTrapArg,
                    lctNameTrapArg,
                    trapCountTrapArg,
                    portNumberTrapArg
                }
      STATUS  current
      DESCRIPTION "Severity    : major 
                   Format      :  $1 Line Signal Fail on  $2 . 
                   Childtraps  : 
                   Description : BER Threshold exceeded for Signal 
                   Failure"
             ::= { alarmsAndEvents 0 115 }

      trapSignalFailClear NOTIFICATION-TYPE
      OBJECTS {
                    objectNameTrapArg,
                    lctNameTrapArg,
                    trapCountTrapArg,
                    portNumberTrapArg
                }
      STATUS  current
      DESCRIPTION "Severity    : major 
                   Format      :  $1 Line Signal Fail on  $2 . 
                   Childtraps  : 
                   Description : BER Threshold exceeded for Signal 
                   Failure"
             ::= { alarmsAndEvents 0 10115 }

      trapPortUnavailablePeriodStarted NOTIFICATION-TYPE
      OBJECTS {
                    objectNameTrapArg,
                    lctNameTrapArg,
                    trapCountTrapArg
                }
      STATUS  current
      DESCRIPTION "Severity    : major 
                   Format      :  $1 Start of Unavailability Period 
                   on  $2  at  $3  level. 
                   Childtraps  : 
                   Description : Start of Unavailability Period"
             ::= { alarmsAndEvents 0 324 }

      trapPortUnavailablePeriodEnded NOTIFICATION-TYPE
      OBJECTS {
                    objectNameTrapArg,
                    lctNameTrapArg,
                    trapCountTrapArg
                }
      STATUS  current
      DESCRIPTION "Severity    : major 
                   Format      :  $1 End of Unavailability Period on 
                    $2  at  $3  level. 
                   Childtraps  : 
                   Description : End of Unavailability Period"
             ::= { alarmsAndEvents 0 325 }

      trapSignalDegrade NOTIFICATION-TYPE
      OBJECTS {
                    objectNameTrapArg,
                    lctNameTrapArg,
                    trapCountTrapArg,
                    portNumberTrapArg
                }
      STATUS  current
      DESCRIPTION "Severity    : major 
                   Format      :  $1 Line Signal Degrade on  $2 . 
                   Childtraps  : 
                   Description : BER Threshold exceeded for Signal 
                   Degrade"
             ::= { alarmsAndEvents 0 381 }

      trapSignalDegradeClear NOTIFICATION-TYPE
      OBJECTS {
                    objectNameTrapArg,
                    lctNameTrapArg,
                    trapCountTrapArg,
                    portNumberTrapArg
                }
      STATUS  current
      DESCRIPTION "Severity    : major 
                   Format      :  $1 Line Signal Degrade on  $2 . 
                   Childtraps  : 
                   Description : BER Threshold exceeded for Signal 
                   Degrade"
             ::= { alarmsAndEvents 0 10381 }

      trapPPAutomaticSwitchToPort NOTIFICATION-TYPE
      OBJECTS {
                    objectNameTrapArg,
                    lctNameTrapArg,
                    trapCountTrapArg
                }
      STATUS  current
      DESCRIPTION "Severity    : zilch 
                   Format      :  $1 Non Revertive switch from port  
                   $2 . 
                   Childtraps  : 
                   Description : Protection Switch Complete"
             ::= { alarmsAndEvents 0 435 }

      trapPPLockOutofProtection NOTIFICATION-TYPE
      OBJECTS {
                    objectNameTrapArg,
                    lctNameTrapArg,
                    trapCountTrapArg
                }
      STATUS  current
      DESCRIPTION "Severity    : minor 
                   Format      :  $1 Lockout of protection, switch 
                   from the protect port  $2 . 
                   Childtraps  : 
                   Description : Lockout Active"
             ::= { alarmsAndEvents 0 436 }

      trapPPLockOutofProtectionClear NOTIFICATION-TYPE
      OBJECTS {
                    objectNameTrapArg,
                    lctNameTrapArg,
                    trapCountTrapArg
                }
      STATUS  current
      DESCRIPTION "Severity    : minor 
                   Format      :  $1 Lockout of protection, switch 
                   from the protect port  $2 . 
                   Childtraps  : 
                   Description : Lockout Active"
             ::= { alarmsAndEvents 0 10436 }

      trapPPForcedSwitchToPort NOTIFICATION-TYPE
      OBJECTS {
                    objectNameTrapArg,
                    lctNameTrapArg,
                    trapCountTrapArg
                }
      STATUS  current
      DESCRIPTION "Severity    : minor 
                   Format      :  $1 Forced switch from port  $2 . 
                   Childtraps  : 
                   Description : Forced Switch Active"
             ::= { alarmsAndEvents 0 437 }

      trapPPForcedSwitchToPortClear NOTIFICATION-TYPE
      OBJECTS {
                    objectNameTrapArg,
                    lctNameTrapArg,
                    trapCountTrapArg
                }
      STATUS  current
      DESCRIPTION "Severity    : minor 
                   Format      :  $1 Forced switch from port  $2 . 
                   Childtraps  : 
                   Description : Forced Switch Active"
             ::= { alarmsAndEvents 0 10437 }

      trapPPManualSwitchToPort NOTIFICATION-TYPE
      OBJECTS {
                    objectNameTrapArg,
                    lctNameTrapArg,
                    trapCountTrapArg
                }
      STATUS  current
      DESCRIPTION "Severity    : minor 
                   Format      :  $1 Manual switch from port  $2 . 
                   Childtraps  : 
                   Description : Manual Switch Active"
             ::= { alarmsAndEvents 0 438 }

      trapPPManualSwitchToPortClear NOTIFICATION-TYPE
      OBJECTS {
                    objectNameTrapArg,
                    lctNameTrapArg,
                    trapCountTrapArg
                }
      STATUS  current
      DESCRIPTION "Severity    : minor 
                   Format      :  $1 Manual switch from port  $2 . 
                   Childtraps  : 
                   Description : Manual Switch Active"
             ::= { alarmsAndEvents 0 10438 }

      trapPPRevertToWork NOTIFICATION-TYPE
      OBJECTS {
                    objectNameTrapArg,
                    lctNameTrapArg,
                    trapCountTrapArg
                }
      STATUS  current
      DESCRIPTION "Severity    : warning 
                   Format      :  $1 Revertive switch from port  $2  
                   complete. 
                   Childtraps  : 
                   Description : Protection Switch Active"
             ::= { alarmsAndEvents 0 439 }

      trapPPRevertToWorkClear NOTIFICATION-TYPE
      OBJECTS {
                    objectNameTrapArg,
                    lctNameTrapArg,
                    trapCountTrapArg
                }
      STATUS  current
      DESCRIPTION "Severity    : warning 
                   Format      :  $1 Revertive switch from port  $2  
                   complete. 
                   Childtraps  : 
                   Description : Protection Switch Active"
             ::= { alarmsAndEvents 0 10439 }

      trapPPManualSwitchFailed NOTIFICATION-TYPE
      OBJECTS {
                    objectNameTrapArg,
                    lctNameTrapArg,
                    trapCountTrapArg
                }
      STATUS  current
      DESCRIPTION "Severity    : zilch 
                   Format      :  $1 Manual switch failed on  $2 . 
                   Childtraps  : 
                   Description : Manual Switch Fail"
             ::= { alarmsAndEvents 0 440 }

      trapPPModeMismatchFailure NOTIFICATION-TYPE
      OBJECTS {
                    objectNameTrapArg,
                    lctNameTrapArg,
                    trapCountTrapArg
                }
      STATUS  current
      DESCRIPTION "Severity    : minor 
                   Format      :  $1 APS/MSP Mode mismatch failure 
                   on  $2 . 
                   Childtraps  : 
                   Description : Protection Mode Mismatch"
             ::= { alarmsAndEvents 0 441 }

      trapPPModeMismatchFailureClear NOTIFICATION-TYPE
      OBJECTS {
                    objectNameTrapArg,
                    lctNameTrapArg,
                    trapCountTrapArg
                }
      STATUS  current
      DESCRIPTION "Severity    : minor 
                   Format      :  $1 APS/MSP Mode mismatch failure 
                   on  $2 . 
                   Childtraps  : 
                   Description : Protection Mode Mismatch"
             ::= { alarmsAndEvents 0 10441 }

      trapPPChannelMismatchFailure NOTIFICATION-TYPE
      OBJECTS {
                    objectNameTrapArg,
                    lctNameTrapArg,
                    trapCountTrapArg
                }
      STATUS  current
      DESCRIPTION "Severity    : minor 
                   Format      :  $1 APS/MSP Channel mismatch 
                   failure on  $2 . 
                   Childtraps  : 
                   Description : Protection Channel Match Fail"
             ::= { alarmsAndEvents 0 442 }

      trapPPChannelMismatchFailureClear NOTIFICATION-TYPE
      OBJECTS {
                    objectNameTrapArg,
                    lctNameTrapArg,
                    trapCountTrapArg
                }
      STATUS  current
      DESCRIPTION "Severity    : minor 
                   Format      :  $1 APS/MSP Channel mismatch 
                   failure on  $2 . 
                   Childtraps  : 
                   Description : Protection Channel Match Fail"
             ::= { alarmsAndEvents 0 10442 }

      trapPPProtectSwitchByteFailure NOTIFICATION-TYPE
      OBJECTS {
                    objectNameTrapArg,
                    lctNameTrapArg,
                    trapCountTrapArg
                }
      STATUS  current
      DESCRIPTION "Severity    : minor 
                   Format      :  $1 APS/MSP Protect Switch Byte 
                   failure on  $2 . 
                   Childtraps  : 
                   Description : Protection Switch Byte Fail"
             ::= { alarmsAndEvents 0 443 }

      trapPPProtectSwitchByteFailureClear NOTIFICATION-TYPE
      OBJECTS {
                    objectNameTrapArg,
                    lctNameTrapArg,
                    trapCountTrapArg
                }
      STATUS  current
      DESCRIPTION "Severity    : minor 
                   Format      :  $1 APS/MSP Protect Switch Byte 
                   failure on  $2 . 
                   Childtraps  : 
                   Description : Protection Switch Byte Fail"
             ::= { alarmsAndEvents 0 10443 }

      trapPPFarEndProtectLineFailure NOTIFICATION-TYPE
      OBJECTS {
                    objectNameTrapArg,
                    lctNameTrapArg,
                    trapCountTrapArg
                }
      STATUS  current
      DESCRIPTION "Severity    : major 
                   Format      :  $1 APS/MSP Far End Protect Line 
                   failure on  $2 . 
                   Childtraps  : 
                   Description : Far End Protection Line Fail"
             ::= { alarmsAndEvents 0 444 }

      trapPPFarEndProtectLineFailureClear NOTIFICATION-TYPE
      OBJECTS {
                    objectNameTrapArg,
                    lctNameTrapArg,
                    trapCountTrapArg
                }
      STATUS  current
      DESCRIPTION "Severity    : major 
                   Format      :  $1 APS/MSP Far End Protect Line 
                   failure on  $2 . 
                   Childtraps  : 
                   Description : Far End Protection Line Fail"
             ::= { alarmsAndEvents 0 10444 }

      trapSectionSignalFail NOTIFICATION-TYPE
      OBJECTS {
                    objectNameTrapArg,
                    lctNameTrapArg,
                    trapCountTrapArg,
                    portNumberTrapArg
                }
      STATUS  current
      DESCRIPTION "Severity    : major 
                   Format      :  $1 Section Signal Fail on  $2 . 
                   Childtraps  : 
                   Description : BER Threshold exceeded on Section 
                   for Signal Failure"
             ::= { alarmsAndEvents 0 479 }

      trapSectionSignalFailClear NOTIFICATION-TYPE
      OBJECTS {
                    objectNameTrapArg,
                    lctNameTrapArg,
                    trapCountTrapArg,
                    portNumberTrapArg
                }
      STATUS  current
      DESCRIPTION "Severity    : major 
                   Format      :  $1 Section Signal Fail on  $2 . 
                   Childtraps  : 
                   Description : BER Threshold exceeded on Section 
                   for Signal Failure"
             ::= { alarmsAndEvents 0 10479 }

      trapSectionSignalDegrade NOTIFICATION-TYPE
      OBJECTS {
                    objectNameTrapArg,
                    lctNameTrapArg,
                    trapCountTrapArg,
                    portNumberTrapArg
                }
      STATUS  current
      DESCRIPTION "Severity    : major 
                   Childtraps  : 
                   Description : BER Threshold exceeded on Section 
                   for Signal Degrade"
             ::= { alarmsAndEvents 0 480 }

      trapSectionSignalDegradeClear NOTIFICATION-TYPE
      OBJECTS {
                    objectNameTrapArg,
                    lctNameTrapArg,
                    trapCountTrapArg,
                    portNumberTrapArg
                }
      STATUS  current
      DESCRIPTION "Severity    : major 
                   Childtraps  : 
                   Description : BER Threshold exceeded on Section 
                   for Signal Degrade"
             ::= { alarmsAndEvents 0 10480 }

      trapRemoteSignalFail NOTIFICATION-TYPE
      OBJECTS {
                    objectNameTrapArg,
                    lctNameTrapArg,
                    trapCountTrapArg,
                    portNumberTrapArg
                }
      STATUS  current
      DESCRIPTION "Severity    : major 
                   Format      :  $1 Section Signal Fail on  $2 . 
                   Childtraps  : 
                   Description : BER Threshold exceeded on Far End 
                   Line for Signal Failure"
             ::= { alarmsAndEvents 0 481 }

      trapRemoteSignalFailClear NOTIFICATION-TYPE
      OBJECTS {
                    objectNameTrapArg,
                    lctNameTrapArg,
                    trapCountTrapArg,
                    portNumberTrapArg
                }
      STATUS  current
      DESCRIPTION "Severity    : major 
                   Format      :  $1 Section Signal Fail on  $2 . 
                   Childtraps  : 
                   Description : BER Threshold exceeded on Far End 
                   Line for Signal Failure"
             ::= { alarmsAndEvents 0 10481 }

      trapRemoteSignalDegrade NOTIFICATION-TYPE
      OBJECTS {
                    objectNameTrapArg,
                    lctNameTrapArg,
                    trapCountTrapArg,
                    portNumberTrapArg
                }
      STATUS  current
      DESCRIPTION "Severity    : major 
                   Format      :  $1 Line REI Signal Degrade on  $2 
                   . 
                   Childtraps  : 
                   Description : BER Threshold exceeded on Far End 
                   Line for Signal Degrade"
             ::= { alarmsAndEvents 0 482 }

      trapRemoteSignalDegradeClear NOTIFICATION-TYPE
      OBJECTS {
                    objectNameTrapArg,
                    lctNameTrapArg,
                    trapCountTrapArg,
                    portNumberTrapArg
                }
      STATUS  current
      DESCRIPTION "Severity    : major 
                   Format      :  $1 Line REI Signal Degrade on  $2 
                   . 
                   Childtraps  : 
                   Description : BER Threshold exceeded on Far End 
                   Line for Signal Degrade"
             ::= { alarmsAndEvents 0 10482 }

      trapBlsrManualSwitch NOTIFICATION-TYPE
      OBJECTS {
                    objectNameTrapArg,
                    lctNameTrapArg,
                    trapCountTrapArg
                }
      STATUS  current
      DESCRIPTION "Severity    : minor 
                   Format      :  $1 Manual Switch Active on  $2 . 
                   Childtraps  : 
                   Description : Manual Switch Active"
             ::= { alarmsAndEvents 0 670 }

      trapBlsrManualSwitchClear NOTIFICATION-TYPE
      OBJECTS {
                    objectNameTrapArg,
                    lctNameTrapArg,
                    trapCountTrapArg
                }
      STATUS  current
      DESCRIPTION "Severity    : minor 
                   Format      :  $1 Manual Switch Active on  $2 . 
                   Childtraps  : 
                   Description : Manual Switch Active"
             ::= { alarmsAndEvents 0 10670 }

      trapBlsrForceSwitch NOTIFICATION-TYPE
      OBJECTS {
                    objectNameTrapArg,
                    lctNameTrapArg,
                    trapCountTrapArg
                }
      STATUS  current
      DESCRIPTION "Severity    : minor 
                   Format      :  $1 Forced Switch Active On  $2 . 
                   Childtraps  : 
                   Description : Forced Switch Active"
             ::= { alarmsAndEvents 0 671 }

      trapBlsrForceSwitchClear NOTIFICATION-TYPE
      OBJECTS {
                    objectNameTrapArg,
                    lctNameTrapArg,
                    trapCountTrapArg
                }
      STATUS  current
      DESCRIPTION "Severity    : minor 
                   Format      :  $1 Forced Switch Active On  $2 . 
                   Childtraps  : 
                   Description : Forced Switch Active"
             ::= { alarmsAndEvents 0 10671 }

      trapBlsrRingSwitch NOTIFICATION-TYPE
      OBJECTS {
                    objectNameTrapArg,
                    lctNameTrapArg,
                    trapCountTrapArg
                }
      STATUS  current
      DESCRIPTION "Severity    : major 
                   Format      :  $1 Ring Switch on  $2 . 
                   Childtraps  : 
                   Description : Ring Switch Active"
             ::= { alarmsAndEvents 0 672 }

      trapBlsrRingSwitchClear NOTIFICATION-TYPE
      OBJECTS {
                    objectNameTrapArg,
                    lctNameTrapArg,
                    trapCountTrapArg
                }
      STATUS  current
      DESCRIPTION "Severity    : major 
                   Format      :  $1 Ring Switch on  $2 . 
                   Childtraps  : 
                   Description : Ring Switch Active"
             ::= { alarmsAndEvents 0 10672 }

      trapBlsrInvalidKByte NOTIFICATION-TYPE
      OBJECTS {
                    objectNameTrapArg,
                    lctNameTrapArg,
                    trapCountTrapArg
                }
      STATUS  current
      DESCRIPTION "Severity    : major 
                   Format      :  $1 Invalid K byte on  $2 . 
                   Childtraps  : 
                   Description : Invalid Kbyte"
             ::= { alarmsAndEvents 0 673 }

      trapBlsrInvalidKByteClear NOTIFICATION-TYPE
      OBJECTS {
                    objectNameTrapArg,
                    lctNameTrapArg,
                    trapCountTrapArg
                }
      STATUS  current
      DESCRIPTION "Severity    : major 
                   Format      :  $1 Invalid K byte on  $2 . 
                   Childtraps  : 
                   Description : Invalid Kbyte"
             ::= { alarmsAndEvents 0 10673 }

      trapBlsrExerciserFailed NOTIFICATION-TYPE
      OBJECTS {
                    objectNameTrapArg,
                    lctNameTrapArg,
                    trapCountTrapArg
                }
      STATUS  current
      DESCRIPTION "Severity    : zilch 
                   Format      :  $1 Protection Exerciser Failed On  
                   $2 . 
                   Childtraps  : 
                   Description : Protection Exerciser Failed"
             ::= { alarmsAndEvents 0 674 }

      trapBlsrExerciserSuccess NOTIFICATION-TYPE
      OBJECTS {
                    objectNameTrapArg,
                    lctNameTrapArg,
                    trapCountTrapArg
                }
      STATUS  current
      DESCRIPTION "Severity    : zilch 
                   Format      :  $1 Protection Exerciser Complete 
                   On  $2 . 
                   Childtraps  : 
                   Description : Protection Exerciser Complete"
             ::= { alarmsAndEvents 0 675 }

      trapBlsrLockOutOfProtection NOTIFICATION-TYPE
      OBJECTS {
                    objectNameTrapArg,
                    lctNameTrapArg,
                    trapCountTrapArg
                }
      STATUS  current
      DESCRIPTION "Severity    : minor 
                   Format      :  $1 Lockout Protection Active On  
                   $2 . 
                   Childtraps  : 
                   Description : Lockout Protection Active"
             ::= { alarmsAndEvents 0 683 }

      trapBlsrLockOutOfProtectionClear NOTIFICATION-TYPE
      OBJECTS {
                    objectNameTrapArg,
                    lctNameTrapArg,
                    trapCountTrapArg
                }
      STATUS  current
      DESCRIPTION "Severity    : minor 
                   Format      :  $1 Lockout Protection Active On  
                   $2 . 
                   Childtraps  : 
                   Description : Lockout Protection Active"
             ::= { alarmsAndEvents 0 10683 }

      trapCFMLOC NOTIFICATION-TYPE
      OBJECTS {
                    objectNameTrapArg,
                    lctNameTrapArg,
                    trapCountTrapArg
                }
      STATUS  current
      DESCRIPTION "Severity    : major 
                   Format      :  $1 The MEP has lost connectivity 
                   to some other MEP in the MA 
                   Childtraps  : 
                   Description : The MEP has lost connectivity to 
                   some other MEP in the MA"
             ::= { alarmsAndEvents 0 612 }

      trapCFMLOCClear NOTIFICATION-TYPE
      OBJECTS {
                    objectNameTrapArg,
                    lctNameTrapArg,
                    trapCountTrapArg
                }
      STATUS  current
      DESCRIPTION "Severity    : major 
                   Format      :  $1 The MEP has lost connectivity 
                   to some other MEP in the MA 
                   Childtraps  : 
                   Description : The MEP has lost connectivity to 
                   some other MEP in the MA"
             ::= { alarmsAndEvents 0 10612 }

      trapCFMLoop NOTIFICATION-TYPE
      OBJECTS {
                    objectNameTrapArg,
                    lctNameTrapArg,
                    trapCountTrapArg
                }
      STATUS  current
      DESCRIPTION "Severity    : major 
                   Format      :  $1 The MEP has detected a loop in 
                   the network 
                   Childtraps  : 
                   Description : The MEP has detected a loop in the 
                   network"
             ::= { alarmsAndEvents 0 613 }

      trapCFMLoopClear NOTIFICATION-TYPE
      OBJECTS {
                    objectNameTrapArg,
                    lctNameTrapArg,
                    trapCountTrapArg
                }
      STATUS  current
      DESCRIPTION "Severity    : major 
                   Format      :  $1 The MEP has detected a loop in 
                   the network 
                   Childtraps  : 
                   Description : The MEP has detected a loop in the 
                   network"
             ::= { alarmsAndEvents 0 10613 }

      trapTcaStmPathES NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      : 
                   Childtraps  : 
                   Description : TCA: Errored Seconds - Path"
             ::= { tcas 0 215 }

      trapTcaStmPathSES NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      : 
                   Childtraps  : 
                   Description : TCA: Severely Errored Seconds - 
                   Path"
             ::= { tcas 0 216 }

      trapTcaStmPathCV NOTIFICATION-TYPE
      OBJECTS {
                    objectNameTrapArg,
                    lctNameTrapArg,
                    trapCountTrapArg,
                    tcaMonTypeTrapArg,
                    tcaMonValTrapArg,
                    tcaThValTrapArg,
                    tcaDurationTrapArg
                }
      STATUS  current
      DESCRIPTION "Severity    : zilch 
                   Format      : 
                   Childtraps  : 
                   Description : TCA: Code Violations - Path"
             ::= { tcas 0 217 }

      trapPathUnavailablePeriodStarted NOTIFICATION-TYPE
      OBJECTS {
                    objectNameTrapArg,
                    lctNameTrapArg,
                    trapCountTrapArg
                }
      STATUS  current
      DESCRIPTION "Severity    : major 
                   Format      :  $1 Start of Unavailability Period 
                   on  $2 . 
                   Childtraps  : 
                   Description : Start of Unavailability Period"
             ::= { alarmsAndEvents 0 326 }

      trapPathUnavailablePeriodEnded NOTIFICATION-TYPE
      OBJECTS {
                    objectNameTrapArg,
                    lctNameTrapArg,
                    trapCountTrapArg
                }
      STATUS  current
      DESCRIPTION "Severity    : major 
                   Format      :  $1 End of Unavailability Period on 
                    $2 . 
                   Childtraps  : 
                   Description : End of Unavailability Period"
             ::= { alarmsAndEvents 0 327 }

      trapPayloadClientPRBSActive NOTIFICATION-TYPE
      OBJECTS {
                    objectNameTrapArg,
                    lctNameTrapArg,
                    trapCountTrapArg
                }
      STATUS  current
      DESCRIPTION "Severity    : warning 
                   Format      :  $1 Client Side PRBS Active 
                   Childtraps  : 
                   Description : Client Side PRBS Active"
             ::= { alarmsAndEvents 0 530 }

      trapPayloadClientPRBSActiveClear NOTIFICATION-TYPE
      OBJECTS {
                    objectNameTrapArg,
                    lctNameTrapArg,
                    trapCountTrapArg
                }
      STATUS  current
      DESCRIPTION "Severity    : warning 
                   Format      :  $1 Client Side PRBS Active 
                   Childtraps  : 
                   Description : Client Side PRBS Active"
             ::= { alarmsAndEvents 0 10530 }

      trapPayloadNetworkPRBSActive NOTIFICATION-TYPE
      OBJECTS {
                    objectNameTrapArg,
                    lctNameTrapArg,
                    trapCountTrapArg
                }
      STATUS  current
      DESCRIPTION "Severity    : warning 
                   Format      :  $1 Network side PRBS active 
                   Childtraps  : 
                   Description : Network side PRBS active"
             ::= { alarmsAndEvents 0 531 }

      trapPayloadNetworkPRBSActiveClear NOTIFICATION-TYPE
      OBJECTS {
                    objectNameTrapArg,
                    lctNameTrapArg,
                    trapCountTrapArg
                }
      STATUS  current
      DESCRIPTION "Severity    : warning 
                   Format      :  $1 Network side PRBS active 
                   Childtraps  : 
                   Description : Network side PRBS active"
             ::= { alarmsAndEvents 0 10531 }

      trapPayloadLossPRBSSync NOTIFICATION-TYPE
      OBJECTS {
                    objectNameTrapArg,
                    lctNameTrapArg,
                    trapCountTrapArg
                }
      STATUS  current
      DESCRIPTION "Severity    : warning 
                   Format      :  $1 Loss of PRBS Synchronization 
                   Childtraps  : 
                   Description : Loss of PRBS Synchronization"
             ::= { alarmsAndEvents 0 532 }

      trapPayloadLossPRBSSyncClear NOTIFICATION-TYPE
      OBJECTS {
                    objectNameTrapArg,
                    lctNameTrapArg,
                    trapCountTrapArg
                }
      STATUS  current
      DESCRIPTION "Severity    : warning 
                   Format      :  $1 Loss of PRBS Synchronization 
                   Childtraps  : 
                   Description : Loss of PRBS Synchronization"
             ::= { alarmsAndEvents 0 10532 }

      trapPathFacilityLoopbackActive NOTIFICATION-TYPE
      OBJECTS {
                    objectNameTrapArg,
                    lctNameTrapArg,
                    trapCountTrapArg
                }
      STATUS  current
      DESCRIPTION "Severity    : minor 
                   Format      :  $1 Loopback Active - Facility 
                   Childtraps  : 
                   Description : Loopback Active - Facility"
             ::= { alarmsAndEvents 0 699 }

      trapPathFacilityLoopbackActiveClear NOTIFICATION-TYPE
      OBJECTS {
                    objectNameTrapArg,
                    lctNameTrapArg,
                    trapCountTrapArg
                }
      STATUS  current
      DESCRIPTION "Severity    : minor 
                   Format      :  $1 Loopback Active - Facility 
                   Childtraps  : 
                   Description : Loopback Active - Facility"
             ::= { alarmsAndEvents 0 10699 }

      trapPathTerminalLoopbackActive NOTIFICATION-TYPE
      OBJECTS {
                    objectNameTrapArg,
                    lctNameTrapArg,
                    trapCountTrapArg
                }
      STATUS  current
      DESCRIPTION "Severity    : minor 
                   Format      :  $1 Loopback Active - Terminal: 
                   Childtraps  : 
                   Description : Loopback Active - Terminal"
             ::= { alarmsAndEvents 0 700 }

      trapPathTerminalLoopbackActiveClear NOTIFICATION-TYPE
      OBJECTS {
                    objectNameTrapArg,
                    lctNameTrapArg,
                    trapCountTrapArg
                }
      STATUS  current
      DESCRIPTION "Severity    : minor 
                   Format      :  $1 Loopback Active - Terminal: 
                   Childtraps  : 
                   Description : Loopback Active - Terminal"
             ::= { alarmsAndEvents 0 10700 }

      trapAutomaticSwitchToProtect NOTIFICATION-TYPE
      OBJECTS {
                    objectNameTrapArg,
                    lctNameTrapArg,
                    trapCountTrapArg
                }
      STATUS  current
      DESCRIPTION "Severity    : zilch 
                   Format      :  $1 Automatic switch to the protect 
                   port on MSP/APS Group  $2 . 
                   Childtraps  : 
                   Description : Switch to protect port"
             ::= { alarmsAndEvents 0 228 }

      trapAutomaticSwitchToWork NOTIFICATION-TYPE
      OBJECTS {
                    objectNameTrapArg,
                    lctNameTrapArg,
                    trapCountTrapArg
                }
      STATUS  current
      DESCRIPTION "Severity    : zilch 
                   Format      :  $1 Automatic switch to the work 
                   port on MSP/APS Group  $2 . 
                   Childtraps  : 
                   Description : Switch to work port"
             ::= { alarmsAndEvents 0 229 }

      trapRevertToWork NOTIFICATION-TYPE
      OBJECTS {
                    objectNameTrapArg,
                    lctNameTrapArg,
                    trapCountTrapArg
                }
      STATUS  current
      DESCRIPTION "Severity    : zilch 
                   Format      :  $1 Revert to the work protect on 
                   MSP/APS Group  $2  complete. 
                   Childtraps  : 
                   Description : Revert to the work port"
             ::= { alarmsAndEvents 0 230 }

      trapManualSwitchFailed NOTIFICATION-TYPE
      OBJECTS {
                    objectNameTrapArg,
                    lctNameTrapArg,
                    trapCountTrapArg
                }
      STATUS  current
      DESCRIPTION "Severity    : zilch 
                   Format      :  $1 Manual switch failed on MSP/APS 
                   Group  $2 . 
                   Childtraps  : 
                   Description : Manual switch failed"
             ::= { alarmsAndEvents 0 231 }

      trapModeMismatchFailure NOTIFICATION-TYPE
      OBJECTS {
                    objectNameTrapArg,
                    lctNameTrapArg,
                    trapCountTrapArg
                }
      STATUS  current
      DESCRIPTION "Severity    : minor 
                   Format      :  $1 APS/MSP Mode mismatch failure 
                   on  $2 . 
                   Childtraps  : 
                   Description : APS/MSP Mode mismatch failure."
             ::= { alarmsAndEvents 0 314 }

      trapModeMismatchFailureClear NOTIFICATION-TYPE
      OBJECTS {
                    objectNameTrapArg,
                    lctNameTrapArg,
                    trapCountTrapArg
                }
      STATUS  current
      DESCRIPTION "Severity    : minor 
                   Format      :  $1 APS/MSP Mode mismatch failure 
                   on  $2 . 
                   Childtraps  : 
                   Description : APS/MSP Mode mismatch failure."
             ::= { alarmsAndEvents 0 10314 }

      trapChannelMismatchFailure NOTIFICATION-TYPE
      OBJECTS {
                    objectNameTrapArg,
                    lctNameTrapArg,
                    trapCountTrapArg
                }
      STATUS  current
      DESCRIPTION "Severity    : minor 
                   Format      :  $1 APS/MSP Channel mismatch 
                   failure on  $2 . 
                   Childtraps  : 
                   Description : APS/MSP Channel mismatch failure."
             ::= { alarmsAndEvents 0 315 }

      trapChannelMismatchFailureClear NOTIFICATION-TYPE
      OBJECTS {
                    objectNameTrapArg,
                    lctNameTrapArg,
                    trapCountTrapArg
                }
      STATUS  current
      DESCRIPTION "Severity    : minor 
                   Format      :  $1 APS/MSP Channel mismatch 
                   failure on  $2 . 
                   Childtraps  : 
                   Description : APS/MSP Channel mismatch failure."
             ::= { alarmsAndEvents 0 10315 }

      trapProtectSwitchByteFailure NOTIFICATION-TYPE
      OBJECTS {
                    objectNameTrapArg,
                    lctNameTrapArg,
                    trapCountTrapArg
                }
      STATUS  current
      DESCRIPTION "Severity    : minor 
                   Format      :  $1 APS/MSP Protect Switch Byte 
                   failure on  $2 . 
                   Childtraps  : 
                   Description : APS/MSP Protect Switch Byte 
                   failure."
             ::= { alarmsAndEvents 0 316 }

      trapProtectSwitchByteFailureClear NOTIFICATION-TYPE
      OBJECTS {
                    objectNameTrapArg,
                    lctNameTrapArg,
                    trapCountTrapArg
                }
      STATUS  current
      DESCRIPTION "Severity    : minor 
                   Format      :  $1 APS/MSP Protect Switch Byte 
                   failure on  $2 . 
                   Childtraps  : 
                   Description : APS/MSP Protect Switch Byte 
                   failure."
             ::= { alarmsAndEvents 0 10316 }

      trapFarEndProtectLineFailure NOTIFICATION-TYPE
      OBJECTS {
                    objectNameTrapArg,
                    lctNameTrapArg,
                    trapCountTrapArg
                }
      STATUS  current
      DESCRIPTION "Severity    : minor 
                   Format      :  $1 APS/MSP Far End Protect Line 
                   failure on  $2 . 
                   Childtraps  : 
                   Description : APS/MSP Far End Protect Line 
                   failure."
             ::= { alarmsAndEvents 0 317 }

      trapFarEndProtectLineFailureClear NOTIFICATION-TYPE
      OBJECTS {
                    objectNameTrapArg,
                    lctNameTrapArg,
                    trapCountTrapArg
                }
      STATUS  current
      DESCRIPTION "Severity    : minor 
                   Format      :  $1 APS/MSP Far End Protect Line 
                   failure on  $2 . 
                   Childtraps  : 
                   Description : APS/MSP Far End Protect Line 
                   failure."
             ::= { alarmsAndEvents 0 10317 }

      trapLockOutofProtection NOTIFICATION-TYPE
      OBJECTS {
                    objectNameTrapArg,
                    lctNameTrapArg,
                    trapCountTrapArg
                }
      STATUS  current
      DESCRIPTION "Severity    : zilch 
                   Format      :  $1 Lockout of protection, switch 
                   to the work port on MSP/APS Group  $2 . 
                   Childtraps  : 
                   Description : APS/MSP Lockout of protection"
             ::= { alarmsAndEvents 0 338 }

      trapForcedSwitchToProtect NOTIFICATION-TYPE
      OBJECTS {
                    objectNameTrapArg,
                    lctNameTrapArg,
                    trapCountTrapArg
                }
      STATUS  current
      DESCRIPTION "Severity    : zilch 
                   Format      :  $1 Forced switch to the protect 
                   port on MSP/APS Group  $2 . 
                   Childtraps  : 
                   Description : APS/MSP Forced Switch to protect 
                   port"
             ::= { alarmsAndEvents 0 339 }

      trapForcedSwitchToWork NOTIFICATION-TYPE
      OBJECTS {
                    objectNameTrapArg,
                    lctNameTrapArg,
                    trapCountTrapArg
                }
      STATUS  current
      DESCRIPTION "Severity    : zilch 
                   Format      :  $1 Forced switch to the work  port 
                   on MSP/APS Group  $2 . 
                   Childtraps  : 
                   Description : APS/MSP Forced Switch to work port"
             ::= { alarmsAndEvents 0 340 }

      trapManualSwitchToProtect NOTIFICATION-TYPE
      OBJECTS {
                    objectNameTrapArg,
                    lctNameTrapArg,
                    trapCountTrapArg
                }
      STATUS  current
      DESCRIPTION "Severity    : zilch 
                   Format      :  $1 Manual switch to the protect 
                   port on MSP/APS Group  $2 . 
                   Childtraps  : 
                   Description : APS/MSP Manual Switch to protect 
                   port"
             ::= { alarmsAndEvents 0 341 }

      trapManualSwitchToWork NOTIFICATION-TYPE
      OBJECTS {
                    objectNameTrapArg,
                    lctNameTrapArg,
                    trapCountTrapArg
                }
      STATUS  current
      DESCRIPTION "Severity    : zilch 
                   Format      :  $1 Manual switch to the work  port 
                   on MSP/APS Group  $2 . 
                   Childtraps  : 
                   Description : APS/MSP Manual Switch to work port"
             ::= { alarmsAndEvents 0 342 }

END
