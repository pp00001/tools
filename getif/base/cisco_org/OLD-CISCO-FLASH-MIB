-- *****************************************************************
-- OLD-CISCO-FLASH-MIB.my:  Old Cisco Flash MIB file
--
-- Copyright (c) 1994,1997 by cisco Systems, Inc.
-- All rights reserved.
-- 
-- *****************************************************************
--

               OLD-CISCO-FLASH-MIB DEFINITIONS ::= BEGIN

               IMPORTS
                    TimeTicks
			FROM RFC1155-SMI
		    OBJECT-TYPE
			FROM RFC1212-MIB
                    DisplayString
			FROM RFC1213-MIB
		    local
			FROM CISCO-SMI;
          
               lflash              OBJECT IDENTIFIER ::= { local 10 }

               -- Local cisco Flash Group

          -- This group is present in all products which contain flash"

               flashSize OBJECT-TYPE
                   SYNTAX  INTEGER
                   ACCESS  read-only
                   STATUS  mandatory
                   DESCRIPTION
                           "Total Size in Octets of Flash memory"
                   ::= { lflash 1 }

               flashFree OBJECT-TYPE
                   SYNTAX  INTEGER
                   ACCESS  read-only
                   STATUS  mandatory
                   DESCRIPTION
                           "Unused Size in Octets of Flash memory"
                   ::= { lflash 2 }

               flashController OBJECT-TYPE
                   SYNTAX  DisplayString
                   ACCESS  read-only
                   STATUS  mandatory
                   DESCRIPTION
                           "Provides the type of Flash controller 
                           (either CCTL or CCTL2) installed in the 
                           router."
                   ::= { lflash 3 }

               flashCard OBJECT-TYPE
                   SYNTAX  DisplayString
                   ACCESS  read-only
                   STATUS  mandatory
                   DESCRIPTION
                           "Provides the type of Flash Card installed
                           in the router. For example, the type of 
                           Flash Card could be either CSC-MS or 
                           CSC-MC+."
                   ::= { lflash 4 }

               flashVPP OBJECT-TYPE
                   SYNTAX  INTEGER {
                        installed(1),
                        missing(2)
                   }
                   ACCESS  read-only
                   STATUS  mandatory
                   DESCRIPTION
                           "State of the VPP DIP jumper on the Flash
                           memory card. Files can be written to the
                           Flash memory card only if the VPP DIP
                           jumper is turned on."
                   ::= { lflash 5 }

               flashErase OBJECT-TYPE
                   SYNTAX  INTEGER
                   ACCESS  write-only
                   STATUS  mandatory
                   DESCRIPTION
                           "Request to erase flash memory"
                   ::= { lflash 6 }

               flashEraseTime OBJECT-TYPE
                   SYNTAX  TimeTicks
                   ACCESS  read-only
                   STATUS  mandatory
                   DESCRIPTION
                           "Indicates the value of sysUptime the last
                           time Flash memory was erased. If the flash
                           had not been erased after powerup it has a
                           value of 0 days 00:00:00."
                   ::= { lflash 7 }

               flashEraseStatus OBJECT-TYPE
                   SYNTAX  INTEGER {
                        flashOpInProgress(1),
                        flashOpSuccess(2),
                        flashOpFailure(3),
                        flashReadOnly(4),
                        flashOpenFailure(5),
                        bufferAllocationFailure(6),
                        noOpAfterPowerOn(7)
                   }
                   ACCESS  read-only
                   STATUS  mandatory
                   DESCRIPTION
                           "Status of current or last flash erasing"
                   ::= { lflash 8 }

               flashToNet OBJECT-TYPE
                   SYNTAX  DisplayString
                   ACCESS  write-only
                   STATUS  mandatory
                   DESCRIPTION
                           "Write flash entry to tftp server. Value
                           should be the name of the flash entry to
                           send. Instance is the IP address of the tftp
                           host."
                   ::= { lflash 9 }

               flashToNetTime OBJECT-TYPE
                   SYNTAX  TimeTicks
                   ACCESS  read-only
                   STATUS  mandatory
                   DESCRIPTION
                           "Indicates the value of sysUpTime the last
                            time a file was transfered from Flash memory
                            on the router to a TFTP host. Returns
                            0 days 00:00:00 if there had been no transfer
                            since powerup."
                   ::= { lflash 10 }

               flashToNetStatus OBJECT-TYPE
                   SYNTAX  INTEGER {
                        flashOpInProgress(1),
                        flashOpSuccess(2),
                        flashOpFailure(3),
                        flashReadOnly(4),
                        flashOpenFailure(5),
                        bufferAllocationFailure(6),
                        noOpAfterPowerOn(7)
                   }
                   ACCESS  read-only
                   STATUS  mandatory
                   DESCRIPTION
                           "Status of current or last flash to net
                           transfer"
                   ::= { lflash 11 }

               netToFlash OBJECT-TYPE
                   SYNTAX  DisplayString
                   ACCESS  write-only
                   STATUS  mandatory
                   DESCRIPTION
                           "Write flash entry from tftp server. Value
                           should be the name of the flash entry to
                           write. Instance is the IP address of the tftp
                           host."
                   ::= { lflash 12 }

               netToFlashTime OBJECT-TYPE
                   SYNTAX  TimeTicks
                   ACCESS  read-only
                   STATUS  mandatory
                   DESCRIPTION
                           "Indicates the value of sysUpTime the last
                           time file was copied from a Trivial File
                           Transfer Protocol(TFTP) server to the Flash
                           memory on the router. Returns 0 days 00:00:00
                           if there had been no transfers since powerup."
                   ::= { lflash 13 }

               netToFlashStatus OBJECT-TYPE
                   SYNTAX  INTEGER {
                        flashOpInProgress(1),
                        flashOpSuccess(2),
                        flashOpFailure(3),
                        flashReadOnly(4),
                        flashOpenFailure(5),
                        bufferAllocationFailure(6),
                        noOpAfterPowerOn(7)
                   }
                   ACCESS  read-only
                   STATUS  mandatory
                   DESCRIPTION
                           "Status of current or last net to flash
                           transfer"
                   ::= { lflash 14 }

               flashStatus OBJECT-TYPE
                   SYNTAX  INTEGER {
                        busy(1),
                        available(2)
                   }
                   ACCESS  read-only
                   STATUS  mandatory
                   DESCRIPTION
                           "Status of the availability of flash"
                   ::= { lflash 15 }

               flashEntries OBJECT-TYPE
                   SYNTAX  INTEGER
                   ACCESS  read-only
                   STATUS  mandatory
                   DESCRIPTION
                           "Number of entries in the flash directory"
                   ::= { lflash 16 }


               -- Local Flash file Table

          -- This group contains information on a per file basis

               lflashFileDirTable OBJECT-TYPE
                   SYNTAX  SEQUENCE OF LflashFileDirEntry
                   ACCESS  not-accessible
                   STATUS  mandatory
                   DESCRIPTION
                            " A list of flash file entries."
                   ::= { lflash 17 }

               lflashFileDirEntry OBJECT-TYPE
                   SYNTAX LflashFileDirEntry
                   ACCESS  not-accessible
                   STATUS  mandatory
                   DESCRIPTION
                            "A collection of flash eprom objects"
                   INDEX { flashEntries }
               ::= { lflashFileDirTable 1 }

               LflashFileDirEntry ::=
                   SEQUENCE {
                       flashDirName
                           DisplayString,
                       flashDirSize
                           INTEGER,
                       flashDirStatus
                           INTEGER
                   }

          -- The following section describes the components of the
          -- table.

               flashDirName OBJECT-TYPE
                   SYNTAX  DisplayString
                   ACCESS  read-only
                   STATUS  mandatory
                   DESCRIPTION
                           "Name associated with the flash entry"
                   ::= { lflashFileDirEntry 1 }

               flashDirSize OBJECT-TYPE
                   SYNTAX  INTEGER
                   ACCESS  read-only
                   STATUS  mandatory
                   DESCRIPTION
                           "Size in Octets of a flash entry"
                   ::= { lflashFileDirEntry 2 }

               flashDirStatus OBJECT-TYPE
                   SYNTAX  INTEGER {
                        valid(1),
                        deleted(2)
                   }
                   ACCESS  read-only
                   STATUS  mandatory
                   DESCRIPTION
                           "Indicates the status of the entry"
                   ::= { lflashFileDirEntry 3 }

               -- End of table


END
