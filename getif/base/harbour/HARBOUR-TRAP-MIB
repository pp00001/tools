-- =======================================================================
-- Version info
--
-- Version 0.1 Created 2001.3.16 by Liyan
-- This version of MIB is created just for the use of Network Management Systems
-- Define some traps for Harbour's switch.
--
-- Copyright (c) Harbour Networks Limited All Rights Reserved
-- =======================================================================

HARBOUR-TRAP-MIB DEFINITIONS ::= BEGIN

    IMPORTS
        MODULE-IDENTITY,
	OBJECT-TYPE,
        NOTIFICATION-TYPE   FROM SNMPv2-SMI
	harbournetworks     FROM HARBOUR-BASE-MIB;

    harbourTraps  MODULE-IDENTITY
        LAST-UPDATED 	"20020316"
        ORGANIZATION 	"Harbour Networks Limited All Rights Reserved"
        CONTACT-INFO 	"www.harbournetworks.com"
        DESCRIPTION
            "The MIB module define some traps for Harbour's switch"
    ::= { harbournetworks 3 }


    harbourLinkTraps	MODULE-IDENTITY
        LAST-UPDATED 	"20020723"
        ORGANIZATION 	"Harbour Networks Limited All Rights Reserved"
        CONTACT-INFO 	"www.harbournetworks.com"
        DESCRIPTION
            "The MIB module define some traps for HarbourLinkServer."
    ::= { harbourTraps 1 }


    harbourLinkDevTraps	MODULE-IDENTITY
        LAST-UPDATED 	"20020725"
        ORGANIZATION 	"Harbour Networks Limited All Rights Reserved"
        CONTACT-INFO 	"www.harbournetworks.com"
        DESCRIPTION
            "The MIB module define some device traps for HarbourLinkServer."
    ::= { harbourLinkTraps 1 }


    harbourLinkPortTraps	MODULE-IDENTITY
        LAST-UPDATED 		"20020725"
        ORGANIZATION 		"Harbour Networks Limited All Rights Reserved"
        CONTACT-INFO 		"www.harbournetworks.com"
        DESCRIPTION
            "The MIB module define some port traps for HarbourLinkServer."
    ::= { harbourLinkTraps 2 }


    harbourClusterTraps	MODULE-IDENTITY
        LAST-UPDATED 	"20020806"
        ORGANIZATION 	"Harbour Networks Limited All Rights Reserved"
        CONTACT-INFO 	"www.harbournetworks.com"
        DESCRIPTION
            "The MIB module define some traps for cluster."
    ::= { harbourTraps 2 }


    harbourClusterMemberTraps	MODULE-IDENTITY
        LAST-UPDATED 	"20020806"
        ORGANIZATION 	"Harbour Networks Limited All Rights Reserved"
        CONTACT-INFO 	"www.harbournetworks.com"
        DESCRIPTION
            "The MIB module define some device traps for cluster."
    ::= { harbourClusterTraps 1 }


    harbourClusterPortTraps	MODULE-IDENTITY
        LAST-UPDATED 		"20020806"
        ORGANIZATION 		"Harbour Networks Limited All Rights Reserved"
        CONTACT-INFO 		"www.harbournetworks.com"
        DESCRIPTION
            "The MIB module define some port traps for cluster."
    ::= { harbourClusterTraps 2 }



    harbourSlotDown  NOTIFICATION-TYPE
        STATUS          current
        DESCRIPTION
            "A harbourSlotDown trap will be sent
             when PCB was pulled out from switch's slot."
    ::= { harbourTraps 0 1 }

    harbourSlotUp  NOTIFICATION-TYPE
        STATUS          current
        DESCRIPTION
            "A harbourSlotUp trap will be sent
             when PCB was pushed into switch's slot."
    ::= { harbourTraps 0 2 }

    harbourPlugout NOTIFICATION-TYPE
        OBJECTS         { ifIndex }
        STATUS          current
        DESCRIPTION
            "A harbourPlugout trap is sent by a
             device when any of its ports is plugged out."
    ::= { harbourTraps 0 3 }

    harbourPullin NOTIFICATION-TYPE
        OBJECTS         { ifIndex }
        STATUS          current
        DESCRIPTION
            "A harbourPlugin trap is sent by a
             device when any of its ports is pulled in."
    ::= { harbourTraps 0 4 }

    harbourVtucDown  NOTIFICATION-TYPE
        STATUS          current
        DESCRIPTION
            "A harbourVtucDown trap will be sent
             when VTUC modem loss of link."
    ::= { harbourTraps 0 5 }

    harbourVtucUp  NOTIFICATION-TYPE
        STATUS          current
        DESCRIPTION
            "A harbourVtucUp trap will be sent
             when VTUC modem get link."
    ::= { harbourTraps 0 6 }

    harbourVdslRateRestore  NOTIFICATION-TYPE
        STATUS          current
        DESCRIPTION
            "A harbourVdslRateRestore trap will be sent
             when vdsl up-rate and down-rate are restored
             to ROM mode."
    ::= { harbourTraps 0 7 }

    harbourPortUserExcess  NOTIFICATION-TYPE
        STATUS          current
        DESCRIPTION
            "ISP often specifies a max user number for a port.
             So a harbourPortUserExcess trap will be sent
             when excessive user use a port."
    ::= { harbourTraps 0 8 }

    harbourBroadcastRisingAlarm  NOTIFICATION-TYPE
    	OBJECTS         { ifIndex , bRThreshold , bRAlarmValue}
        STATUS          current
        DESCRIPTION
            "A harbourBroadcastRisingAlarm trap will be sent
             as the broadcast packet received too fast."
    ::= { harbourTraps 0 9 }

    harbourBroadcastRecoverNotice  NOTIFICATION-TYPE
    	OBJECTS         { ifIndex }
        STATUS          current
        DESCRIPTION
            "A harbourBroadcastRecoverNotice trap will be sent
             as a port enabled by broadcast restrain module."
    ::= { harbourTraps 0 10 }

    harbourUtilizationRisingAlarm  NOTIFICATION-TYPE
    	OBJECTS         { ifIndex , utilizationThreshold , utilizationValue }
        STATUS          current
        DESCRIPTION
            "A harbourUtilizationRisingAlarm trap will be sent
             as the port's utilization exceed the threshold."
    ::= { harbourTraps 0 11 }

    harbourVdslRateConfigFail  NOTIFICATION-TYPE
        STATUS          current
        DESCRIPTION
            "A harbourVdslRateConfigFail trap will be sent
             when vdsl up-rate or down-rate can't reach
             specified rate mode after rate configuration."
    ::= { harbourTraps 0 12 }

    harbourPortDropRateAlarm  NOTIFICATION-TYPE
    	OBJECTS         { ifIndex , portDropRateThreshold , portDropRate }
        STATUS          current
        DESCRIPTION
            "A harbourPortDropRateAlarm trap will be sent
             as the port's drop rate exceed the threshold."
    ::= { harbourTraps 0 13 }

    harbourFanFault  NOTIFICATION-TYPE
        STATUS          current
        DESCRIPTION
            "A harbourFanFault trap will be sent
             when a fault occurred in a fan."
    ::= { harbourTraps 0 14 }

    harbourFanWell  NOTIFICATION-TYPE
        STATUS          current
        DESCRIPTION
            "A harbourFanWell trap will be sent
             when a fan get right."
    ::= { harbourTraps 0 15 }

    harbourPPPOEAddressPoolEngrossRatioTrap      NOTIFICATION-TYPE
        OBJECTS {
      		ipLocalPoolName,
       		pppoeAddressPoolMaxEngrossRatio
                }
        STATUS  current
        DESCRIPTION
            "A pppoeAddressPoolEngrossRatio trap will be sent
            when the ratio of using the PPPOE IP address pool
             reachs the threshold ."
     ::= { harbourTraps 0 16 }

--hlink trap

	harbourLinkClientLogin NOTIFICATION-TYPE
    		OBJECTS		{ 	harbourLV2SClientProductName,
					harbourLSuserName,
    					harbourLSclientDevNo,
    					harbourLSclientDevPath }
		STATUS		current
		DESCRIPTION
        		"The harbourLinkClientLogin trap indicates that
                	the hlink client login to the server; the trap
                	is sent by hlink server soon after the hlink
                	client login to it."
    	::= { harbourLinkDevTraps 0 1 }


	harbourLinkClientLogout NOTIFICATION-TYPE
    		OBJECTS		{ 	harbourLV2SClientProductName,
					harbourLSuserName,
    					harbourLSclientDevNo,
    					harbourLSclientDevPath }

	      	STATUS          current
              	DESCRIPTION
                	"The harbourLinkClientLogout trap indicates that
                      	the hlink client logout from the server; the trap
                      	is sent by hlink server soon after the hlink
                      	client login from it."
    	::= { harbourLinkDevTraps 0 2 }


 	harbourLinkClientWarmStart NOTIFICATION-TYPE
    		OBJECTS		{ 	harbourLV2SClientProductName,
					harbourLSuserName,
    					harbourLSclientDevNo,
    					harbourLSclientDevPath }

	      	STATUS          current
              	DESCRIPTION
                	"A harbourLinkClientWarmStart trap is sent by a
                      	hlink server when any of its client warm start.
                      	The warm start info is sent from the client to
                      	the server before this client warm start."
    	::= { harbourLinkDevTraps 0 3 }


	harbourLinkClientColdStart NOTIFICATION-TYPE
    		OBJECTS		{ 	harbourLV2SClientProductName,
					harbourLSuserName,
    					harbourLSclientDevNo,
    					harbourLSclientDevPath }

	      	STATUS          current
              	DESCRIPTION
                	"A harbourLinkClientColdStart trap is sent by a
                      	hlink server when any of its client cold start.
                      	The cold start info is sent from the client to
                      	the server after this client cold start."
    	::= { harbourLinkDevTraps 0 4 }


	harbourLinkClientSynchronizeSuccessful NOTIFICATION-TYPE
    		OBJECTS		{ 	harbourLV2SClientProductName,
					harbourLSuserName,
    					harbourLSclientDevNo,
    					harbourLSclientDevPath }

	      	STATUS          current
              	DESCRIPTION
                	"A harbourLinkClientSynchronizeSuccessful trap is
                      	sent by a hlink server when the admin status of
                      	any of its client's port is enable from disable."
    	::= { harbourLinkDevTraps 0 5 }


	harbourLinkClientSynchronizeFailed NOTIFICATION-TYPE
    		OBJECTS		{ 	harbourLV2SClientProductName,
					harbourLSuserName,
    					harbourLSclientDevNo,
    					harbourLSclientDevPath }

	      	STATUS          current
              	DESCRIPTION
			"A harbourLinkClientSynchronizeFailed trap is sent
                      	by a hlink server when the admin status of any of
                      	its client's port is enable from disable."
    	::= { harbourLinkDevTraps 0 6 }


	harbourLinkClientPortLinkDown NOTIFICATION-TYPE
		OBJECTS		{
					harbourLV2SClientProductName,
					harbourLSuserName,
					harbourLSclientDevNo,
					harbourLSclientDevPortNo,
					harbourLSclientDevPath
				}
	      	STATUS          current
              	DESCRIPTION
                	"A harbourLinkClientPortLinkDown trap is sent by a
                      	hlink server when any of its client's port is
                      	unlink from link."
    	::= { harbourLinkPortTraps 0 1 }


    	harbourLinkClientPortLinkUp NOTIFICATION-TYPE
		OBJECTS		{
					harbourLV2SClientProductName,
					harbourLSuserName,
					harbourLSclientDevNo,
					harbourLSclientDevPortNo,
					harbourLSclientDevPath
				}
	      	STATUS          current
              	DESCRIPTION
                      	"A harbourLinkClientPortLinkUp trap is sent by a
                      	hlink server when any of its client's port is
                      	link from unlink."
    	::= { harbourLinkPortTraps 0 2 }


	harbourLinkClientPortDisable NOTIFICATION-TYPE
		OBJECTS		{
					harbourLV2SClientProductName,
					harbourLSuserName,
					harbourLSclientDevNo,
					harbourLSclientDevPortNo,
					harbourLSclientDevPath
				}
	      	STATUS          current
              	DESCRIPTION
                      	"A harbourLinkClientPortDisable trap is sent by a
                      	hlink server when the admin status of any of its
                      	client's port is disable from enable."
    	::= { harbourLinkPortTraps 0 3 }


	harbourLinkClientPortEnable NOTIFICATION-TYPE
		OBJECTS		{
					harbourLV2SClientProductName,
					harbourLSuserName,
					harbourLSclientDevNo,
					harbourLSclientDevPortNo,
					harbourLSclientDevPath
				}
	      	STATUS          current
              	DESCRIPTION
                	"A harbourLinkClientPortEnable trap is sent by a
                      	hlink server when the admin status of any of its
                      	client's port is enable from disable."
    	::= { harbourLinkPortTraps 0 4 }

--end


 	harbourClusterWarmStart NOTIFICATION-TYPE
		OBJECTS		{ harbourBSeriesClusterSwitcherId }
	      	STATUS          current
              	DESCRIPTION
                	"As the member switch warm start , a trap
                	of this type is send to the commander and
                	then to the NMS."
    	::= { harbourClusterMemberTraps 0 1 }


	harbourClusterColdStart NOTIFICATION-TYPE
		OBJECTS		{ harbourBSeriesClusterSwitcherId }
	      	STATUS          current
              	DESCRIPTION
                	"As the member switch cold start , a trap
                	of this type is send to the commander and
                	then to the NMS."
    	::= { harbourClusterMemberTraps 0 2 }


	harbourClusterRmonRisingAlarm NOTIFICATION-TYPE
		OBJECTS		{ harbourBSeriesClusterSwitcherId,
				alarmIndex, alarmVariable, alarmSampleType,
                                alarmValue, alarmRisingThreshold }
	      	STATUS          current
              	DESCRIPTION
                	"The SNMP trap that is generated when an alarm
                  entry crosses its rising threshold and generates
                  an event that is configured for sending SNMP
                  traps."
    	::= { harbourClusterMemberTraps 0 3 }


	harbourClusterRmonFallingAlarm NOTIFICATION-TYPE
		OBJECTS		{ harbourBSeriesClusterSwitcherId,
				alarmIndex, alarmVariable, alarmSampleType,
                                alarmValue, alarmRisingThreshold }
	      	STATUS          current
              	DESCRIPTION
                	"The SNMP trap that is generated when an alarm
                  entry crosses its falling threshold and generates
                  an event that is configured for sending SNMP
                  traps."
    	::= { harbourClusterMemberTraps 0 4 }


	harbourClusterStpNewRoot NOTIFICATION-TYPE
		OBJECTS		{ harbourBSeriesClusterSwitcherId }
	      	STATUS          current
              	DESCRIPTION
                	"The SNMP trap that is generated when an alarm
                  entry crosses its rising threshold and generates
                  an event that root change with stp."
    	::= { harbourClusterMemberTraps 0 5 }


	harbourClusterStpTopoChange NOTIFICATION-TYPE
		OBJECTS		{ harbourBSeriesClusterSwitcherId }
	      	STATUS          current
              	DESCRIPTION
                	"The SNMP trap that is generated when an alarm
                  entry crosses its rising threshold and generates
                  an event that topo change with stp."
    	::= { harbourClusterMemberTraps 0 6 }


	harbourClusterPortUnlink NOTIFICATION-TYPE
		OBJECTS		{
					harbourBSeriesClusterSwitcherId,
					ifIndex
				}
	      	STATUS          current
              	DESCRIPTION
                	"As one of the member's port link or unlink ,a
                	trap of this type will be send to the commander
                	and the to the NMS."
    	::= { harbourClusterPortTraps 0 1 }


    	harbourClusterPortLink NOTIFICATION-TYPE
		OBJECTS		{
					harbourBSeriesClusterSwitcherId,
					ifIndex
				}
	      	STATUS          current
              	DESCRIPTION
                      	"As one of the member's port link or unlink ,a
                	trap of this type will be send to the commander
                	and the to the NMS."
    	::= { harbourClusterPortTraps 0 2 }


	harbourClusterPortPlugOut NOTIFICATION-TYPE
		OBJECTS		{
					harbourBSeriesClusterSwitcherId,
					ifIndex
				}
	      	STATUS          current
              	DESCRIPTION
                	"As one of the member's port plug out ,a
                	trap of this type will be send to the commander
                	and the to the NMS."
    	::= { harbourClusterPortTraps 0 3 }


	harbourClusterPortPullIn NOTIFICATION-TYPE
		OBJECTS		{
					harbourBSeriesClusterSwitcherId,
					ifIndex
				}
	      	STATUS          current
              	DESCRIPTION
                	"As one of the member's port pull in ,a
                	trap of this type will be send to the commander
                	and the to the NMS."
    	::= { harbourClusterPortTraps 0 4 }
--for nethammer trap

    	harbourNetHammerTraps	MODULE-IDENTITY
	        LAST-UPDATED 	"20020806"
	        ORGANIZATION 	"Harbour Networks Limited All Rights Reserved"
	        CONTACT-INFO 	"www.harbournetworks.com"
	        DESCRIPTION
	            "The MIB module define some traps for NetHammer Router device."
	    ::= { harbourTraps 3 }


 	harbourNetHammerDhcpTraps	MODULE-IDENTITY
	        LAST-UPDATED 	"20020806"
	        ORGANIZATION 	"Harbour Networks Limited All Rights Reserved"
	        CONTACT-INFO 	"www.harbournetworks.com"
	        DESCRIPTION
	            "The MIB module define some device traps for cluster."
	    ::= { harbourNetHammerTraps 1 }

	harbourNetHammerDhcpRelease NOTIFICATION-TYPE
		OBJECTS		{ ifname , ipaddr   }
	      	STATUS          current
              	DESCRIPTION
                	"As the DHCP client release an ipaddress , a trap
                	of this type is send to the commander and
                	then to the NMS.."
    	::= { harbourNetHammerDhcpTraps  0 1 }

    	harbourNetHammerDhcpUpdate NOTIFICATION-TYPE
		OBJECTS		{ ifname , ipaddr  }
	      	STATUS          current
              	DESCRIPTION
                	"As the DHCP client Update an ipaddress , a trap
                	of this type is send to the commander and
                	then to the NMS."
    	::= { harbourNetHammerDhcpTraps  0 2 }

--end



END
