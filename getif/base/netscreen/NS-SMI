-- These MIBs were created on 08/02/2000
--
-- Copyright (c) 1999 - 2000 by NetScreen Technologies, Inc.
-- All rights reserved.
-- 

-- MODULE-IDENTITY
--  OrgName
--    Netscreen Technologies, Inc.
--  ContactInfo
--     Customer Support
--     
--     2860 San TOmas Expwy
--     Santa Clara, CA  95051
--     USA
--    
--     Tel: 1.877.NETSCREEN
--     E-mail: support@netscreen.com
--     Http://www.netscreen.com
--
--  Last modified date: 09/28/2001


NETSCREEN-SMI DEFINITIONS ::= BEGIN
IMPORTS
    IpAddress FROM RFC1155-SMI
    enterprises FROM RFC1155-SMI
    DisplayString FROM RFC1213-MIB;
    
netscreen OBJECT IDENTIFIER ::= { enterprises 3224 }
-- used for Netscreen SysObject ID
netscreenProducts OBJECT IDENTIFIER ::= { netscreen 1 }
-- Netscreen traps
netscreenTrapInfo OBJECT IDENTIFIER ::= { netscreen 2 }
-- Netscreen Intrusion Detect Service Mibs
netscreenIDS OBJECT IDENTIFIER ::= { netscreen 3 }
-- Netscreen VPN Mibs
netscreenVpn OBJECT IDENTIFIER ::= { netscreen 4 }
-- Netscreen QoS Management Mibs
netscreenQos OBJECT IDENTIFIER ::= { netscreen 5 }
-- Netscreen NSRP Mibs
netscreenNsrp OBJECT IDENTIFIER ::= { netscreen 6 }
-- Netscreen Device Setting
netscreenSetting OBJECT IDENTIFIER ::= { netscreen 7 }
-- NetScreen Zone MIB
netscreenZone OBJECT IDENTIFIER ::= { netscreen 8 }
-- NetScreen Interface 
netscreenInterface OBJECT IDENTIFIER ::= { netscreen 9 }
-- NetScreen Policy Info MIB
netscreenPolicy OBJECT IDENTIFIER ::= { netscreen 10 }
-- NetScreen NAT Setting Info MIB
netscreenNAT OBJECT IDENTIFIER ::= { netscreen 11 }
-- NesScreen Address Info MIB
netscreenAddr OBJECT IDENTIFIER ::= { netscreen 12 }
-- NetScreen Service Info MIB 
netscreenService OBJECT IDENTIFIER ::= { netscreen 13 }
-- NetScreen Schedule Info MIB
netscreenSchedule OBJECT IDENTIFIER ::= { netscreen 14 }
-- NetScreen Vsys Info MIB
netscreenVsys OBJECT IDENTIFIER ::= { netscreen 15 }
-- NetScreen Resource MIB
netscreenResource OBJECT IDENTIFIER ::= { netscreen 16 }  
-- NetScreen IP MIP
netscreenIp OBJECT IDENTIFIER ::= { netscreen 17 }
-- NetScreen Chasis MIB
netscreenChasis OBJECT IDENTIFIER ::= { netscreen 21 }

END
