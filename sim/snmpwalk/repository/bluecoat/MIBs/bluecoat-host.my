--
-- BlueCoat Host MIB
--

--
-- IMPORTANT:
--
-- This MIB is intended for internal use only, and is expected to change or be
-- replaced completely in future releases.  It is published only for
-- completeness.  Blue Coat Systems makes no guarantees of fitness or accuracy
-- of values supplied by this interface.
--
-- Any use is strongly discouraged.
--

BLUECOAT-HOST-RESOURCES-MIB DEFINITIONS ::= BEGIN

IMPORTS
       MODULE-IDENTITY, OBJECT-TYPE, NOTIFICATION-TYPE,
       ObjectName, Integer32, Counter32, snmpModules
                  FROM SNMPv2-SMI
       blueCoatMgmt FROM BLUECOAT-MIB;

blueCoatHostResourcesMIB MODULE-IDENTITY
     LAST-UPDATED "200610230000Z"   -- October 23, 2006
     ORGANIZATION "Blue Coat"
     CONTACT-INFO
         "support@bluecoat.com"
     DESCRIPTION
         "Internal MIB defines Blue Coat SG serial number for Blue Coat Director use."
     REVISION "200610230000Z"       -- October 23, 2006
     DESCRIPTION
         "Marked as deprecated."
     ::= { blueCoatMgmt 9 }

--
-- GROUPS
--
bchrDevice        OBJECT IDENTIFIER ::= { blueCoatHostResourcesMIB  1}

--
-- Blue Coat serial number for Blue Coat Director use
--
bchrSerial  OBJECT-TYPE
         SYNTAX  OCTET STRING (SIZE (0..20))
         MAX-ACCESS read-only
         STATUS  deprecated
         DESCRIPTION
                 "Serial number of the Blue Coat SG."
         ::= { bchrDevice 1 }
END
